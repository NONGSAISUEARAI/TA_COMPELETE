;;; Real WIPEOUTs generated by AutoCAD from known polygons. Independent oracle:
;;; their recovered world vertices must equal the ORIGINAL drawn vertices.
(setq shw-eps 1e-7 sh21-pass 0 sh21-fail 0
      sh21-log (open (strcat sht-root "tests/results-v21.txt") "w"))
(defun SH21:Assert (label ok)
  (write-line (strcat (if ok "PASS " "FAIL ") label) sh21-log)
  (if ok (setq sh21-pass (1+ sh21-pass)) (setq sh21-fail (1+ sh21-fail))))
(defun SH21:XYZ (p) (list (car p) (cadr p) (if (caddr p) (caddr p) 0.0)))
(defun SH21:SameVertices (expected actual / ok p)
  (setq ok (= (length expected) (length actual)))
  (foreach p expected
    (if (not (vl-some '(lambda (q) (equal (SH21:XYZ p) q 1e-6)) actual)) (setq ok nil))) ok)
(defun SH21:Wipe (points / en)
  (setq en (entmakex (append
    (list '(0 . "LWPOLYLINE") '(100 . "AcDbEntity") '(100 . "AcDbPolyline")
      (cons 90 (length points)) '(70 . 1))
    (mapcar '(lambda (p) (cons 10 (list (car p) (cadr p)))) points))))
  (command-s "_.WIPEOUT" "_Polyline" en "_No")
  (entlast))
(defun SH21:Check (label points / wipe)
  (setq wipe (SH21:Wipe points))
  (SH21:Assert label (SH21:SameVertices points (TA:SHW:WipeVertices (entget wipe)))))
(defun SH21:CutXs (points y / edges a b xs)
  (setq edges (append points (list (car points))))
  (while (cdr edges)
    (setq a (car edges) b (cadr edges))
    (if (or (and (<= (cadr a) y) (< y (cadr b)))
            (and (<= (cadr b) y) (< y (cadr a))))
      (setq xs (cons (+ (car a) (* (- y (cadr a))
        (/ (- (car b) (car a)) (- (cadr b) (cadr a))))) xs)))
    (setq edges (cdr edges)))
  (vl-sort xs '<))
(defun SH21:Run (/ points wipe actual angle c s expected mirrored data)
  (SH21:Check "square mask remains unchanged" '((0.0 0.0) (10.0 0.0) (10.0 10.0) (0.0 10.0)))
  (SH21:Check "wide rectangular mask stays at its original elevation in XY"
    '((0.0 0.0) (18.0 0.0) (18.0 10.0) (0.0 10.0)))
  (SH21:Check "tall rectangle remains correct" '((0.0 0.0) (6.0 0.0) (6.0 10.0) (0.0 10.0)))
  (setq points '((2.0 0.0) (20.0 0.0) (20.0 10.0) (6.0 10.0))
        wipe (SH21:Wipe points) actual (TA:SHW:WipeVertices (entget wipe)))
  (SH21:Assert "sloped mask matches drawn polygon, without vertical reflection or shift"
    (SH21:SameVertices points actual))
  (SH21:Assert "lower horizontal source starts at x=2.8, not the mirrored edge"
    (equal '(2.8 20.0) (SH21:CutXs actual 2.0) 1e-6))
  (SH21:Assert "upper horizontal source starts at x=5.2"
    (equal '(5.2 20.0) (SH21:CutXs actual 8.0) 1e-6))
  (SH21:Assert "no hidden segment is generated above the actual mask"
    (null (SH21:CutXs actual 14.0)))
  (SH21:Check "clockwise sloped mask" (reverse points))
  (SH21:Check "concave masking boundary"
    '((0.0 0.0) (20.0 0.0) (20.0 3.0) (8.0 3.0) (8.0 10.0) (0.0 10.0)))
  (command-s "_.ROTATE" wipe "" '(0.0 0.0 0.0) "37")
  (setq angle (* pi (/ 37.0 180.0)) c (cos angle) s (sin angle)
        expected (mapcar '(lambda (p) (list (- (* c (car p)) (* s (cadr p)))
                                           (+ (* s (car p)) (* c (cadr p))))) points))
  (SH21:Assert "native rotated WIPEOUT follows its U/V vectors"
    (SH21:SameVertices expected (TA:SHW:WipeVertices (entget wipe))))
  (command-s "_.MIRROR" wipe "" '(0.0 0.0 0.0) '(1.0 0.0 0.0) "_No")
  (setq mirrored (entlast) expected (mapcar '(lambda (p) (list (car p) (- (cadr p)))) expected))
  (SH21:Assert "native mirrored WIPEOUT preserves its handedness"
    (SH21:SameVertices expected (TA:SHW:WipeVertices (entget mirrored))))
  (command-s "_.MOVE" mirrored "" '(0.0 0.0 0.0) '(368298.357578048 394547.737881694 0.0))
  (setq expected (mapcar '(lambda (p)
    (list (+ (car p) 368298.357578048) (+ (cadr p) 394547.737881694))) expected))
  (SH21:Assert "large drawing coordinates match the real project coordinate range"
    (SH21:SameVertices expected (TA:SHW:WipeVertices (entget mirrored))))
  ;; An explicit DXF rectangle with non-default image pixel height also uses
  ;; that height, rather than assuming image dimensions of one pixel.
  (setq data '((10 100.0 200.0 0.0) (11 10.0 0.0 0.0) (12 0.0 10.0 0.0)
    (13 1.0 2.0 0.0) (71 . 1) (14 -0.5 -0.5 0.0) (14 0.5 1.5 0.0)))
  (SH21:Assert "rectangular clip uses the actual image height"
    (SH21:SameVertices '((100.0 200.0) (110.0 200.0) (110.0 220.0) (100.0 220.0))
      (TA:SHW:WipeVertices data)))
  (write-line (strcat "TOTAL " (itoa sh21-pass) " passed, " (itoa sh21-fail) " failed") sh21-log)
  (close sh21-log)
  (princ (strcat "\nV2.1 TOTAL " (itoa sh21-pass) " passed, " (itoa sh21-fail) " failed")))
(SH21:Run)
(princ)
