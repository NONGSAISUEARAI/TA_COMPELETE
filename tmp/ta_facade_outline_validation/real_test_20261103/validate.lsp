(load "C:/Users/tawan.t/Documents/GitHub/TA_COMPELETE/GPT CODE/TA_FACADE_OUTLINE/TA_FACADE_OUTLINE.lsp")
(setq tfoi-ss (ssget "_X" '((410 . "Model") (0 . "LWPOLYLINE"))))
(setq tfoi-index 0 tfoi-sources nil)
(repeat (sslength tfoi-ss)
  (setq tfoi-sources (cons (ssname tfoi-ss tfoi-index) tfoi-sources) tfoi-index (1+ tfoi-index)))
(setq tfoi-before (mapcar 'entget tfoi-sources)
      tfoi-pickfirst (getvar "PICKFIRST"))
(setvar "PICKFIRST" 1) (sssetfirst nil tfoi-ss)
(c:FO)
(setvar "PICKFIRST" tfoi-pickfirst)
(setq tfoi-out (ssget "_X" '((410 . "Model") (8 . "TA-FACADE-OUTLINE,TA-FACADE-INFO")))
      tfoi-file (open "C:/Users/tawan.t/Documents/GitHub/TA_COMPELETE/outputs/fo_test_debug/fixed-geometry.lspdata" "w")
      tfoi-report (open "C:/Users/tawan.t/Documents/GitHub/TA_COMPELETE/outputs/fo_test_debug/validation.txt" "w")
      tfoi-index 0)
(defun TFOI:Log (text) (princ (strcat "\n" text)) (write-line text tfoi-report))
(defun TFOI:Dump (kind entity)
  (prin1 (list kind (vl-remove-if '(lambda (pair) (= (type (cdr pair)) 'ENAME)) (entget entity))) tfoi-file)
  (write-line "" tfoi-file))
(TFOI:Log "Validated c:FO with the original 14 panel plines from test.dwg in a disposable copy.")
(if tfoi-out
  (repeat (sslength tfoi-out)
    (setq entity (ssname tfoi-out tfoi-index) data (entget entity) tfoi-index (1+ tfoi-index))
    (TFOI:Dump "ENTITY" entity)
    (if (= "LWPOLYLINE" (TFO:Get 0 data ""))
      (TFOI:Log (strcat "Closed outline: vertices=" (itoa (TFO:Get 90 data 0))
        "; area-m2=" (rtos (* factor_area_ (abs (TFO:LoopArea (TFO:LWVertices data)))) 2 8))))
    (if (= "INSERT" (TFO:Get 0 data ""))
      (progn
        (TFOI:Log (strcat "INFO block=" (TFO:Get 2 data "")))
        (while (and (setq entity (entnext entity)) (/= "SEQEND" (TFO:Get 0 (setq data (entget entity)) "")))
          (if (= "ATTRIB" (TFO:Get 0 data ""))
            (progn (TFOI:Dump "ATTRIBUTE" entity)
              (TFOI:Log (strcat (TFO:Get 2 data "") "=" (TFO:Get 1 data ""))))))))))
(TFOI:Log (strcat "Sources unchanged=" (if (equal tfoi-before (mapcar 'entget tfoi-sources)) "YES" "NO")))
(TFOI:Log (strcat "Output root entities=" (if tfoi-out (itoa (sslength tfoi-out)) "0")))
(close tfoi-file) (close tfoi-report)
(command-s "_.ZOOM" "_Extents")
(princ)
