(load "C:/Users/tawan.t/Documents/GitHub/TA_COMPELETE/GPT CODE/TA_FACADE_OUTLINE/TA_FACADE_OUTLINE.lsp")
(setq tfoi-file (open "C:/Users/tawan.t/Documents/GitHub/TA_COMPELETE/tmp/ta_facade_outline_validation/real_test_20261103/debug.lspdata" "w"))
(defun TFOI:Print (value / tail)
  (cond
    ((null value) (princ "nil" tfoi-file))
    ((= (type value) 'REAL) (princ (rtos value 2 14) tfoi-file))
    ((listp value)
      (princ "(" tfoi-file) (setq tail value)
      (while (and tail (listp tail))
        (TFOI:Print (car tail)) (setq tail (cdr tail))
        (if tail (princ " " tfoi-file)))
      (if tail (progn (princ ". " tfoi-file) (TFOI:Print tail)))
      (princ ")" tfoi-file))
    (T (prin1 value tfoi-file))))
(defun TFOI:Write (label value) (TFOI:Print (list label value)) (write-line "" tfoi-file))
(defun TFOI:Data (entity) (vl-remove-if '(lambda (pair) (= (type (cdr pair)) 'ENAME)) (entget entity)))
(setq TFOI:OriginalGeometryLoops TFO:GeometryLoops TFOI:OriginalCoverage TFO:CheckCoverage
      TFOI:OriginalOuterLoops TFO:OuterLoops)
(defun TFO:OuterLoops (loops / result)
  (TFOI:Write "OUTER_IN" loops)
  (setq result (TFOI:OriginalOuterLoops loops))
  (TFOI:Write "OUTER_OUT" result) result)
(defun TFO:GeometryLoops (curves / result)
  (TFOI:Write "GEOMETRY_IN" (mapcar 'TFOI:Data curves))
  (setq result (TFOI:OriginalGeometryLoops curves))
  (TFOI:Write "GEOMETRY_OUT" result) result)
(defun TFO:CheckCoverage (curves loops / boundaries vertices curve edge)
  (foreach vertices loops (setq boundaries (cons (TFO:LoopEdges vertices T) boundaries)))
  (foreach curve curves
    (foreach edge (TFO:EntityEdges curve)
      (if (not (TFO:EdgeCovered edge boundaries))
        (progn
          (TFOI:Write "UNCOVERED" (list (TFOI:Data curve) edge))
          (princ (strcat "\nUNCOVERED " (vl-princ-to-string edge)))))))
  (TFOI:OriginalCoverage curves loops))
(setq tfoi-ss (ssget "_X" '((410 . "Model") (0 . "INSERT,LWPOLYLINE,POLYLINE,LINE,ARC,CIRCLE"))))
(TFOI:Write "INPUT" (mapcar 'TFOI:Data (vl-remove-if 'null (mapcar 'handent '("31C" "31B" "31A" "319" "318" "317" "315" "314" "313" "311" "310" "30F" "30C" "30B")))))
(setq tfoi-result (TFO:CommandBuild tfoi-ss))
(close tfoi-file)
(princ)
