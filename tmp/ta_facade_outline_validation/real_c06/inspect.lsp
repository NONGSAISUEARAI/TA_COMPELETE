;;; Read-only inventory of the disposable DWG copy.
(defun TFOI:Data (entity / data)
  (setq data (entget entity))
  (vl-remove-if '(lambda (pair) (= (type (cdr pair)) 'ENAME)) data))
(defun TFOI:Write (kind value)
  (prin1 (list kind value) tfoi-file) (write-line "" tfoi-file))
(defun TFOI:Dump (/ ss index entity record child)
  (setq tfoi-file (open (strcat tfoi-root "inventory.lspdata") "w"))
  (foreach name '("INSUNITS" "LUNITS" "LUPREC" "EXTMIN" "EXTMAX" "DWGNAME" "CTAB")
    (TFOI:Write "VAR" (list name (getvar name))))
  (setq ss (ssget "_X") index 0)
  (if ss
    (repeat (sslength ss)
      (setq entity (ssname ss index))
      (TFOI:Write "ENTITY" (TFOI:Data entity))
      (if (= "INSERT" (cdr (assoc 0 (entget entity))))
        (progn
          (setq child entity)
          (if (= 1 (cdr (assoc 66 (entget entity))))
            (while (and (setq child (entnext child)) (/= "SEQEND" (cdr (assoc 0 (entget child)))))
              (TFOI:Write "ATTRIBUTE" (TFOI:Data child))))))
      (setq index (1+ index))))
  (setq record (tblnext "LAYER" T))
  (while record (TFOI:Write "LAYER" record) (setq record (tblnext "LAYER")))
  (setq record (tblnext "BLOCK" T))
  (while record
    (TFOI:Write "BLOCK" (vl-remove-if '(lambda (pair) (= (type (cdr pair)) 'ENAME)) record))
    (setq child (cdr (assoc -2 record)))
    (while (and child (/= "ENDBLK" (cdr (assoc 0 (entget child)))))
      (TFOI:Write "CHILD" (TFOI:Data child)) (setq child (entnext child)))
    (setq record (tblnext "BLOCK")))
  (close tfoi-file) (princ "\nTFOI: inventory complete.") (princ))
(TFOI:Dump)
