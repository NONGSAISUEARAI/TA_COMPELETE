;;; Inspect actual inserted attributes in a disposable blank drawing.
(setq fmlp-log (open "C:/Users/tawan.t/Documents/GitHub/TA_COMPELETE/tmp/ta_facade_outline_validation/fml_prefix_20261109/attributes.txt" "w"))
(defun FMLP:Log (value) (write-line value fmlp-log) (princ (strcat "\n" value)))
(defun FMLP:Definition (/ child data result)
  (setq child (cdr (assoc -2 (tblsearch "BLOCK" block_maxlength_))))
  (while (and child (/= "ENDBLK" (TFO:Get 0 (setq data (entget child)) "")))
    (setq result (cons data result) child (entnext child))) (reverse result))
(defun FMLP:Record (label / ss index root attribute data)
  (setq ss (ssget "_X" (list '(0 . "INSERT") (cons 8 layer_maxlength_))) index 0)
  (FMLP:Log (strcat "CASE=" label "; INSERTS=" (if ss (itoa (sslength ss)) "0")))
  (if ss (repeat (sslength ss)
    (setq root (ssname ss index) index (1+ index) attribute root)
    (FMLP:Log (strcat "  BLOCK=" (TFO:Get 2 (entget root) "")))
    (while (and (setq attribute (entnext attribute)) (/= "SEQEND" (TFO:Get 0 (setq data (entget attribute)) "")))
      (if (= "ATTRIB" (TFO:Get 0 data ""))
        (FMLP:Log (strcat "  " (TFO:Get 2 data "") "=" (TFO:Get 1 data "")))))
    (entdel root))))
(defun FMLP:Finish ()
  (FMLP:Log (strcat "BLOCK_DEFINITION_REUSED=" (if (equal fmlp-definition (FMLP:Definition)) "YES" "NO")))
  (FMLP:Log (strcat "SOURCE_UNCHANGED=" (if (equal fmlp-before (entget fmlp-source)) "YES" "NO")))
  (entdel fmlp-source) (close fmlp-log) (princ))
(entmake (TFO:LWData '(((0.0 0.0) 0.0) ((2010.0 0.0) 0.0) ((2010.0 100.0) 0.0) ((0.0 100.0) 0.0)) 0.0 "0"))
(setq fmlp-source (entlast) fmlp-before (entget fmlp-source) fmlp-ss (ssadd))
(ssadd fmlp-source fmlp-ss)
(setvar "PICKFIRST" 1)
(princ)
