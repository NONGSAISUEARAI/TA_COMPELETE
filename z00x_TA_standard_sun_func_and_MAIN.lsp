;setvar before run drawing
(if (= first_time_login nil)
  (progn
    (setvar 'luprec 8)
    (setvar 'auprec  8)
    ; (alert "ภายในสามนาทีหลังจากนี้\nถ้ายังไม่ปิดคอมเครื่องนี้ ก็ไม่เป็นไม่ต้องปิด แค่นั้นแหละ")
    ; (alert "คงจะอยากรู้สินะว่าจะต้องกด อีกกี่ที ผมถึงจะปล่อยให้คุณได้ทำงานสักที ")
    ; (alert "5")
    ; (alert "4")
    ; (alert "3")
    ; (alert "2")
    ; (alert "1")
    ; (alert "คิดว่า 0 หรอ \nไม่ !!!\nมันจะเร็วไป\nไม่สาแก่ใจ อีช้อย")
    ; (alert "5")
    ; (alert "4")
    ; (alert "3")
    ; (alert "2")
    ; (alert "1")
    ; (alert "5")
    ; (alert "4")
    ; (alert "3")
    ; (alert "2")
    ; (alert "1")
    ; (alert "5")
    ; (alert "4")
    ; (alert "3")
    ; (alert "2")
    ; (alert "1")
    (setq first_time_login "")
  )
)
;
;update 20250628 4:34pm
  ;Effective Block Name Funcition Lee Mac
    ;; Effective Block Name  -  Lee Mac
      ;; obj - [vla] VLA Block Reference object
    (defun LM:effectivename (obj) 
      (vlax-get-property obj 
                        (if (vlax-property-available-p obj 'effectivename) 
                          'effectivename
                          'name
                        )
      )
    )
    ;; Effective Block Name  -  Lee Mac
    ;; ent - [ent] Block Reference entity
    (defun LM:al-effectivename (ent / blk rep) 
      (if (wcmatch (setq blk (cdr (assoc 2 (entget ent)))) "`**") 
        (if 
          (and 
            (setq rep (cdadr 
                        (assoc -3 
                              (entget 
                                (cdr 
                                  (assoc 330 
                                          (entget 
                                            (tblobjname "block" blk)
                                          )
                                  )
                                )
                                '("AcDbBlockRepBTag")
                              )
                        )
                      )
            )
            (setq rep (handent (cdr (assoc 1005 rep))))
          )
          (setq blk (cdr (assoc 2 (entget rep))))
        )
      )
      blk
    )

  ;
  ;Attribute Function Lee Mac
    ;; Get Attribute Value  -  Lee Mac
    ;; Returns the value held by the specified tag within the supplied block, if present.
    ;; blk - [vla] VLA Block Reference Object
    ;; tag - [str] Attribute TagString
    ;; Returns: [str] Attribute value, else nil if tag is not found.
    (defun LM:vl-getattributevalue (blk tag) 
      (setq tag (strcase tag))
      (vl-some 
        '(lambda (att) 
          (if (= tag (strcase (vla-get-tagstring att))) (vla-get-textstring att))
        )
        (vlax-invoke blk 'getattributes)
      )
    )
    ;; Set Attribute Value  -  Lee Mac
    ;; Sets the value of the first attribute with the given tag found within the block, if present.
    ;; blk - [vla] VLA Block Reference Object
    ;; tag - [str] Attribute TagString
    ;; val - [str] Attribute Value
    ;; Returns: [str] Attribute value if successful, else nil.
    (defun LM:vl-setattributevalue (blk tag val) 
      (setq tag (strcase tag))
      (vl-some 
        '(lambda (att) 
          (if (= tag (strcase (vla-get-tagstring att))) 
            (progn (vla-put-textstring att val) val)
          )
        )
        (vlax-invoke blk 'getattributes)
      )
    )
    ;; Get Attribute Values  -  Lee Mac
    ;; Returns an association list of attributes present in the supplied block.
    ;; blk - [vla] VLA Block Reference Object
    ;; Returns: [lst] Association list of ((<tag> . <value>) ... )
    (defun LM:vl-getattributevalues (blk) 
      (mapcar '(lambda (att) (cons (vla-get-tagstring att) (vla-get-textstring att))) 
              (vlax-invoke blk 'getattributes)
      )
    )
    (defun LM:vl-getattributevalue-tag-TA-Modifies (blk) 
      (mapcar '(lambda (att) (vla-get-tagstring att)) 
              (vlax-invoke blk 'getattributes)
      )
    )
    (defun LM:vl-getattributevalue-val-TA-Modifies (blk) 
      (mapcar '(lambda (att) (vla-get-textstring att)) 
              (vlax-invoke blk 'getattributes)
      )
    )
    ;; Set Attribute Values  -  Lee Mac
    ;; Sets attributes with tags found in the association list to their associated values.
    ;; blk - [vla] VLA Block Reference Object
    ;; lst - [lst] Association list of ((<tag> . <value>) ... )
    ;; Returns: nil
    (defun LM:vl-setattributevalues (blk lst / itm) 
      (foreach att (vlax-invoke blk 'getattributes) 
        (if (setq itm (assoc (vla-get-tagstring att) lst)) 
          (vla-put-textstring att (cdr itm))
        )
      )
    )
  ;
  ;Dynamic Funcion Lee Mac
    ;; Get Dynamic Block Property Value  -  Lee Mac
      ;; Returns the value of a Dynamic Block property (if present)
      ;; blk - [vla] VLA Dynamic Block Reference object
      ;; prp - [str] Dynamic Block property name (case-insensitive)

      (defun LM:getdynpropvalue ( blk prp )
          (setq prp (strcase prp))
          (vl-some '(lambda ( x ) (if (= prp (strcase (vla-get-propertyname x))) (vlax-get x 'value)))
              (vlax-invoke blk 'getdynamicblockproperties)
          )
      )
    ;; Set Dynamic Block Property Value  -  Lee Mac
      ;; Modifies the value of a Dynamic Block property (if present)
      ;; blk - [vla] VLA Dynamic Block Reference object
      ;; prp - [str] Dynamic Block property name (case-insensitive)
      ;; val - [any] New value for property
      ;; Returns: [any] New value if successful, else nil

      (defun LM:setdynpropvalue ( blk prp val )
          (setq prp (strcase prp))
          (vl-some
            '(lambda ( x )
                  (if (= prp (strcase (vla-get-propertyname x)))
                      (progn
                          (vla-put-value x (vlax-make-variant val (vlax-variant-type (vla-get-value x))))
                          (cond (val) (t))
                      )
                  )
              )
              (vlax-invoke blk 'getdynamicblockproperties)
          )
      )
    ;; Get Dynamic Block Properties  -  Lee Mac
      ;; Returns an association list of Dynamic Block properties & values.
      ;; blk - [vla] VLA Dynamic Block Reference object
      ;; Returns: [lst] Association list of ((<prop> . <value>) ... )

      (defun LM:getdynprops ( blk )
          (mapcar '(lambda ( x ) (cons (vla-get-propertyname x) (vlax-get x 'value)))
              (vlax-invoke blk 'getdynamicblockproperties)
          )
      )
      (defun LM:getdynprops_nonvalue ( blk )
          (mapcar '(lambda ( x ) (vla-get-propertyname x))
              (vlax-invoke blk 'getdynamicblockproperties)
          )
      )
    ;; Set Dynamic Block Properties  -  Lee Mac
      ;; Modifies values of Dynamic Block properties using a supplied association list.
      ;; blk - [vla] VLA Dynamic Block Reference object
      ;; lst - [lst] Association list of ((<Property> . <Value>) ... )
      ;; Returns: nil

      (defun LM:setdynprops ( blk lst / itm )
          (setq lst (mapcar '(lambda ( x ) (cons (strcase (car x)) (cdr x))) lst))
          (foreach x (vlax-invoke blk 'getdynamicblockproperties)
              (if (setq itm (assoc (strcase (vla-get-propertyname x)) lst))
                  (vla-put-value x (vlax-make-variant (cdr itm) (vlax-variant-type (vla-get-value x))))
              )
          )
      )
    ;; Get Dynamic Block Property Allowed Values  -  Lee Mac
      ;; Returns the allowed values for a specific Dynamic Block property.
      ;; blk - [vla] VLA Dynamic Block Reference object
      ;; prp - [str] Dynamic Block property name (case-insensitive)
      ;; Returns: [lst] List of allowed values for property, else nil if no restrictions

      (defun LM:getdynpropallowedvalues ( blk prp )
          (setq prp (strcase prp))
          (vl-some '(lambda ( x ) (if (= prp (strcase (vla-get-propertyname x))) (vlax-get x 'allowedvalues)))
              (vlax-invoke blk 'getdynamicblockproperties)
          )
      )
    ;; Toggle Dynamic Block Flip State  -  Lee Mac
      ;; Toggles the Flip parameter if present in a supplied Dynamic Block.
      ;; blk - [vla] VLA Dynamic Block Reference object
      ;; Return: [int] New Flip Parameter value

      (defun LM:toggleflipstate ( blk )
          (vl-some
            '(lambda ( prp / rtn )
                  (if (equal '(0 1) (vlax-get prp 'allowedvalues))
                      (progn
                          (vla-put-value prp (vlax-make-variant (setq rtn (- 1 (vlax-get prp 'value))) vlax-vbinteger))
                          rtn
                      )
                  )
              )
              (vlax-invoke blk 'getdynamicblockproperties)
          )
      )
    ;; Get Visibility Parameter Name  -  Lee Mac
      ;; Returns the name of the Visibility Parameter of a Dynamic Block (if present)
      ;; blk - [vla] VLA Dynamic Block Reference object
      ;; Returns: [str] Name of Visibility Parameter, else nil

      (defun LM:getvisibilityparametername ( blk / vis )  
          (if
              (and
                  (vlax-property-available-p blk 'effectivename)
                  (setq blk
                      (vla-item
                          (vla-get-blocks (vla-get-document blk))
                          (vla-get-effectivename blk)
                      )
                  )
                  (= :vlax-true (vla-get-isdynamicblock blk))
                  (= :vlax-true (vla-get-hasextensiondictionary blk))
                  (setq vis
                      (vl-some
                        '(lambda ( pair )
                              (if
                                  (and
                                      (= 360 (car pair))
                                      (= "BLOCKVISIBILITYPARAMETER" (cdr (assoc 0 (entget (cdr pair)))))
                                  )
                                  (cdr pair)
                              )
                          )
                          (dictsearch
                              (vlax-vla-object->ename (vla-getextensiondictionary blk))
                              "ACAD_ENHANCEDBLOCK"
                          )
                      )
                  )
              )
              (cdr (assoc 301 (entget vis)))
          )
      )
    ;; Get Dynamic Block Visibility State  -  Lee Mac
      ;; Returns the value of the Visibility Parameter of a Dynamic Block (if present)
      ;; blk - [vla] VLA Dynamic Block Reference object
      ;; Returns: [str] Value of Visibility Parameter, else nil

      (defun LM:getvisibilitystate ( blk / vis )
          (if (setq vis (LM:getvisibilityparametername blk))
              (LM:getdynpropvalue blk vis)
          )
      )
    ;; Set Dynamic Block Visibility State  -  Lee Mac
      ;; Sets the Visibility Parameter of a Dynamic Block (if present) to a specific value (if allowed)
      ;; blk - [vla] VLA Dynamic Block Reference object
      ;; val - [str] Visibility State Parameter value
      ;; Returns: [str] New value of Visibility Parameter, else nil

      (defun LM:SetVisibilityState ( blk val / vis )
          (if
              (and
                  (setq vis (LM:getvisibilityparametername blk))
                  (member (strcase val) (mapcar 'strcase (LM:getdynpropallowedvalues blk vis)))
              )
              (LM:setdynpropvalue blk vis val)
          )
      )
  ;
  ;Remove&Edit List Function Lee Mac
    (defun LM:RemoveNth (n l / i) 
      ;;  Arguments:                                              ;;
      ;;  n - index of item to remove (zero based)                ;;
      ;;  l - list from which item is to be removed               ;;
        (setq i -1)
        (vl-remove-if '(lambda (x) (= (setq i (1+ i)) n)) l)
    )
    (defun LM:str->lst ( str del / len lst pos )
      (setq len (1+ (strlen del)))
      (while (setq pos (vl-string-search del str))
          (setq lst (cons (substr str 1 pos) lst)
                str (substr str (+ pos len))
          )
      )
      (reverse (cons str lst))
    )
    (defun LM:lst->str ( lst del / str )
      (setq str (car lst))
      (foreach itm (cdr lst) (setq str (strcat str del itm)))
      str
    )
    (defun TA:list-to-Text (target_list_)  
      ;preloop_and_while
        (setq target_list_i 0)
        (setq target_result_list ())
        (while (< target_list_i (length target_list_))
          (setq target_list_val_ (nth  target_list_i target_list_))
          (cond
            ( (= (type target_list_val_) 'REAL)
              (progn
                (setq convert_val_  (rtos target_list_val_ 2 4))
                (setq target_result_list (cons convert_val_ target_result_list ))
              )
            )
            ( (= (type target_list_val_) 'INT)
              (progn
                (setq convert_val_  (rtos target_list_val_ 2 4))
                (setq target_result_list (cons convert_val_ target_result_list ))
              )
            )
            ( (and 
                (/= (type target_list_val_) 'INT)
                (/= (type target_list_val_) 'REAL)
              )
              (progn
                (setq target_result_list (cons target_list_val_ target_result_list))
              )
            )
          )
          (setq target_list_i (+ target_list_i 1))
        )
      ;
      (setq target_result_list (reverse target_result_list ))
    )
  ;
  ;Method Selection Set Ta Trai
    (defun TA:standard_func_selection_set_cond_case_1 () ;วิธีเก็บข้อมูล selection set แบบเดียวกับ pickfirst variable
      ;selection_set
        (if  ;pre_select_ssget_or_post_select_ssget
          (= 
            (setq ss_pre_filter_set_xx (ssget "I" 
                                              (list 
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx (ssget 
                                          (list 
                                            (cons 0 "INSERT") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx)
        )
      ;
    )
    (defun TA:standard_func_entsel_case_1 () ;วิธีเก็บข้อมูลแบบตัวแปรเดี่ยวตามเงื่อนไข (condition rule) จนกว่าจะถูกต้อง
      ;user_input get_effectivename 
        (setq get_effectivename_ nil)
        (setq get_effectivename_obj_val_ nil)
        ;preloop_and_while_
            (while (not get_effectivename_)
              (pri  nc (setq get_effectivename_ (car (entsel "\nPlease Specify Attribute Block\n"))))
              (if (and ;condition rule
                    (/= get_effectivename_ nil)
                    (= (vla-get-hasattributes (vlax-ename->vla-object get_effectivename_)) :vlax-true)
                    ; (/= (vla-get-isdynamicblock (vlax-ename->vla-object get_effectivename_)) :vlax-true)
                  )
                (progn ;add data
                  ; (alert "\nplease select block object")
                  ; (setq get_effectivename_ nil)
                  ; (setq get_effectivename_obj_val_ nil)
                  (setq get_effectivename_obj_val_ (LM:Effectivename (vlax-ename->vla-object get_effectivename_)))
                  ;add more
                )
                (setq get_effectivename_ nil)
              )
            )
        ;
      ;
      ;user_input_get_block_(not loop)
        ;block_data_for insertion
          (setq blk_ename_ (car (entsel "specify_block_")))
          (setq blk_ename_obj_ (vlax-ename->vla-object blk_ename_))
          (if (= (setq type_obj_ (vla-get-objectname (vlax-ename->vla-object blk_ename_))) "AcDbBlockReference") ;For Check objectname
            (progn
              (setq blk_ename_obj_inspt_ (vlax-safearray->list (vlax-variant-value (vla-get-insertionpoint blk_ename_obj_))))
              (setq blk_ename_obj_efname_ (LM:effectivename blk_ename_obj_ ))
            )
            (alert "Object is not block.")
          )
        ;
      ;
      ;get_data_dynamic_block_object
        (if (= 1 1) 
          (progn
            ;user_input_get_block_(not loop)
              ;block_data_for insertion
                (if (/= (setq blk_ename_ (car (entsel "specify_block_"))) nil)
                  (progn
                    (setq blk_ename_obj_ (vlax-ename->vla-object blk_ename_))
                  )
                  (alert "Object is blank.")
                )         
                (if (and
                      (= (setq type_obj_ (vla-get-objectname (vlax-ename->vla-object blk_ename_))) "AcDbBlockReference");For Check objectname
                      (= (vla-get-isdynamicblock blk_ename_obj_) :vlax-true );For Check objectname is dynamicblock
                    ) 
                  (progn
                    (setq blk_ename_obj_inspt_ (vlax-safearray->list (vlax-variant-value (vla-get-insertionpoint blk_ename_obj_))))
                    (setq blk_ename_obj_efname_ (LM:effectivename blk_ename_obj_ ))
                  )
                  (alert "Object is not block.")
                )
              ;
            ;
          )
        )
      ;
    )
  ;
  ;Sorting Coordinate Function Ta Trai
    (defun CO:sort_by_X (list_)  ;เรียงชุดข้อมูลตามแนวแกน
      (setq sortedLst (vl-sort list_ (function (lambda (a b) (< (car (cadr a)) (car (cadr b)))))))
    )
    (defun CO:sort_by_y (list_)  ;เรียงชุดข้อมูลตามแนวแกน
      (setq sortedLst (vl-sort list_ (function (lambda (a b) (< (cadr (cadr a)) (cadr (cadr b)))))))
    )
    (defun CO:sort_by_val_ (val_ list_ )  ;เรียงชุดข้อมูลตามแนวแกน
      (if (< val_ (length (car list_)))
        (progn
          (setq sortedLst (vl-sort list_ (function (lambda (a b) (< (nth val_ a) (nth val_ b))))))
        )
        (setq error_ "The number of val is less than list")
      )
    )
    (defun TA:standard_list_croodinate_sorting (ss_post_filter_set_ sequence ) ;เรียง object ตามแนวแกน ใน selection set
      ; ;selection_set
        ;   (if  ;pre_select_ssget_or_post_select_ssget
        ;     (= 
        ;       (setq ss_pre_filter_set_xx (ssget "I" 
        ;                                         (list 
        ;                                           (cons 0 "INSERT") ;type of object
        ;                                           ; (cons 8 "000 - GRID")   ;kind of layer
        ;                                           ; (cons 2 "000-GRID_LINE_DYN")       ;kind of nameblock
        ;                                           ; (cons 62 1)           ;kind of color call sign with color code index
        ;                                         )
        ;                                   )
        ;       )
        ;       nil
        ;     )
        ;     (progn 
        ;       (setq ss_pre_filter_set_xx (ssget 
        ;                                     (list 
        ;                                       (cons 0 "INSERT") ;type of object
        ;                                       ; (cons 8 "000 - GRID")   ;kind of layer
        ;                                       ; (cons 2 "000-GRIDLINE_DYN")       ;kind of nameblock
        ;                                       ; (cons 62 1)           ;kind of color call sign with color code index
        ;                                     )
        ;                                   )
        ;       )
        ;     )
        ;     (sslength ss_pre_filter_set_xx)
        ;   )
      ; ;
      ; ;user_input
        ;   (setq effectivename_val (LM:effectivename (vlax-ename->vla-object (car (entsel )))))
      ; ;
      ; ;filter_via_sub_func
        ;   (setq ss_post_filter_set_ (TA:Filter_ss_set_ ss_pre_filter_set_xx  effectivename_val))
      ; ;
      ;preloop_and_while get_ename_and_add_ins_pt
        (setq sum_data_ ())
        (setq ss_post_filter_set_i 0)
        (while  (< ss_post_filter_set_i (sslength ss_post_filter_set_))
          ;get_data
            (setq ss_post_filter_set_ename (ssname ss_post_filter_set_ ss_post_filter_set_i))
            (setq ss_post_filter_set_obj (vlax-ename->vla-object ss_post_filter_set_ename))
          ;
          ;sum_data_via_data
            (setq sum_data (TA:ename+vla-get-insertionpoint ss_post_filter_set_obj))
            (setq sum_data_ (cons sum_data sum_data_))
          ;
          (setq ss_post_filter_set_i (+ ss_post_filter_set_i 1))
        )
      ;
      ;sub_user_input_
        (cond
          ((= sequence "X") ;correct case
            (progn
              (princ "XXX")
              (setq sort_x (CO:sort_by_X sum_data_))
            )
          )
          ((= sequence "Y") ;correct case
            (progn
              (princ "YYY")
              (setq sort_y (CO:sort_by_Y sum_data_))
            )
          )
          ((and ;incorrect case
              (/= sequence "X")
              (/= sequence "Y")
            )
            (progn
              (princ "error_sorting_ename please specify argument X or Y")
              ; (setq sort_y (sort_by_y sum_data_))
            )
          )
        )
      ;
    )
    
    (defun TA:corrd_sorting_group (all_vlains_ Toerrance_num_value)
      ;Note By Code_Developer
      ;principle of codework is designed for finding coordinate in list and create main row 
      ;The main row will be used as fundamental for sorting each column in coordinate list 
      ;Fully command must have sub-functions with names starting with TA: or LM:
      ;
      ;argument list
      ;all_vlains_        =  all coordinate in list 
      ;                       (standard form for all_vlains argument must be 
      ;                        (
      ;                         (x y z)entity_name
      ;                         (x y z)entity_name
      ;                         (x y z)entity_name
      ;                        )
      ;TA:Toerrance_num_  = is argument from Sub FUNC name "TA:Toerrance_num_"
      ;                     that specify and decide coordinate by calculate spacing 
      ;                     coodinate to coodinate is same column or not in row/col
      ;
      ;main idea of codework
      ;first step is always keep lowest insertion coordinate point in variable name "test_vlains_ename_1st"
      ;second step by setting "test_vlains_ename_1st" as main corrdinate that let other coordinates pass
      ;into the loop for checking whether they are in the same row/column,via using SUB_FUNC name TA:Toerrance_num_
      ;
      ;
      ;creating main rows process
        ;preloop_and_while creating main row in list 
          (setq test_vlains_ename_1st (nth 0 all_vlains_))
          (setq all_vlains_i 0)
          (setq main_row ())
          (setq main_row (cons test_vlains_ename_1st main_row))
          (while (< all_vlains_i (length all_vlains_))
            (setq all_vlains_ename_subrow_ (nth  all_vlains_i all_vlains_))
            (if 
              (and 
                (/= test_vlains_ename_1st all_vlains_ename_subrow_)
                (TA:Toerrance_num_ 
                  (car (car test_vlains_ename_1st))
                  (car (car all_vlains_ename_subrow_))
                  Toerrance_num_value
                )
              )
              (progn 
                (setq main_row (cons all_vlains_ename_subrow_ main_row))
                (length main_row)
              )
            )
            (setq all_vlains_i (+ all_vlains_i 1))
          )
        ;
        ;TA:stanndard_lambda_sorting_Y-axis
          (setq main_row_sorted_Y_ (vl-sort main_row ;bigest open indent list
                                                    (function 
                                                      (lambda (a b) 
                                                        (> (nth 1 (car a)) (nth 1 (car b)))
                                                      )
                                                    )
                                ) ;bigest close indent list
          )
        ;
      ;
      ;creating sub rows process
        ;preloop_and_while main row loop first loop
          (setq main+sub_row_ ())
          (setq main_row_sorted_Y_i 0)
          (while (< main_row_sorted_Y_i (length main_row_sorted_Y_))
            (setq main_row_sorted_Y_main_set_ (nth  main_row_sorted_Y_i main_row_sorted_Y_))
              ;preloop_and_while main row loop second loop
                (setq all_vlains_i 0)
                (setq sub_row_ ())
                (while (< all_vlains_i (length all_vlains_))
                  (setq all_vlains_subrow_ (nth  all_vlains_i all_vlains_))
                    (if 
                      (and 
                        (/= test_vlains_ename_1st all_vlains_ename_subrow_)
                        (TA:Toerrance_num_ 
                          (cadr (car all_vlains_subrow_))
                          (cadr (car main_row_sorted_Y_main_set_))
                          10 ;do not use argument from TA:corrd_sorting_group
                        )
                      )
                      (progn 
                        (setq sub_row_ (cons all_vlains_subrow_ sub_row_ ))
                        (length sub_row_)
                        ;TA:stanndard_lambda_sorting
                        (setq sub_row_ (vl-sort sub_row_  ;bigest open indent list
                                                                  (function 
                                                                    (lambda (a b) 
                                                                      (< (nth 0 (car a)) (nth 0 (car b)))
                                                                    )
                                                                  )
                                              ) ;bigest close indent list
                        )
                        
                        ;
                      )
                    )
                  (setq all_vlains_i (+ all_vlains_i 1))
                )
              ;
            (setq main+sub_row_ (cons sub_row_ main+sub_row_))
            ; (format-data main+sub_row_)
            (length main+sub_row_)
            (TA:textscr_process_V2 "sorting corrdinate" main_row_sorted_Y_i main_row_sorted_Y_ )
            (setq main_row_sorted_Y_i (+ main_row_sorted_Y_i 1))
          )
        ;
        ;TA:stanndard_lambda_sorting
          ;88 211 342 405 463 คือกลุ่มตัวเลขที่ต้องการจะใช้เรียงในกลุ่ม ;main
          ;จากที่กล่าวมา ถ้าต้องเรียงกลุ่ม ;main จะทำการดึงตัวแปรกลุ่ม ;main 
          ;เพื่อตั้งต้นก่อน จะได้ผลลัพธ์แบบนี้
          ; (setq main 
          ;   (list ;main
          ;     (list(list 138.044 88.6521 0.0) "<Entity name: 23abbecab20>") 
          ;     (list(list 288.589 90.6521 0.0) "<Entity name: 23abbecabb0>")
          ;     (list(list 392.914 92.6521 0.0) "<Entity name: 23abbecabe0>")
          ;   )
          ; )
          ;ซึ่ง main ในที่นี้ คือตัวแทน a b ใน lambda โดยเป็น main คือ list ย่อยของ main+sub_row_
          ;วิธีตรวจสอบำตอบง่ายๆ คือ ให้ ตั้งการดึงข้อมูลย่อยจาก main
          ;สมมุติว่าใช้ (cadr (nth 0 (nth 0 main))) แล้วได้ตัวเลขในกลุ่มดังกล่าว [88 211 342 405 463]
          ;แสดงว่าถูกต้อง
          ; (setq main+sub_row_ 
          ;   (list
          ;     (list ;main
          ;       (list(list 138.044 88.6521 0.0) "<Entity name: 23abbecab20>") 
          ;       (list(list 288.589 90.6521 0.0) "<Entity name: 23abbecabb0>")
          ;       (list(list 392.914 92.6521 0.0) "<Entity name: 23abbecabe0>")
          ;     ) 
          ;     (list ;main
          ;       (list(list 147.328 211.264 0.0) "<Entity name: 23abbecab50>") 
          ;       (list(list 288.589 210.776 0.0) "<Entity name: 23abbecabc0>")
          ;       (list(list 392.914 212.776 0.0) "<Entity name: 23abbecabf0>")
          ;     )
          ;     (list ;main
          ;       (list(list 100.205 342.1 0.0) "<Entity name: 23abbecab80>") 
          ;       (list(list 288.589 344.1 0.0) "<Entity name: 23abbecabd0>")
          ;       (list(list 392.914 346.1 0.0) "<Entity name: 23abbecac00>")
          ;     )
          ;     (list ;main
          ;       (list(list 119.914 405.524 0.0) "<Entity name: 23abbecaed0>") 
          ;       (list(list 251.971 407.524 0.0) "<Entity name: 23abbecaee0>")
          ;       (list(list 356.296 409.524 0.0) "<Entity name: 23abbecaef0>")
          ;     )
          ;     (list ;main
          ;       (list(list 156.532 463.701 0.0) "<Entity name: 23abbecaf60>") 
          ;       (list(list 288.589 465.701 0.0) "<Entity name: 23abbecaf70>")
          ;       (list(list 392.914 467.701 0.0) "<Entity name: 23abbec7800>")
          ;     )
          ;   )
          ; )
          (setq main+sub_row_sorted_ (vl-sort main+sub_row_  ;bigest open indent list
                                              (function 
                                                (lambda (a b) 
                                                  (>
                                                    (cadr (nth 0 (nth 0 a)))
                                                    (cadr (nth 0 (nth 0 b)))
                                                    
                                                  )
                                                )
                                              )
                                    ) ;bigest close indent list
          )
          ; (format-data main+sub_row_)
          (setq main+sub_row_sorted_ main+sub_row_sorted_)
        ;
        
      ;
      ;
    )
    (defun TA:custom-sort (user_custom_sort_ target_custom_sort_ )
      ;Note By Code_Developer
      ;This command is designed to work exclusively with a list array 
      ;principle of codework is designed for sorting by user custom, Then user can create custom in array list-form
      ;
      ;example argument
        ; (setq user_custom_sort_ '("Cherry" "Banana" "Apple" "Mango"))
        ; (setq target_custom_sort_  '("Cherry" "Banana" "Cherry" "Banana" "Cherry" "Banana" "Apple" "Mango" "Apple" "Mango" "Apple" "Mango"))
      ;
      ;
      ;preloop_and_while
        (setq new_sort_ ())
        (setq user_custom_sort_i 0)
        (while (< user_custom_sort_i (length user_custom_sort_))
          (setq user_custom_sort_tag_ (nth  user_custom_sort_i user_custom_sort_))
          
          ;preloop_and_while
            (setq target_custom_sort_i 0)
            (while (< target_custom_sort_i (length target_custom_sort_))
              (setq target_custom_sort_val_ (nth  target_custom_sort_i target_custom_sort_))
              
              (if (= target_custom_sort_val_ user_custom_sort_tag_ )
                (progn
                  (setq new_sort_ (cons target_custom_sort_val_ new_sort_))
                )
              )
              (setq target_custom_sort_i (+ target_custom_sort_i 1))
            )
          ;
      
          (setq user_custom_sort_i (+ user_custom_sort_i 1))
        )
      ;
      (setq new_sort_ new_sort_)
    )
    (defun TA:TBsort_ (TBsort_ tol
                       / data xSortIndex xSorted currentColumn columnX
                         item itemX columnSortIndex sortedResult)

      ;; ระยะ X ที่ถือว่าอยู่ในคอลัมน์เดียวกัน
      (if (or (null tol) (<= tol 0.0))
        (setq tol 5.0)
      )

      ;; ถ้าใช้ UCS ให้แปลงจุดจาก WCS เป็น UCS ก่อน
      (if (= (getvar "WORLDUCS") 0)
        (setq data
          (mapcar
            '(lambda (item)
              (list
                (car item)
                (trans (cadr item) 0 1)
              )
            )
            TBsort_
          )
        )
        (setq data TBsort_)
      )

      ;; ขั้นแรกเรียงทุกวัตถุตาม X จากซ้ายไปขวา
      ;; ใช้ vl-sort-i เพื่อไม่ให้ข้อมูลตำแหน่งซ้ำถูกตัดออก
      (setq xSortIndex
        (vl-sort-i
          data
          '(lambda (a b)
            (< (car (cadr a)) (car (cadr b)))
          )
        )
      )
      (setq xSorted
        (mapcar
          '(lambda (index)
            (nth index data)
          )
          xSortIndex
        )
      )

      ;; แบ่งกลุ่มตามคอลัมน์จากซ้ายไปขวา
      (setq currentColumn nil
            columnX       nil
            sortedResult  nil
      )

      (foreach item xSorted
        (setq itemX (car (cadr item)))

        (if (or (null currentColumn)
                (<= (abs (- itemX columnX)) tol)
            )
          (progn
            ;; ค่า X ของสมาชิกแรกเป็นแนวอ้างอิงของคอลัมน์
            (if (null currentColumn)
              (setq columnX itemX)
            )
            (setq currentColumn (cons item currentColumn))
          )
          (progn
            ;; จบคอลัมน์เดิม: เรียงค่า Y จากมากไปน้อย
            (setq columnSortIndex
              (vl-sort-i
                currentColumn
                '(lambda (a b)
                  (> (cadr (cadr a)) (cadr (cadr b)))
                )
              )
            )
            (setq sortedResult
              (append
                sortedResult
                (mapcar
                  '(lambda (index)
                    (nth index currentColumn)
                  )
                  columnSortIndex
                )
              )
            )

            ;; เริ่มคอลัมน์ใหม่ทางขวา
            (setq currentColumn (list item)
                  columnX       itemX
            )
          )
        )
      )

      ;; เรียงและเพิ่มคอลัมน์สุดท้าย
      (if currentColumn
        (progn
          (setq columnSortIndex
            (vl-sort-i
              currentColumn
              '(lambda (a b)
                (> (cadr (cadr a)) (cadr (cadr b)))
              )
            )
          )
          (setq sortedResult
            (append
              sortedResult
              (mapcar
                '(lambda (index)
                  (nth index currentColumn)
                )
                columnSortIndex
              )
            )
          )
        )
      )

      sortedResult
    )
    (defun TA:LRsort_ (LRsort_ tol)
      (defun TA:convert-list-ucs (lst /)
        (mapcar
          '(lambda (a)
            (list
              (car a)
              (trans (cadr a) 0 1)
            )
          )
          lst
        )
      )
      (setq tol 5.0) ; ระยะที่ถือว่าเป็นแถวเดียวกัน (mm)
      (if (= (getvar "worlducs" ) 0 )
        (progn
          (setq LRsort_ (TA:convert-list-ucs LRsort_))
          (setq sorted_
            (vl-sort LRsort_
              '(lambda (a b)

                (setq ya (cadr (cadr a)))
                (setq yb (cadr (cadr b)))

                (setq xa (car (cadr a)))
                (setq xb (car (cadr b)))

                (if (> (abs (- ya yb)) tol)
                  (> ya yb) ; แถวบน -> ล่าง
                  (< xa xb) ; ซ้าย -> ขวา
                )

              )
            )

          )
        )
        (setq sorted_
          (vl-sort LRsort_
            '(lambda (a b)

              (setq ya (cadr (cadr a)))
              (setq yb (cadr (cadr b)))

              (setq xa (car (cadr a)))
              (setq xb (car (cadr b)))

              (if (> (abs (- ya yb)) tol)
                (> ya yb) ; แถวบน -> ล่าง
                (< xa xb) ; ซ้าย -> ขวา
              )

            )
          )
        )
        
      )
    )
    (defun TA:Sort_mtext_top_to_bottom_
      (
        selection_set_
        /
        index_
        mtext_ename_
        mtext_obj_
        insertion_point_
        data_list_
        sorted_list_
      )

      (vl-load-com)

      (setq index_ 0)
      (setq data_list_ '())

      ;get MText data
      (while (< index_ (sslength selection_set_))
        (setq mtext_ename_
          (ssname selection_set_ index_)
        )

        (setq mtext_obj_
          (vlax-ename->vla-object mtext_ename_)
        )

        ;InsertionPoint from VLA is WCS
        (setq insertion_point_
          (vlax-safearray->list
            (vlax-variant-value
              (vla-get-InsertionPoint mtext_obj_)
            )
          )
        )

        ;WCS to Current UCS
        (setq insertion_point_
          (trans insertion_point_ 0 1)
        )

        ;store ENAME, point and original index
        (setq data_list_
          (cons
            (list
              mtext_ename_
              insertion_point_
              index_
            )
            data_list_
          )
        )

        (setq index_ (1+ index_))
      )

      ;sort:
      ;1. Y จากมากไปน้อย = บนลงล่าง
      ;2. ถ้า Y เท่ากัน ให้ X จากน้อยไปมาก = ซ้ายไปขวา
      (setq data_list_
        (vl-sort
          data_list_
          (function
            (lambda (data_a_ data_b_ / point_a_ point_b_)
              (setq point_a_ (cadr data_a_))
              (setq point_b_ (cadr data_b_))

              (cond
                ;different Y
                (
                  (not
                    (equal
                      (cadr point_a_)
                      (cadr point_b_)
                      1e-8
                    )
                  )
                  (> (cadr point_a_)
                    (cadr point_b_)
                  )
                )

                ;same Y, different X
                (
                  (not
                    (equal
                      (car point_a_)
                      (car point_b_)
                      1e-8
                    )
                  )
                  (< (car point_a_)
                    (car point_b_)
                  )
                )

                ;same position, use original index
                (T
                  (< (caddr data_a_)
                    (caddr data_b_)
                  )
                )
              )
            )
          )
        )
      )

      ;return ENAME list
      (setq sorted_list_
        (mapcar
          'car
          data_list_
        )
      )

      sorted_list_
    )
    (defun TA:Sort_nested_list_
      (input_list_ sort_position_
      /
      index_
      decorated_list_
      sorted_list_
      )

      (setq index_ 0)

      ;; เพิ่มเลขลำดับเดิม เพื่อป้องกันรายการซ้ำหาย
      (setq decorated_list_
        (mapcar
          '(lambda (item_)
            (setq index_ (1+ index_))
            (cons index_ item_)
          )
          input_list_
        )
      )

      (setq sorted_list_
        (vl-sort
          decorated_list_
          '(lambda
            (item_a_ item_b_
              /
              value_a_
              value_b_
              number_a_
              number_b_
              string_a_
              string_b_
            )

            ;; sort_position_ ใช้ 1, 2 หรือ 3
            (setq value_a_
              (nth
                (1- sort_position_)
                (car (cdr item_a_))
              )
            )

            (setq value_b_
              (nth
                (1- sort_position_)
                (car (cdr item_b_))
              )
            )

            ;; แปลง Numeric String เป็นตัวเลข
            (setq number_a_
              (cond
                ((numberp value_a_) value_a_)
                ((= (type value_a_) 'STR)
                  (distof value_a_ 2)
                )
              )
            )

            (setq number_b_
              (cond
                ((numberp value_b_) value_b_)
                ((= (type value_b_) 'STR)
                  (distof value_b_ 2)
                )
              )
            )

            (cond
              ;; เรียงแบบตัวเลข
              ((and number_a_ number_b_)
                (if (= number_a_ number_b_)
                  (< (car item_a_) (car item_b_))
                  (< number_a_ number_b_)
                )
              )

              ;; เรียงแบบข้อความ
              (T
                (setq string_a_
                  (strcase (vl-princ-to-string value_a_))
                )

                (setq string_b_
                  (strcase (vl-princ-to-string value_b_))
                )

                (if (= string_a_ string_b_)
                  ;; ค่าเหมือนกัน ให้รักษาลำดับเดิม
                  (< (car item_a_) (car item_b_))

                  ;; เรียงข้อความ A-Z
                  (=
                    string_a_
                    (car
                      (acad_strlsort
                        (list string_a_ string_b_)
                      )
                    )
                  )
                )
              )
            )
          )
        )
      )

      ;; ตัดเลขลำดับที่เพิ่มไว้ออก
      (mapcar 'cdr sorted_list_)
    )
  ;
  ;get_Intersect_func
    (defun LM:intersections (ob1 ob2 mod / lst rtn) 
      (if 
        (and (vlax-method-applicable-p ob1 'intersectwith) 
            (vlax-method-applicable-p ob2 'intersectwith)
            (setq lst (vlax-invoke ob1 'intersectwith ob2 mod))
        )
        (repeat (/ (length lst) 3) 
          (setq rtn (cons (list (car lst) (cadr lst) (caddr lst)) rtn)
                lst (cdddr lst)
          )
        )
      )
      (remove_member_list_ 2 (reverse rtn))
      
    )
    (defun LM:intersections+0 (ob1 ob2 mod / lst rtn) 
      (if 
        (and (vlax-method-applicable-p ob1 'intersectwith) 
            (vlax-method-applicable-p ob2 'intersectwith)
            (setq lst (vlax-invoke ob1 'intersectwith ob2 mod))
        )
        (repeat (/ (length lst) 3) 
          (setq rtn (cons (list (car lst) (cadr lst) (caddr lst)) rtn)
                lst (cdddr lst)
          )
        )
      )
      ; (remove_member_list_ 2 (reverse rtn))
      (reverse rtn)
      
    )
    (defun LM:intersections_crood_position (ob1 ob2 coord_ mod  / lst rtn) 
      (if 
        (and (vlax-method-applicable-p ob1 'intersectwith) 
            (vlax-method-applicable-p ob2 'intersectwith)
            (setq lst (vlax-invoke ob1 'intersectwith ob2 mod))
        )
        (repeat (/ (length lst) 3) 
          (setq rtn (cons (list (car lst) (cadr lst) (caddr lst)) rtn)
                lst (cdddr lst)
          )
        )
      )
      (cond ;soectify corrdinate position
        ((= coord_ "xyz")
        (progn 
          (reverse rtn)
        )
        )
        ((= coord_ "xy")
        (progn 
          (remove_member_list_ 2 (reverse rtn))
        )
        )
        ((or
          (/= coord_ "xy")
          (/= coord_ "xyz")
          (= coord_ nil)
        )
        (progn 
          (princ "\n:::::::::::::::: ERROR ::::::::::::::::::::::")
          (princ "\n:::::Please Specify Coordinate Position::::::\n")
          (princ ":::::::::::::: X Y    = 2 coord :::::::::::::\n")
          (princ ":::::::::::::: X Y Z  = 3 coord :::::::::::::\n")
        )
        )
      )
    )
    (defun LM:intersectionsinset ( sel / id1 id2 ob1 ob2 rtn )
      (repeat (setq id1 (sslength sel))
          (setq ob1 (vlax-ename->vla-object (ssname sel (setq id1 (1- id1)))))
          (repeat (setq id2 id1)
              (setq ob2 (vlax-ename->vla-object (ssname sel (setq id2 (1- id2))))
                    rtn (cons (LM:intersections ob1 ob2 acextendnone) rtn)
              )
          )
      )
      (apply 'append (reverse rtn))
    )
    (defun LM:intersectionsinset+0 ( sel / id1 id2 ob1 ob2 rtn )
      (repeat (setq id1 (sslength sel))
          (setq ob1 (vlax-ename->vla-object (ssname sel (setq id1 (1- id1)))))
          (repeat (setq id2 id1)
              (setq ob2 (vlax-ename->vla-object (ssname sel (setq id2 (1- id2))))
                    rtn (cons (LM:intersections+0 ob1 ob2 acextendnone) rtn)
              )
          )
      )
      (apply 'append (reverse rtn))
    )
    (defun LM:intersectionsinobjlist ( lst / ob1 rtn )
      (while (setq ob1 (car lst))
          (foreach ob2 (setq lst (cdr lst))
              (setq rtn (cons (LM:intersections ob1 ob2 acextendnone) rtn))
          )
      )
      (apply 'append (reverse rtn))
    )
    
  ;
  ;Filter Selection Set by Effectivename Ta Trai  
    ;Note By Code_Developer
    ;
    ;Fully command must have sub-functions with names starting with TA: or LM:
    ;
    ;
    (defun TA:EF_Filter_ss_set_ (ss_pre_filter_set_  effectivename) ;กรอง block object ด้วย LM:effectivename
      (setq ss_post_filter_set_ (ssadd))
      ; (setq effectivename "12a")
      ;preloop_and_while
        (setq ss_pre_filter_set_i 0)
            (while 
              ;get_data
                (setq ss_pre_filter_set_ename (ssname  ss_pre_filter_set_ ss_pre_filter_set_i) )
                (setq ss_pre_filter_set_obj (vlax-ename->vla-object ss_pre_filter_set_ename))
                (setq ss_pre_filter_set_obj_efname_ (LM:effectivename ss_pre_filter_set_obj))
              ;
              ;filter_data
                (if (= ss_pre_filter_set_obj_efname_ effectivename)
                  (progn
                  (ssadd ss_pre_filter_set_ename ss_post_filter_set_)
                  )
                  (princ (strcat "\nfilter_selection_set_and_sorting is processing " (rtos (* ss_pre_filter_set_i (/ 100 (float (sslength ss_pre_filter_set_)))) 2 0) "%\n"))
                )
              ;
              (setq ss_pre_filter_set_i (+ ss_pre_filter_set_i 1))
            )
      ;
      (sslength ss_post_filter_set_)
      (princ ss_post_filter_set_)
      (setq ss_post_filter_set_ ss_post_filter_set_)
    )
    (defun TA:EF_Filter_ss_set_v2_ (ss_pre_filter_set_  effectivename_list) ;กรอง block object ด้วย LM:effectivename 
      (setq ss_post_filter_set_ (ssadd))
      ; (setq effectivename "12a")
      ;preloop_and_while
        (setq ss_pre_filter_set_i 0)
        (while 
          ;get_data
            (setq ss_pre_filter_set_ename (ssname  ss_pre_filter_set_ ss_pre_filter_set_i) )
            (setq ss_pre_filter_set_obj (vlax-ename->vla-object ss_pre_filter_set_ename))
            
          ;
          ;filter_data
            (if (and 
                  (= (vla-get-objectname ss_pre_filter_set_obj) "AcDbBlockReference")
                  (= (TA:FIND_DUPLICATE_LIST (LM:effectivename ss_pre_filter_set_obj) effectivename_list) "Y")
                )
              (progn
              (ssadd ss_pre_filter_set_ename ss_post_filter_set_)
              )
              (princ (strcat "\nfilter_selection_set_and_sorting is processing " (rtos (* ss_pre_filter_set_i (/ 100 (float (sslength ss_pre_filter_set_)))) 2 0) "%\n"))
            )
          ;
          (setq ss_pre_filter_set_i (+ ss_pre_filter_set_i 1))
        )
      ;
      (sslength ss_post_filter_set_)
      (princ ss_post_filter_set_)
      (setq ss_post_filter_set_ ss_post_filter_set_)
    )
    
    (defun TA:Prop_Filter_ss_set_ (Selection_list_ nameprop_ propval_)
      (setq temp_ssget_ (ssadd))
      (setq Selection_list_i 0)
      (while (< Selection_list_i (sslength Selection_list_))
        (setq Selection_list_ename_ (ssname Selection_list_ Selection_list_i))
        (setq Selection_list_obj_ (vlax-ename->vla-object Selection_list_ename_))
          (if
            (= (vlax-get-property Selection_list_obj_ nameprop_) propval_ )
            (progn
              (setq temp_ssget_ (ssadd Selection_list_ename_ temp_ssget_))
            )
            (princ "\n")
          )
        (setq Selection_list_i (+ Selection_list_i 1))
      )
      (sslength temp_ssget_)
      (setq temp_ssget_ temp_ssget_)
    )
    (defun TA:member (str_name_ member_list_)
        (setq member_list_i 0)
        (setq found nil)
        (while (and
                (< member_list_i (length member_list_))
                (/= found T)
              )
          (setq member_list_val (nth member_list_i member_list_))
          (if (= str_name_ member_list_val)
            (progn
              (setq found T)  
            )
              (setq found nil)
          )
          (setq member_list_i (+ member_list_i 1))
        )
        (setq result found)
    )
    (defun TA:member_position (str_name_ pos member_list_)
        (setq member_list_i 0)
        (setq result_found_val ())
        (setq found nil)
        (while (and
                (< member_list_i (length member_list_))
                ; (/= found T)
              )
          (setq member_list_val (nth member_list_i member_list_))
          (if (= str_name_ (nth pos member_list_val))
            (progn
              ; (setq found T)
              (setq result_found_val (cons member_list_val result_found_val))          
            )
              (setq found nil)
          )
          (setq member_list_i (+ member_list_i 1))
        )
        (setq result result_found_val)
    )
    (defun remove_member_list_ (num_ point_list_)
      (setq new_list_ ())
      ; (setq num_ 2)
      (setq point_list_i 0)
      (while (< point_list_i (length point_list_))
        
        (setq point_list_set_ (nth point_list_i point_list_))
        (setq point_list_set_remove (vl-remove (nth num_ point_list_set_) point_list_set_))
        (setq new_list_ (cons point_list_set_remove new_list_))
        (setq point_list_i (+ point_list_i 1))
        
      )
      (setq result_ (reverse new_list_))
    )
    (defun remove_single_list_ (num_ point_list_)
      (setq new_list_ ())
        (setq point_list_set_ point_list_)
        (setq point_list_set_remove (vl-remove (nth num_ point_list_set_) point_list_set_))

      (setq result_ point_list_set_remove)
    )
    (defun TA:remove_val_list_ (val_list_ target_list_)
      ;example
        ; (setq target_list_ (list 1 2 3 4 5 6 7 8 9 nil))
        ; (setq target_list_ (list "ปรับปรุงอาตาร_DERMA_HEALTH_คลอ" "ง9_DB_STUDIO" ""))
        ; (setq val_list_ nil) 
        ; (TA:remove_val_list_ 8 target_list_)
      ;
      ;preloop_and_while
        (setq target_list_i 0)
        (while (< target_list_i (length target_list_))
          (setq target_list_ename_ (nth  target_list_i target_list_))
          (if (or (= target_list_ename_ nil) (= target_list_ename_ "") )
            (progn
              (setq target_list_ (vl-remove (nth target_list_i target_list_) target_list_))
            )
          )
          (setq target_list_i (+ target_list_i 1))
        )
        (setq target_list_ target_list_)
      ; 
    )
    (defun TA:FIND_DUPLICATE_LIST (target_val_ target_list_)
      ;example_code
        ; (setq target_val_ 69)
        ; (setq target_list_ (list 2 5 69 4 26 9 5 23 6 9 52  6))
      ;
      ;preloop_and_while
        (setq target_list_i 0)
        (setq check_list_val "N")
        (while (and (< target_list_i (length target_list_)) (= check_list_val "N"))
          (setq target_list_ename_ (nth  target_list_i target_list_))
            (if (= target_val_ target_list_ename_ )
              (progn
                (setq check_list_val "Y")
              )
              (setq check_list_val "N")
            )
          (setq target_list_i (+ target_list_i 1))
        )
      ;
      ;summary_checking_list_
        (if (= target_list_i (length target_list_))
          (progn
            ; (princ (strcat "do not found duplicate targetlist \n" ))
          )
          ; (princ (strcat "target_val_ has been duplicate in " (rtos target_list_i 2 0) "\n" ))
        )
        (setq check_list_val check_list_val)
      ;
    )
    (defun TA:Count_item_in_list_ (c_list_ )
      ;
        (setq result_ ())
        (while (/= c_list_ nil)
          (length c_list_)
          (setq c_list_val_ (car c_list_))
          (setq count_i (- 
                    (length c_list_)
                    (length (setq c_list_ (vl-remove c_list_val_ c_list_)))
                  )
          )
          (setq result_ (cons (cons c_list_val_ count_i ) result_))
          
        )
      ;
    )
    (defun LM:CountItems (l show_count_ / c r x) 
      (while l 
        (setq x (car l)
              c (length l)
              l (vl-remove x (cdr l))
              r (cons 
                  (if show_count_ 
                    (cons x (- c (length l)))
                    x
                  )
                  r
                )
        )
      )
      (reverse r)
    )
    (defun TA:GroupSum_ (lst / result item head_ val found) 
      (foreach item lst 
        (setq head_ (car item))
        (setq val (cdr item))

        (if (/= head_ "") 
          (if (setq found (assoc head_ result)) 
            (setq result (subst 
                          (cons head_ (+ val (cdr found)))
                          found
                          result
                        )
            )
            (setq result (cons (cons head_ val) result))
          )
        )
      )
      (reverse result)
    )
    (defun TA:find-all-indexes (val lst / idx result)
      (setq idx 0)
      (setq result '())
      (while lst
        (if (equal (car lst) val)
          (setq result (cons idx result))
        )
        (setq idx (1+ idx))
        (setq lst (cdr lst))
      )
      (reverse result)
    )
    (defun TA:wcmatch_list (filter_string_list_ list_data_ strcase_val)
      ;Note By Code_Developer
      ;This command is designed to work exclusively with a list name & array.
      ;The pripicle of the codework will read list name & array then filter target value that filter_string parameter indicate.
      ;Fully command must have sub-functions with names starting with TA: or LM:
      ;
      ;Example how argument work
        ; (setq filter_string_list_ (list 
        ;                             "*text_that _you_need*"
        ;                             "50"
        ;                             "45"   
        ;                             "*re*"
        ;                             "*ai*"
        ;                           )
        ; )
        ; (setq list_data_ (list "5s0" "45a" ))
        ; (setq strcase_val nil)
        ; (TA:wcmatch_list filter_string_list_ list_data_ T)
      ;
      ;1st condition
      (cond
        ((= strcase_val nil)
          (progn
            (setq filter_string_list_ (mapcar 
                                        '(lambda (x) 
                                            (if 
                                              (and (= (type x) 'str) 
                                                  (/= (atof x) 'real)
                                              ) 
                                              (progn 
                                                (strcase x T)
                                              ) 
                                              ""
                                            ;  (if (testexpr)
                                            ;   (progn
                                            ;     (thenexpr)
                                            ;   )
                                            ;  )
                                            )
                                          )
                                        filter_string_list_
                                      )
            )
            (setq list_data_ (mapcar 
                                        '(lambda (x) 
                                            (if 
                                              (and 
                                                (= (type x) 'str)
                                                (/= (atof x) 'real)
                                              ) 
                                              (progn 
                                                
                                                (strcase x T)
                                              ) 
                                              ""
                                            ;  (if (testexpr)
                                            ;   (progn
                                            ;     (thenexpr)
                                            ;   )
                                            ;  )
                                            )
                                          )
                                        list_data_
                                      )
            )
          )
        )
        ; ((= strcase_val T)
        ;   (progn
        ;     (setq filter_string_list_ (mapcar 
        ;                                 '(lambda (x) 
        ;                                    (if 
        ;                                      (and (= (type x) 'str) 
        ;                                           (/= (atof x) 'real)
        ;                                      ) 
        ;                                      (progn 
        ;                                        (strcase x T)
        ;                                      ) 
        ;                                      ""
        ;                                     ;  (if (testexpr)
        ;                                     ;   (progn
        ;                                     ;     (thenexpr)
        ;                                     ;   )
        ;                                     ;  )
        ;                                    )
        ;                                  )
        ;                                 filter_string_list_
        ;                               )
        ;     )
        ;     (setq list_data_ (mapcar 
        ;                                 '(lambda (x) 
        ;                                    (if 
        ;                                      (and  
        ;                                           (/= (atof x) 'real)
        ;                                      ) 
        ;                                      (progn 
        ;                                        (strcase x T)
        ;                                      ) 
        ;                                      ""
        ;                                     ;  (if (testexpr)
        ;                                     ;   (progn
        ;                                     ;     (thenexpr)
        ;                                     ;   )
        ;                                     ;  )
        ;                                    )
        ;                                  )
        ;                                 list_data_
        ;                               )
        ;     )
        ;   )
        ; )
      )
        (setq filter_result_ (vl-remove-if-not 
                              '(lambda (x) 
                                  (apply 'or 
                                          (mapcar 
                                            '(lambda (p) (wcmatch x p))
                                            filter_string_list_
                                          )
                                  )
                                )
                              list_data_
                            )
        )
        (setq filter_result_ (reverse filter_result_))
      ;
    )
    (defun TA:wcmatch_list_rev02
      (filter_string_list_ list_data_ strcase_val / filter_result_)

      (setq filter_result_
        (vl-remove-if-not
          '(lambda (data_)
            (and
              (= (type data_) 'STR)
              (vl-some
                '(lambda (pattern_)
                    (and
                      (= (type pattern_) 'STR)
                      ((lambda (data_compare_ pattern_compare_)
                        (if (vl-string-search "*" pattern_)
                          (wcmatch data_compare_ pattern_compare_)
                          (= data_compare_ pattern_compare_)
                        )
                      )
                      (if strcase_val data_ (strcase data_))
                      (if strcase_val pattern_ (strcase pattern_))
                      )
                    )
                  )
                filter_string_list_
              )
            )
          )
          list_data_
        )
      )

      ;คงพฤติกรรมเรียงกลับตามฟังก์ชันเดิม
      (reverse filter_result_)
    )
    (defun TA:list-to-ss (ename-lst ss-name)  
      (setq ss-name (ssadd))
      (if (= (type ename-lst) 'LIST)
        (progn
          (foreach x ename-lst 
            (if (= (type x ) 'ENAME)
              (progn
                (setq ss-name (ssadd x ss-name ))
              )
            )
          )
        )
      )
    )
    (defun TA:ssobj_to_ins_ (inskeeper_ / inskeeper_i inskeeper_list_)
      ;preloop_and_while
        (setq inskeeper_i 0)
        (setq inskeeper_list_ ())
        (while (and 
                (= (type inskeeper_) 'PICKSET)  
                (< inskeeper_i (sslength inskeeper_))
              )
          (setq inskeeper_ename_ (ssname inskeeper_ inskeeper_i))
          (setq inskeeper_obj_ (vlax-ename->vla-object  inskeeper_ename_))
          (setq inskeeper_list_  (cons (list inskeeper_ename_ inskeeper_obj_) inskeeper_list_ ))
          (setq inskeeper_i (+ inskeeper_i 1))
        )
      ;
      (setq result_list inskeeper_list_)
    )
  
  ;
  ;Get_Data Document Ta Trai
    (defun LM:getdocumentobject ( dwg / app dbx dwl err vrs )
        (cond
            (   (not (setq dwg (findfile dwg))) nil)
            (   (cdr
                    (assoc (strcase dwg)
                        (vlax-for doc (vla-get-documents (setq app (vlax-get-acad-object)))
                            (setq dwl (cons (cons (strcase (vla-get-fullname doc)) doc) dwl))
                        )
                    )
                )
            )
            (   (progn
                    (setq dbx
                        (vl-catch-all-apply 'vla-getinterfaceobject
                            (list app
                                (if (< (setq vrs (atoi (getvar 'acadver))) 16)
                                    "objectdbx.axdbdocument"
                                    (strcat "objectdbx.axdbdocument." (itoa vrs))
                                )
                            )
                        )
                    )
                    (or (null dbx) (vl-catch-all-error-p dbx))
                )
                (prompt "\nUnable to interface with ObjectDBX.")
            )
            (   (vl-catch-all-error-p (setq err (vl-catch-all-apply 'vla-open (list dbx dwg))))
                (prompt (strcat "\n" (vl-catch-all-error-message err)))
            )
            (   dbx   )
        )
    )
    (defun getdrawinglayouts ( dwg / doc idx rtn )
      ;original_method_
        (if (setq doc (LM:getdocumentobject dwg))
            (progn
                (vlax-for lyt (vla-get-layouts doc)
                    (setq rtn (cons (vla-get-name lyt) rtn)
                          idx (cons (vla-get-taborder lyt) idx)
                    )
                )
                (vlax-release-object doc)
                (mapcar '(lambda ( n ) (nth n rtn)) (vl-sort-i idx '<))
            )
        )
      ;
    )
    (defun c:select_layout_number_LayNum_ ()
      (setq input_layout_number (cond ( (getint (strcat "\nspecify get color \n<" (rtos (setq input_layout_number (cond (input_layout_number) (1.0) ) ) ) "> : " ) ) ) (input_layout_number) ) )
      (setq layout_list_ (getdrawinglayouts (getvar "dwgname")))
      (setvar "ctab" (nth (fix input_layout_number) layout_list_ ) )
    )
    (defun c:go-to-model_2model ()
      (setvar "ctab" "model")
    )
    (defun c:select_layout_number_2LayoutClose_2LAC ()
      (setq layout_list_ (getdrawinglayouts (getvar "dwgname")))
      (setvar "ctab" (nth 1 layout_list_ ) )
      (command "zoom" "extent" )
      (command "qsave")
      (command "close")
    )    
    (defun c:select_layout_number_2Layout_2LAA ()
      (setq layout_list_ (getdrawinglayouts (getvar "dwgname")))
      (setvar "ctab" (nth 1 layout_list_ ) )
      (command "zoom" "extent" )
      (command "qsave")
    )   
    (defun c:gethandle ()
      (setq get_ename_ (car (entsel "specify Object")))
      (setq get_obj_ (vlax-ename->vla-object get_ename_))
      (princ (vla-get-handle get_obj_))
    )
    (defun TA:get-current-space (doc)
      (if
        (and
          (= (getvar "TILEMODE") 0)
          (= (getvar "CVPORT") 1)
        )
        (vla-get-PaperSpace doc)
        (vla-get-ModelSpace doc)
      )
    )

  ;
  ;Get_Data Function Ta Trai
    (defun TA:get_name_block_in_drawing (mode)
      ;user_input_
        (setq mode "mode")
      ;
      ;get_obj_file_
        (setq multi_blocks_obj (vla-get-blocks (vla-get-ActiveDocument (vlax-get-acad-object))))
        (setq block_list_ ())
      ;
      ;method_for_get_name_block_in_drawing
        ;method_1_get_name_
          (vlax-for block_ multi_blocks_obj 
            (setq block_list_ (append block_list_ (list (vla-get-name block_))))
          )
        ;
        ; ;method_2_get_name_
        ;   (setq block_i 0)
        ;   (while (< block_i (vla-get-count multi_blocks_obj))
        ;     (setq block_ (vla-item multi_blocks_obj block_i))
        ;     (setq block_list_ (append block_list_ (list (vla-get-name block_))))
        ;     (setq block_i (1+ block_i))
        ;   )
        ; ;
      ;
      ;sorting_name_block
        (setq sorted_block_list_ (acad_strlsort block_list_))
      ;
      ;preloop_and_while filtter_
        (setq sorted_block_list_i 0)
        (setq filter_sorted_block_ ())

        (while (< sorted_block_list_i (length sorted_block_list_))
          (setq filter_sorted_block_effectivename_ (nth sorted_block_list_i sorted_block_list_))
          
          (if (/= (substr filter_sorted_block_effectivename_ 1 1) "*") ; ตรวจสอบว่าชื่อเริ่มต้นด้วย *
            (progn
              (setq filter_sorted_block_ (cons filter_sorted_block_effectivename_ filter_sorted_block_))
            )
          )
          (setq sorted_block_list_i (+ sorted_block_list_i 1))
        )
      ;

      
      (setq filter_sorted_block_total (length filter_sorted_block_))
      (princ "\n                  |=====================|")
      (princ "\n                  | TOTAL BLOCK IN FILE |")
      (princ (strcat "\n                  |     = " (itoa filter_sorted_block_total) " block     |"))
      (princ "\n                  |          set        |")
      (princ "\n                  |---------------------|\n")
      (setq filter_sorted_block_ filter_sorted_block_)

    )
    (defun TA:get_name_layer_in_drawing ()
      (setq layers_list_ ())
      (setq layers_obj (vla-get-layers (vla-get-ActiveDocument (vlax-get-acad-object))))
      ;method_1_get_layers_name
        (vlax-for lay layers_obj
          (setq layers_list (append layers_list (list (vla-get-Name lay))))
        )
      ;
      ;method_2_get_layers_name
        (setq layers_i 0)
        (while (< layers_i (vla-get-count layers_obj))
          (setq layers_ (vla-item layers_obj layers_i))
          (setq layers_list_ (append layers_list_ (list (vla-get-name layers_))))
          (setq layers_i (1+ layers_i))
        )
      ;
      ;summary_layer_data
        (setq layers_list_total (length layers_list_))
        (princ "\n                  |=====================|")
        (princ "\n                  | TOTAL LAYERS IN FILE |")
        (princ (strcat "\n                  |     = " (itoa layers_list_total) " layer     |"))
        (princ "\n                  |          set        |")
        (princ "\n                  |---------------------|")
        (setq layers_list_ layers_list_)
      ;
    )
    (defun TA:ename+vla-get-insertionpoint (obj) ;ประกอบ entity_name กับ insertion_poiint ให้เป็น list (BLOCK ONLY)
      (if (= (vla-get-objectname obj) "AcDbBlockReference")
        (progn
          ;get_data
            (setq ename_ (vlax-vla-object->ename obj)) 
            
            (setq _inspt (vlax-safearray->list (vlax-variant-value (vla-get-insertionpoint obj))))
          ;
          ;sum_data_to_list
            (setq sum_list (list 
                            ename_
                            _inspt
                            ;add more
                          )
            )
          ;
        )
        (setq error "OBJECT IS NOT BLOCK")
      )
    )
    (defun TA:vla-get-insertionpoint+ename (obj) ;ประกอบ entity_name กับ insertion_poiint ให้เป็น list (BLOCK ONLY)
      (if (= (vla-get-objectname obj) "AcDbBlockReference")
        (progn
          ;get_data
            (setq ename_ (vlax-vla-object->ename obj)) 
            
            (setq _inspt (vlax-safearray->list (vlax-variant-value (vla-get-insertionpoint obj))))
          ;
          ;sum_data_to_list
            (setq sum_list (list 
                            _inspt
                            ename_
                            ;add more
                          )
            )
          ;
        )
        (setq error "OBJECT IS NOT BLOCK")
      )
    )
    (defun TA:move_axis_insertionpoint (blk_obj_ axis_set_ axis_val_) ;ใช้ move axis_set_ ทีละแกน = "x" "y" "z" 
      (if (= (vla-get-objectname blk_obj_) "AcDbBlockReference")
        (progn
          (setq blk_obj_ins_ (vlax-safearray->list (vlax-variant-value (vla-get-insertionpoint blk_obj_))))
          (cond
            (;aixs_case_1
              (and 
                (= (strcase axis_set_) "X")
                (= (numberp axis_val_) T)
              )
              (progn
                (vla-put-insertionpoint blk_obj_ 
                                        (vlax-3d-point (list
                                                          (+ (car blk_obj_ins_) axis_val_)
                                                          (+ (cadr blk_obj_ins_) 0)
                                                          (+ (caddr blk_obj_ins_) 0)
                                                        )
                                        )
                )
                (princ "aixs_case_1")
              )
            )
            (;aixs_case_2
              (and
                  (= (strcase axis_set_ ) "Y")
                  (= (numberp axis_val_) T)
              )
              (progn
                (vla-put-insertionpoint blk_obj_ 
                                        (vlax-3d-point (list
                                                          (+ (car blk_obj_ins_) 0)
                                                          (+ (cadr blk_obj_ins_) axis_val_)
                                                          (+ (caddr blk_obj_ins_) 0)
                                                        )
                                        )
                )
                (princ "aixs_case_2")
              )
            )
            (;aixs_case_3
              (and 
                (= (strcase axis_set_) "Z")
                (= (numberp axis_val_) T)
              )
              (progn
                (vla-put-insertionpoint blk_obj_ 
                                        (vlax-3d-point (list
                                                          (+ (car blk_obj_ins_) 0)
                                                          (+ (cadr blk_obj_ins_) 0)
                                                          (+ (caddr blk_obj_ins_) axis_val_)
                                                        )
                                        )
                )
                (princ "aixs_case_3")
              )
            )
          )
          
        )
      )
    )
    (defun TA:move_polar_insertionpoint (blk_obj_  axis_set_ axis_val_) ;ใช้ move axis_set_ ทีละแกน = "x" "y" "z" 
      ; (setq polar_val )
      ; (setq blk_ename_ (car (entsel "specify Object")))
      ; (setq blk_obj_ (vlax-ename->vla-object blk_ename_))
      ; (setq rotation_val (vla-get-rotation blk_obj_))
      ; (setq axis_set_ "y")
      ; (setq axis_val_ 20)
      (if (= (vla-get-objectname blk_obj_) "AcDbBlockReference")
        (progn
          (setq blk_obj_ins_ (vlax-safearray->list (vlax-variant-value (vla-get-insertionpoint blk_obj_))))
          (setq blk_obj_rotation_val (vla-get-rotation blk_obj_))
          (cond
            (;aixs_case_1
              (and 
                (= (strcase axis_set_) "X")
                (= (numberp axis_val_) T)
                (= (numberp blk_obj_rotation_val) T)
              )
              (progn
                (setq new_ins_ (polar blk_obj_ins_ (deg-to-rad (TA:ModifyRotation (rad-to-deg blk_obj_rotation_val) 90)) axis_val_))
                (vla-put-insertionpoint blk_obj_ 
                                        (vlax-3d-point (list
                                                          (+ (car new_ins_) 0)
                                                          (+ (cadr new_ins_) 0)
                                                          (+ (caddr new_ins_) 0)
                                                        )
                                        )
                )
                (princ "aixs_case_1")
              )
            )
            (;aixs_case_2
              (and
                  (= (strcase axis_set_ ) "Y")
                  (= (numberp axis_val_) T)
                  (= (numberp blk_obj_rotation_val) T)
              )
              (progn
                (setq new_ins_ (polar blk_obj_ins_ (deg-to-rad (TA:ModifyRotation (rad-to-deg blk_obj_rotation_val) 180)) axis_val_))
                (vla-put-insertionpoint blk_obj_ 
                                        (vlax-3d-point (list
                                                          (+ (car new_ins_) 0)
                                                          (+ (cadr new_ins_) 0)
                                                          (+ (caddr new_ins_) 0)
                                                        )
                                        )
                )
                (princ "aixs_case_2")
              )
            )
            (;aixs_case_3
              (and 
                (= (strcase axis_set_) "Z")
                (= (numberp axis_val_) T)
              )
              (progn
                (alert "no polar FUNC FOR Z")
                (princ "aixs_case_3")
              )
            )
          )
          
        )
      )
    )
    (defun TA:ename+vla-getboundingbox (obj) ;ประกอบ entity_name กับ vla-getboundingbox ให้เป็น list (LINE OR POLYLINE ONLY)
      ; (setq obj (vla-get-objectname (vlax-ename->vla-object (car (entsel))))) ;For Check objectname
      (if (or
            (= (vla-get-objectname obj) "AcDbLine")
            (= (vla-get-objectname obj) "AcDbPolyline")
            (= (vla-get-objectname obj) "AcDbBlockReference") 
            (= (vla-get-objectname obj) "AcDbArc") 
          )
        (progn
          ;get_data
            (setq ename_ (vlax-vla-object->ename obj)) 
            
            (setq _inspt (vla-getboundingbox obj 'min_ 'max_))
            (setq min_ (vlax-safearray->list min_))
            (setq max_ (vlax-safearray->list max_))
          ;
          ;sum_data_to_list
            (setq sum_list (list 
                            ename_
                            min_
                            max_
                            ;add more
                          )
            )
          ;
        )
        (setq error "OBJECT IS NOT LINE/POLYLINE")
      )
    )
    (defun TA:ss_vla-getboundingbox (sss_)
      ; (setq sss_ (ssget))
      (cond
        (;type_case_1
            (and
              (= (type sss_) 'PICKSET)
            )
            (progn
              ;preloop_and_while
                (setq sss_i 0)
                (setq sss_obj_getboundingbox_list_ nil)
                (while (< sss_i (sslength sss_))
                  (setq sss_ename_ (ssname sss_ sss_i))
                  (setq sss_obj_ (vlax-ename->vla-object sss_ename_))
                  (setq sss_obj_getboundingbox (vla-getboundingbox sss_obj_ 'min_ 'max_)) 
                  (setq sss_min_ (vlax-safearray->list min_)) 
                  (setq sss_max_ (vlax-safearray->list max_))
                  (setq sss_obj_getboundingbox_list_ (cons (list sss_min_ sss_max_) sss_obj_getboundingbox_list_))      
                  (setq sss_i (+ sss_i 1))
                )
                ;TA:stanndard_lambda_sorting
                  (setq low_xy_ (list 
                                  (setq low_x (car 
                                                (car 
                                                  (car 
                                                    (vl-sort sss_obj_getboundingbox_list_  ;bigest open indent list
                                                            (function 
                                                              (lambda (a b) 
                                                                (< (nth 0 (car a)) 
                                                                    (nth 0 (car b))
                                                                )
                                                              )
                                                            )
                                                    )
                                                  )
                                                )
                                              ) ;bigest close indent list
                                  )
                                  (setq low_y (cadr 
                                                (car 
                                                  (car 
                                                    (vl-sort sss_obj_getboundingbox_list_  ;bigest open indent list
                                                            (function 
                                                              (lambda (a b) 
                                                                (< (nth 1 (car a)) 
                                                                    (nth 1 (car b))
                                                                )
                                                              )
                                                            )
                                                    )
                                                  )
                                                )
                                              ) ;bigest close indent list
                                  )
                                )
                  )
                  (setq high_xy_ (list 
                                  (setq high_x (car 
                                                  (cadr 
                                                    (car 
                                                      (vl-sort sss_obj_getboundingbox_list_  ;bigest open indent list
                                                              (function 
                                                                (lambda (a b) 
                                                                  (> (nth 0 (cadr a)) 
                                                                      (nth 0 (cadr b))
                                                                  )
                                                                )
                                                              )
                                                      )
                                                    )
                                                  )
                                                ) ;bigest close indent list
                                  )
                                  (setq high_y (cadr 
                                                  (cadr 
                                                    (car 
                                                      (vl-sort sss_obj_getboundingbox_list_  ;bigest open indent list
                                                              (function 
                                                                (lambda (a b) 
                                                                  (> (nth 1 (cadr a)) 
                                                                      (nth 1 (cadr b))
                                                                  )
                                                                )
                                                              )
                                                      )
                                                    )
                                                  )
                                                ) ;bigest close indent list
                                  )
                                )
                  )
                ;
                (list low_xy_ high_xy_  )
                
              ;
              ; (princ "type_case_1")
            )
        )
        (;type_case_2
          (and
            (= (type sss_) 'LIST)
          )
          (progn
            (progn
              ;preloop_and_while
                (setq sss_i 0)
                (setq sss_obj_getboundingbox_list_ nil)
                (while (< sss_i (length sss_))
                  (setq sss_ename_ (nth sss_i sss_ ))
                  (setq sss_obj_ (vlax-ename->vla-object sss_ename_))
                  (setq sss_obj_getboundingbox (vla-getboundingbox sss_obj_ 'min_ 'max_)) 
                  (setq sss_min_ (vlax-safearray->list min_)) 
                  (setq sss_max_ (vlax-safearray->list max_))
                  (setq sss_obj_getboundingbox_list_ (cons (list sss_min_ sss_max_) sss_obj_getboundingbox_list_))      
                  (setq sss_i (+ sss_i 1))
                )
                ;TA:stanndard_lambda_sorting
                  (setq low_xy_ (list 
                                  (setq low_x (car 
                                                (car 
                                                  (car 
                                                    (vl-sort sss_obj_getboundingbox_list_  ;bigest open indent list
                                                            (function 
                                                              (lambda (a b) 
                                                                (< (nth 0 (car a)) 
                                                                    (nth 0 (car b))
                                                                )
                                                              )
                                                            )
                                                    )
                                                  )
                                                )
                                              ) ;bigest close indent list
                                  )
                                  (setq low_y (cadr 
                                                (car 
                                                  (car 
                                                    (vl-sort sss_obj_getboundingbox_list_  ;bigest open indent list
                                                            (function 
                                                              (lambda (a b) 
                                                                (< (nth 0 (cadr a)) 
                                                                    (nth 0 (cadr b))
                                                                )
                                                              )
                                                            )
                                                    )
                                                  )
                                                )
                                              ) ;bigest close indent list
                                  )
                                )
                  )
                  (setq high_xy_ (list 
                                  (setq high_x (car 
                                                  (cadr 
                                                    (car 
                                                      (vl-sort sss_obj_getboundingbox_list_  ;bigest open indent list
                                                              (function 
                                                                (lambda (a b) 
                                                                  (> (nth 0 (car a)) 
                                                                      (nth 0 (car b))
                                                                  )
                                                                )
                                                              )
                                                      )
                                                    )
                                                  )
                                                ) ;bigest close indent list
                                  )
                                  (setq high_y (cadr 
                                                  (cadr 
                                                    (car 
                                                      (vl-sort sss_obj_getboundingbox_list_  ;bigest open indent list
                                                              (function 
                                                                (lambda (a b) 
                                                                  (> (nth 0 (cadr a)) 
                                                                      (nth 0 (cadr b))
                                                                  )
                                                                )
                                                              )
                                                      )
                                                    )
                                                  )
                                                ) ;bigest close indent list
                                  )
                                )
                  )
                ;
                (list low_xy_ high_xy_  )
              ;
              ; (princ "type_case_1")
            ) 
          )
        )
      ) 
    )
    (defun TA:ss-erase (ss_pre_filter_set_xx_)
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (vla-delete ss_pre_filter_set_xx_obj_)
          (setq ss_pre_filter_set_xx_i (+ ss_pre_filter_set_xx_i 1))
        )
      ;
    )
    (defun TA:get-visible-boundingbox (blk_obj_ ) ;get coordinate real visible boundingbox 
      ; (setq blk_ename_ (car (entsel "specify Object")))
      ; (setq blk_obj_ (vlax-ename->vla-object blk_ename_))
      (setq blk_obj_rotation (vla-get-rotation blk_obj_))
      (setq blk_obj_ins_ (vlax-safearray->list (vlax-variant-value (vla-get-insertionpoint blk_obj_))))
      (setq blk_list_ ())
      (if (= (vla-get-objectname blk_obj_) "AcDbBlockReference")
        (progn
          (setq visible_list_ (ssadd))
          (setq blkname (cdr (assoc 2 (entget (vlax-vla-object->ename blk_obj_)))))
          (setq bdef (tblobjname "BLOCK" blkname))
          
          (if (= (vl-prin1-to-string (type bdef)) "ENAME") ;สำหรับ ดึงข้อมูลเพื่อทำ vla-getboundingbox
            (progn
              (setq nested (entnext bdef))
              (while 
                (and nested 
                    (/= (cdr (assoc 0 (entget nested))) "ENDBLK")
                )
                (if (and 
                      (setq nested_obj_ (vlax-ename->vla-object nested))
                      (/= (vla-get-objectname nested_obj_) "AcDbAttributeDefinition")
                      (/= (vla-get-objectname nested_obj_) "AcDbAttribute")
                      (/= (vla-get-objectname nested_obj_) "AcDbSequenceEnd")
                      (= (vla-get-visible nested_obj_) :vlax-true)
                    )
                  (progn 
                    (setq nested_ename (vlax-vla-object->ename nested_obj_))
                    (setq nested_obj_getboundingbox (vla-getboundingbox nested_obj_ 'min_ 'max_)) 
                    (setq nested_min_ (vlax-safearray->list min_)) 
                    (setq nested_max_ (vlax-safearray->list max_)) 
                    (command "rectangle" nested_min_ nested_max_)
                    (setq visible_list_ (ssadd (entlast) visible_list_))
                    (sslength visible_list_)
                  )
                )
                (setq nested (entnext nested))
                
              )
            )
          )
          (if (/= (sslength visible_list_ ) 0) ;สำหรับ reset ตำแหน่ง vla-getboundingbox
            (progn
              (command "pselect"  visible_list_ "" )
              (setq sss_ (ssget "i") )
              (setq ssssss (TA:ss_vla-getboundingbox sss_))
              (command "rectangle" (car ssssss) (cadr ssssss) )
              (vla-rotate 
                (vlax-ename->vla-object (entlast))
                (vlax-3d-point 0 0 0)
                blk_obj_rotation
              )
              (vla-move  
                (vlax-ename->vla-object (entlast))
                (vlax-3d-point 0 0 0)
                (vlax-3d-point blk_obj_ins_)
              )
              (command "erase" visible_list_ "")
              (setq lasted_ename (entlast))
              (setq lasted_sss_ (ssadd  ))
              (setq lasted_sss_ (ssadd lasted_ename lasted_sss_))
              (setq lasted_gbound_ (TA:ss_vla-getboundingbox lasted_sss_))
              ;get-data_
                (setq main_border_ (TA:ss_vla-getboundingbox lasted_sss_ ) )
                (setq ptmid_ (TA:midpoint (car main_border_) (cadr main_border_)))  
                (setq pt1 (list 
                    (car (car main_border_)) 
                    (cadr (car main_border_)) 
                    0 
                  )
                )
                (setq pt2 (list 
                    (car (cadr main_border_)) 
                    (cadr (car main_border_)) 
                    0 
                  )
                )
                (setq pt3 (list 
                    (car (cadr main_border_)) 
                    (cadr (cadr main_border_)) 
                    0 
                  )
                )
                (setq pt4 (list 
                    (car (car main_border_)) 
                    (cadr (cadr main_border_)) 
                    0 
                  )
                )
                (setq Len_1 (distance pt1 pt2))
                (setq Len_2 (distance pt2 pt3))
                (setq Len_3 (distance pt3 pt4))
                (setq Len_4 (distance pt4 pt1))
              ;
            )
          )
          ;result
            (list 
              (list pt1 pt2 pt3 pt4 )
              (list Len_1 Len_2 Len_3 Len_4)
            )
          ;
        )
      )
    )
    (defun TA:get-visible-boundingbox (blk_obj_ ) ;get coordinate real visible boundingbox 
      ; (setq blk_ename_ (car (entsel "specify Object")))
      ; (setq blk_obj_ (vlax-ename->vla-object blk_ename_))
      (setq blk_obj_rotation (vla-get-rotation blk_obj_))
      (setq blk_obj_ins_ (vlax-safearray->list (vlax-variant-value (vla-get-insertionpoint blk_obj_))))
      (setq blk_list_ ())
      (if (= (vla-get-objectname blk_obj_) "AcDbBlockReference")
        (progn
          (setq visible_list_ (ssadd))
          (setq blkname (cdr (assoc 2 (entget (vlax-vla-object->ename blk_obj_)))))
          (setq bdef (tblobjname "BLOCK" blkname))
          
          (if (= (vl-prin1-to-string (type bdef)) "ENAME") ;สำหรับ ดึงข้อมูลเพื่อทำ vla-getboundingbox
            (progn
              (setq nested (entnext bdef))
              (while 
                (and nested 
                    (/= (cdr (assoc 0 (entget nested))) "ENDBLK")
                )
                (if (and 
                      (setq nested_obj_ (vlax-ename->vla-object nested))
                      (/= (vla-get-objectname nested_obj_) "AcDbAttributeDefinition")
                      (/= (vla-get-objectname nested_obj_) "AcDbAttribute")
                      (/= (vla-get-objectname nested_obj_) "AcDbSequenceEnd")
                      (= (vla-get-visible nested_obj_) :vlax-true)
                    )
                  (progn 
                    (setq nested_ename (vlax-vla-object->ename nested_obj_))
                    (setq nested_obj_getboundingbox (vla-getboundingbox nested_obj_ 'min_ 'max_)) 
                    (setq nested_min_ (vlax-safearray->list min_)) 
                    (setq nested_max_ (vlax-safearray->list max_)) 
                    (command "rectangle" nested_min_ nested_max_)
                    (setq visible_list_ (ssadd (entlast) visible_list_))
                    (sslength visible_list_)
                  )
                )
                (setq nested (entnext nested))
                
              )
            )
          )
          (if (/= (sslength visible_list_ ) 0) ;สำหรับ reset ตำแหน่ง vla-getboundingbox
            (progn
              (command "pselect"  visible_list_ "" )
              (setq sss_ (ssget "i") )
              (setq ssssss (TA:ss_vla-getboundingbox sss_))
              (command "rectangle" (car ssssss) (cadr ssssss) )
              (vla-rotate 
                (vlax-ename->vla-object (entlast))
                (vlax-3d-point 0 0 0)
                blk_obj_rotation
              )
              (vla-move  
                (vlax-ename->vla-object (entlast))
                (vlax-3d-point 0 0 0)
                (vlax-3d-point blk_obj_ins_)
              )
              (command "erase" visible_list_ "")
              (setq lasted_ename (entlast))
              (setq lasted_sss_ (ssadd  ))
              (setq lasted_sss_ (ssadd lasted_ename lasted_sss_))
              (setq lasted_gbound_ (TA:ss_vla-getboundingbox lasted_sss_))
              ;get-data_
                (setq main_border_ (TA:ss_vla-getboundingbox lasted_sss_ ) )
                (setq ptmid_ (TA:midpoint (car main_border_) (cadr main_border_)))  
                (setq pt1 (list 
                    (car (car main_border_)) 
                    (cadr (car main_border_)) 
                    0 
                  )
                )
                (setq pt2 (list 
                    (car (cadr main_border_)) 
                    (cadr (car main_border_)) 
                    0 
                  )
                )
                (setq pt3 (list 
                    (car (cadr main_border_)) 
                    (cadr (cadr main_border_)) 
                    0 
                  )
                )
                (setq pt4 (list 
                    (car (car main_border_)) 
                    (cadr (cadr main_border_)) 
                    0 
                  )
                )
                (setq Len_1 (distance pt1 pt2))
                (setq Len_2 (distance pt2 pt3))
                (setq Len_3 (distance pt3 pt4))
                (setq Len_4 (distance pt4 pt1))
              ;
            )
          )
          ;result
            (list 
              (list pt1 pt2 pt3 pt4 )
              (list Len_1 Len_2 Len_3 Len_4)
            )
          ;
        )
      )
    )
    (defun TA:Get_Pline_vertext_angle_case1 (ename_) 
      ; (setq ename_ new_rec)
      (setq s_ (cadr (TA:Get_Pline_vertext_ins_point_ ename_)))
      (setq d1 (angtos (angle (nth 1 s_) (nth 2 s_))))
      (setq s_i 0)
      (setq s_ii 1)
      (setq end_val_ nil)
      (setq sum_ ())
      (while (< s_i (length s_))
          (setq pt_1 (nth s_i s_))
          (setq pt_3 (nth s_i s_))
          (if (= s_ii (length s_)) 
            (progn 
              (setq end_val_ "end")
              (setq pt_3 (nth (- s_i 1) s_))
            )
            (setq pt_2 (nth s_ii s_))
          )
          (setq angle_pt (atof (angtos (angle pt_1 pt_2))))
          (if (= end_val_ "end") 
            (progn
              (setq angle_pt (atof (angtos (angle pt_3 pt_1))))
              (setq sum (append  (list pt_1) (list angle_pt s_ii) ))
            )
            (setq sum (append  (list pt_1) (list angle_pt s_ii)))
          )
          
          (setq sum_ (cons sum sum_))
          (setq s_i (+ s_i 1))
          (setq s_ii (+ s_ii 1))
      )
      (setq result_ (reverse sum_))
    )
    (defun TA:Get_Pline_vertext_angle_case2 (ename_) 
      (setq s_ (cadr (TA:Get_Pline_vertext_ins_point_ ename_)))
      (setq d1 (angtos (angle (nth 1 s_) (nth 2 s_))))
      (setq s_i 0)
      (setq s_ii 1)
      (setq end_val_ nil)
      (setq sum_ ())
      (while (< s_i (length s_))
          (setq pt_1 (nth s_i s_))
          (if (= s_ii (length s_)) 
            (progn 
              (setq end_val_ "end")
            )
            (setq pt_2 (nth s_ii s_))
          )
          (setq angle_pt (atof (angtos (angle pt_1 pt_2))))
          (if (= end_val_ "end") 
            (progn 
              (setq sum (append  (list pt_1) (list end_val_ s_ii) ))
            )
            (setq sum (append  (list pt_1) (list angle_pt s_ii)))
          )
          
          (setq sum_ (cons sum sum_))
          (setq s_i (+ s_i 1))
          (setq s_ii (+ s_ii 1))
      )
      (setq result_ (reverse sum_))
    )
    (defun TA:Get_Pline_vertext_ins_point_ (ename_) ;must be (car (entsel))
      (setq Get_Pline_ (entget ename_))
      (setq Get_Pline_vtx_pt (vl-remove-if-not '(lambda (x) (= 10 (car x))) Get_Pline_))
      (setq Get_Pline_vtx_pt_ (mapcar 'cdr Get_Pline_vtx_pt))
      (setq ename+Get_Pline_vtx_pt_ (list
                                      ename_
                                      Get_Pline_vtx_pt_
                                    )
      
      )
    )
    (defun TA:get_vertex_len_ (ename_)
      ; (setq ref_line (car (entsel)))
      (setq ss (vlax-ename->vla-object ename_))
      (setq vertex_total (length (cadr (TA:Get_Pline_vertext_ins_point_ ename_))))
      (setq sum_ ())

      (setq vertex_i 0)
      (setq vertex_ii 1)

      (while (< vertex_i vertex_total)
        (cond
          (;_case_1
            (and
                (/= vertex_i (- vertex_total 1))
            )
            (progn
              ;get_data_len
                (setq len_i (vlax-curve-getDistatParam ss vertex_i) )
                (setq len_ii (vlax-curve-getDistatParam ss vertex_ii))
                ;
                ;sum
                  (setq sum (list (- len_ii len_i)))
                  (setq sum_ (append sum sum_ ))
                ;
              (princ "_case_1\n")
            )
          )
          (;_case_2
            (and
              (= vertex_i (- vertex_total 1))    
            )
            (progn
              ;ไม่มี
              (princ "_case_2\n")
            )
          )

        )
        
        
        (setq vertex_i (+ vertex_i 1))
        (setq vertex_ii (+ vertex_ii 1))
      )
      ;summary_reverse
        (setq sum_len (reverse sum_))
      ;
    )
    (defun TA:midpoint (ins_start_ ins_end_) ;คำนวณ midpoint จากระยะหัว-ท้าย ของเส้น
      ; (setq ins_start_ (list ins_start_x1 ins_start_y1))
      ; (setq ins_end_ (list ins_end_x1 ins_end_y1))
      (setq ins_mid_ (list 
                  (/ (+ (car ins_start_) (car ins_end_)) 2.0)
                  (/ (+ (cadr ins_start_) (cadr ins_end_)) 2.0)
                )
      )
    )
    (defun LM:PolyCentroid (e / l) 
      (foreach x (setq e (entget e)) (if (= 10 (car x)) (setq l (cons (cdr x) l))))
      ((lambda (a) 
        (if (not (equal 0.0 a 1e-8)) 
          (trans 
            (mapcar '/ 
                    (apply 'mapcar 
                          (cons '+ 
                                (mapcar 
                                  (function 
                                    (lambda (a b) 
                                      ((lambda (m) 
                                          (mapcar 
                                            (function (lambda (c d) (* (+ c d) m)))
                                            a
                                            b
                                          )
                                        ) 
                                        (- (* (car a) (cadr b)) (* (car b) (cadr a)))
                                      )
                                    )
                                  )
                                  l
                                  (cons (last l) l)
                                )
                          )
                    )
                    (list a a)
            )
            (cdr (assoc 210 e))
            0
          )
        )
      ) 
      (* 3.0 
          (apply '+ 
                (mapcar 
                  (function 
                    (lambda (a b) (- (* (car a) (cadr b)) (* (car b) (cadr a))))
                  )
                  l
                  (cons (last l) l)
                )
          )
      )
      )
    )
    (defun TA:find_center (main_border_) -
      (setq main_border_obj_ (vlax-ename->vla-object main_border_))
      (setq obj (vla-get-objectname main_border_obj_)) ;For Check objectname
      (if (= obj "AcDbPolyline") 
        (progn 
          (setq main_border_obj_boline_ (TA:ename+vla-getboundingbox main_border_obj_))
          (setq min_crood (cadr main_border_obj_boline_))
          (setq max_crood (caddr main_border_obj_boline_))
          (setq Mx (/ (+ (car min_crood) (car max_crood)) 2))
          (setq My (/ (+ (cadr min_crood) (cadr max_crood)) 2))
          (setq Mz (/ (+ (caddr min_crood) (caddr max_crood)) 2))
          (setq center_point_ (list Mx My Mz))
        )
        (alert "TA:find_center : Object is not PolyLine")
      )
    )
    (defun TA:Find_boundary_line_ (main_border_)
      ;for testing code
        ; (setq main_border_ (car (entsel)))
      ;
      ;get_data_
        (setq main_border_obj_ (vlax-ename->vla-object main_border_))
        (setq obj (vla-get-objectname main_border_obj_)) ;For Check objectname
        (if (or (= obj "AcDbPolyline") (= obj "AcDbBlockReference") (= obj "AcDbArc")) 
          (progn 
            (setq main_border_obj_boline_ (TA:ename+vla-getboundingbox main_border_obj_))
            (setq min_crood (cadr main_border_obj_boline_))
            (setq max_crood (caddr main_border_obj_boline_))
            ; (setq Mx (/ (+ (car min_crood) (car max_crood)) 2))
            ; (setq My (/ (+ (cadr min_crood) (cadr max_crood)) 2))
            ; (setq Mz (/ (+ (caddr min_crood) (caddr max_crood)) 2))
            ; (setq center_point_ (list Mx My Mz))
            (setq obj_boline_ (list 
                                (cadr main_border_obj_boline_ )
                                (caddr main_border_obj_boline_ )
                              )
            )
          )
          (alert "TA:find_center : Object is not PolyLine")
        )
      ;
    )
    (defun TA:textscr_process (msg Overall_rangecell_data_list_i Overall_rangecell_data_list_) ;for showing while loop process
      ; (textscr)
      ; (setq msg "sdsadsdasdasdasdas \n asasdsa ")
      ; (setq Overall_rangecell_data_list_i ss_pre_filter_set_xx_i )
      ; (setq Overall_rangecell_data_list_ ss_pre_filter_set_xx_ )
      (if (and
            (= (type msg) 'STR)            
            (= (type Overall_rangecell_data_list_i) 'INT)
            (or
              (= (type Overall_rangecell_data_list_) 'PICKSET )
              (= (type Overall_rangecell_data_list_) 'LIST )
            )
          )
        (progn
          (setq percent-sub
                 (fix (* (/ (float Overall_rangecell_data_list_i) 
                           (if (= (type Overall_rangecell_data_list_) 'PICKSET )
                            (progn
                              (sslength Overall_rangecell_data_list_)
                            )
                              (length Overall_rangecell_data_list_)
                           )
                         ) 
                         100
                      )
                 )
          )
          (princ 
            (strcat 
              msg
              (rtos percent-sub 2 0) " / " (rtos 100 2 0) "\n"
            )
          )
        )
      )
    )
    (defun TA:textscr_process_V2 (msg-1 Overall_rangecell_data_list_i Overall_rangecell_data_list_) ;for showing while loop process
      ; (textscr)
      ; (setq msg-1 "sdsadsdasdasdasdas \n asasdsa ")
      ; (setq Overall_rangecell_data_list_i ss_pre_filter_set_xx_i )
      ; (setq Overall_rangecell_data_list_ ss_pre_filter_set_xx_ )
      (if (and
            (= (type msg-1) 'STR)            
            (= (type Overall_rangecell_data_list_i) 'INT)
            (or
              (= (type Overall_rangecell_data_list_) 'PICKSET )
              (= (type Overall_rangecell_data_list_) 'LIST )
            )
          )
        (progn
          (setq percent-sub
                 (fix (* (/ (float Overall_rangecell_data_list_i) 
                           (if (= (type Overall_rangecell_data_list_) 'PICKSET )
                            (progn
                              (setq total_in_list_ (sslength Overall_rangecell_data_list_))
                            )
                              (setq total_in_list_ (length Overall_rangecell_data_list_))
                           )
                         ) 
                         100
                      )
                 )
          )
          (princ 
            (strcat 
              msg-1 " "
              (rtos percent-sub 2 0) "/" (rtos 100 2 0) "%" " " "(" 
              (rtos Overall_rangecell_data_list_i 2 0) "/" (rtos total_in_list_ 2 0) ")" "\n"
              
            )
          )
        )
      )
    )
    (defun c:breakline_Brdist ()
      (setq pline_ename_ (car (entsel "specify Object")))
      (setq pline_obj_ (vlax-ename->vla-object pline_ename_))
      (if (= (vla-get-objectname pline_obj_) "AcDbPolyline")
        (progn
          (setq osmode (getvar "osmode"))
          (setvar "osmode" 0)
          (if (< (setq real (getreal "specify dist.")) 0)
            (progn
              (setq ss (+ (vla-get-length pline_obj_) real))
              
              (command "breakatpoint" pline_ename_ (vlax-curve-getPointAtDist pline_obj_ ss))
            )
            (command "breakatpoint" pline_ename_ (vlax-curve-getPointAtDist pline_obj_ real))
          )
          
          (setvar "osmode" osmode)
        )
      )
    )
    
    (defun TA:assembly_coordinate_coner (main_border_)
      ;get-data_
        (setq pt_mid (list 
                    (/ (+ (car (car main_border_)) (car (cadr main_border_))) 2.0)
                    (/ (+ (cadr (car main_border_)) (cadr (cadr main_border_))) 2.0)
                  )
        )  
        (setq pt1 (list 
            (car (car main_border_)) 
            (cadr (car main_border_)) 
            0 
          )
        )
        (setq pt2 (list 
            (car (cadr main_border_)) 
            (cadr (car main_border_)) 
            0 
          )
        )
        (setq pt3 (list 
            (car (cadr main_border_)) 
            (cadr (cadr main_border_)) 
            0 
          )
        )
        (setq pt4 (list 
            (car (car main_border_)) 
            (cadr (cadr main_border_)) 
            0 
          )
        )
        (setq Len_1 (distance pt1 pt2))
        (setq Len_2 (distance pt2 pt3))
        (setq Len_3 (distance pt3 pt4))
        (setq Len_4 (distance pt4 pt1))
      ;
      (setq result (list pt1 pt2 pt3 pt4 pt_mid len_1 Len_2 Len_3 Len_4))
    )
  ;
  ;convert_FUNC
    (defun deg-to-rad (angle)
      (* angle (/ pi 180.0))
    )
    (defun rad-to-deg (rad)
      (/ (* rad 180) pi) 
    )
    (defun is-decimal (n) 
      (/= n (fix n))
    )
    (defun is-even-number (n) 
      ;preloop_and_while
      (setq n_i 0)
      (while (< n_i (+ 1 n)) 
        (if (= n_i n) (progn (setq result T) ) (setq result nil) )
        (setq n_i (+ n_i 1))
      )
      ;
      (setq result result)
    )
    (defun TA:ModifyRotation (Ex_rotation New_rotation)
      ;Note By Code_Developer
      ;The principle of this code is designed to modify the angle value, allowing for both increments and decrements based on a reference number.
      ;The reference number used must be a value representing degrees, ranging from 1 to 360.
      ;The number added or subtracted from the angle is calculated based on the number of degrees rotated, considering 1 full rotation as 360 degrees.
      ;
      (cond 
        ( ;normal_rotation_case_1
          (and 
            (>= New_rotation 0)
            (<= New_rotation 360)
          )
          (progn
            (princ "rotation_case_1\n")
            (setq new_rotaion_val_ (+ Ex_rotation New_rotation))
            (if (<= new_rotaion_val_ 360)
              (progn
                (setq new_rotaion_val_ (+ Ex_rotation New_rotation))
              )
              (setq new_rotaion_val_ (- (+ Ex_rotation New_rotation) 360))
            )
            
            
          )
        )
        (;multi_time_rotation_case_2
          (and 
            (> New_rotation 360)
          )
          (progn 
            (princ "rotation_case_2\n")
            (setq round_time_ (atoi (rtos (/ New_rotation 360) 2 0)))
            (setq round_time_val (* round_time_ 360))
            (setq new_rotaion_val_ (- New_rotation round_time_val))
            (if (> (+ Ex_rotation new_rotaion_val_ ) 360)
            (progn
              (setq new_rotaion_val_ans_ (-  (+ Ex_rotation new_rotaion_val_ ) 360 ))
            )
              (setq new_rotaion_val_ans_ (+ Ex_rotation new_rotaion_val_ ))
            )
            
          )
        )
        (;rotation_case_3
          (and 
            (<= New_rotation 0) 
          )
          (progn 
            (princ "rotation_case_3\n")
            (setq round_time_ (atoi (rtos (/ New_rotation 360) 2 0)))
            (setq round_time_val (* round_time_ 360))
            (setq new_rotaion_val_ (- New_rotation round_time_val))
            (setq Ex_rotation_val_ (+ Ex_rotation new_rotaion_val_))
            (if (< Ex_rotation_val_ 0)
              (progn
                (setq new_rotaion_val_ans_ (+ 360 Ex_rotation_val_))
              )
              (setq new_rotaion_val_ans_ Ex_rotation_val_ )
            )
            
          )
        )
        
      )
    )
    (defun LM:round ( n )
      (fix (+ n (if (minusp n) -0.5 0.5)))
    )
    (defun LM:roundup (n m) 
      ((lambda (r) (cond ((equal 0.0 r 1e-8) n) ((< n 0) (- n r)) ((+ n (- m r))))) 
        (rem n m)
      )
    )
    (defun TA:round-05 (num / n)
      ;; ปัดค่า num ให้ใกล้ .00 หรือ .50
      (setq n (* 2 num))             ; ขยายเป็นครึ่งหน่วย
      (if (minusp num)               ; ถ้าเป็นลบ
        (setq n (fix (- n 0.5)))     ; ปัดลงไปใกล้สุด
        (setq n (fix (+ n 0.5)))     ; ถ้าเป็นบวก ปัดขึ้นใกล้สุด
      )
      (/ n 2.0)                      ; ย่อกลับมา .0 หรือ .5
    )
    (defun TA:round-10 (num / n)
      ;; ปัดค่าทีละ 10 แบบไม่ให้มีเศษหลุด
      (setq n (+ (/ num 10.0) (if (minusp num) -0.0001 0.0001)))
      (* 10 (fix (+ n (if (minusp num) -0.5 0.5))))
    )
    (defun relocate_ins_ (data_list_ x_sym x_num_ y_sym y_num_ )
      (if (= (length data_list_) 2)
        (progn
          (setq data_list_ (list 
                            (x_sym (car data_list_) x_num_)
                            (y_sym (cadr data_list_) y_num_)
                          )
          )
        )
      )
    )
    (defun TA:Toerrance_num_ (target_num_ main_num_ tor_num_)
      (if
        (and 
          (< target_num_ (+ main_num_ tor_num_))
          (> target_num_ (- main_num_ tor_num_))
        )
        (progn
          T
        )
      )
    )
    (defun c:Selection-set_reverse_ssreverse ()
      ;selection_set_for_fillter_blk_name
        (if  ;pre_select_ssget_or_post_select_ssget
          (=
            (setq ss_pre_filter_set_xx_ (ssget "i"
                                              (list
                                                (cons 0 "LINE") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "LINE") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if (> (rad-to-deg (vla-get-angle ss_pre_filter_set_xx_obj_)) 90)
            (progn
              (command "reverse" ss_pre_filter_set_xx_ename_ "" )
            )
          )
          (setq ss_pre_filter_set_xx_i (+ ss_pre_filter_set_xx_i 1))
        )
      ;
    )
    (defun c:temp_reset_angle_RSANGE_ ()
      ;selection_set_for_fillter_blk_name
        (if  ;pre_select_ssget_or_post_select_ssget
          (=
            (setq ss_pre_filter_set_xx_ (ssget "i"
                                              (list
                                                (cons 0 "line") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "line") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          
          (setq ss_pre_filter_set_xx_obj_start_end_pt_ (list
                                          (setq ss_pre_filter_set_xx_obj_startpt_ (vlax-safearray->list
                                                                     (vlax-variant-value ( vla-get-startpoint ss_pre_filter_set_xx_obj_ ))
                                                                   )
                                          )
                                          (setq ss_pre_filter_set_xx_obj_endpt_ (vlax-safearray->list
                                                                    (vlax-variant-value ( vla-get-endpoint ss_pre_filter_set_xx_obj_ ))
                                                                 )
                                          )
                                        )
          )
          (vla-put-endpoint ss_pre_filter_set_xx_obj_
            (vlax-3d-point  
              (car ss_pre_filter_set_xx_obj_endpt_)
              (cadr ss_pre_filter_set_xx_obj_startpt_)
              0
            )
          )
          (setq ss_pre_filter_set_xx_i (+ ss_pre_filter_set_xx_i 1))
        )
      ;
    )
    (defun TA:is-scientific (n)
      (if 
        (or 
          (= (type n) 'real)
          (= (type n) 'ins)
        )
        (progn
          (if (wcmatch (strcase (rtos n 2 100)) "*E*")
            (progn
              T
            )
          )
        )
        nil
      )
    )
    (defun TA:fixprecision (n)
      (if 
        (or 
          (= (type n) 'real)
          (= (type n) 'ins)
        )
        (progn
          (setq n (- (fix n) n))
          (if (and 
                (/= n 0 )
                (< n 0.00000001 )
                (> n -1 )
              )
            (progn
              (fix n)
            )
          )
        )
        nil
      )
      
    )
    (defun TA:prefix_value (n)  
      (cond  
        ( ;_case_1 
         (and 
           (> n 0)
           (< n 10)
         )
         (progn 
           (strcat "000" (rtos n 2 0))
         )
        )
        ( ;_case_1
         (and 
           (>= n 10)
           (< n 100) 
         )
         (progn 
           (strcat "00" (rtos n 2 0))
         )
        )
        ( ;_case_1
         (and 
           (>= n 100)
           (< n 1000)
         )
         (progn 
           (strcat "0" (rtos n 2 0))
         )
        )
        ( ;_case_1
         (and 
           (>= n 1000) 
         )
         (progn 
           (strcat  (rtos n 2 0)) 
         )
        )
        
      )
    )
    (defun TA:prefix_value_00 (n)  
      (cond  
        ( ;_case_1 
         (and 
           (> n 0)
           (< n 10)
         )
         (progn 
           (strcat "0" (rtos n 2 0))
         )
        )
        ( ;_case_1
         (and 
           (>= n 10)
           (< n 100) 
         )
         (progn 
           (strcat  (rtos n 2 0))
         )
        )
        ( ;_case_1
         (and 
           (>= n 100) 
         )
         (progn 
           (strcat  (rtos n 2 0))
         )
        )
      )
    )
    (defun TA:prefix_value_000 (n)  
      (cond  
        ( ;_case_1 
         (and 
           (> n 0)
           (< n 10)
         )
         (progn 
           (strcat "00" (rtos n 2 0))
         )
        )
        ( ;_case_1
         (and 
           (>= n 10)
           (< n 100) 
         )
         (progn 
           (strcat "0" (rtos n 2 0))
         )
        )
        ( ;_case_1
         (and 
           (>= n 100) 
           (< n 1000)
         )
         (progn 
           (strcat  (rtos n 2 0))
         )
        )
        ( ;_case_1
         (and 
           (>= n 1000) 
         )
         (progn 
           (strcat  (rtos n 2 0))
         )
        )
      )
    )
    
    (defun TA:list_rotate_left (lst)
      (if lst
        (append (cdr lst) (list (car lst)))
      )
    )
    (defun TA:list_rotate_right (lst)
      (if lst
        (append (list (car (reverse lst))) (reverse (cdr (reverse lst))) )
      )
    )
    (defun TA:KeepNumber (str /)
      (vl-list->string
        (vl-remove-if-not
          '(lambda (c) (and (>= c 48) (<= c 57)))
          (vl-string->list str)
        )
      )
    )
    (defun TA:List_to_mtext_ ( input_list_ insertion_point_ text_height_ / acad_document_ drawing_space_ mtext_string_ mtext_obj_ )

      (vl-load-com)

      ;convert each list item to one MText line
      (setq mtext_string_ "")

      (foreach item_ input_list_
        (setq mtext_string_
          (strcat
            mtext_string_
            (if (= mtext_string_ "")
              ""
              "\\P"
            )
            (vl-princ-to-string item_)
          )
        )
      )

      ;get current drawing space
      (setq acad_document_
        (vla-get-ActiveDocument
          (vlax-get-acad-object)
        )
      )

      (setq drawing_space_
        (vla-get-Block
          (vla-get-ActiveLayout acad_document_)
        )
      )

      ;create MText
      (setq mtext_obj_
        (vla-AddMText
          drawing_space_
          (vlax-3d-point insertion_point_)
          0.0
          mtext_string_
        )
      )

      (vla-put-Height
        mtext_obj_
        text_height_
      )

      mtext_obj_
    )
    (defun TA:Mtext_format_to_text_
      (
        mtext_string_
        /
        _replace_all_
        semicolon_position_
      )

      ;replace all strings
      (defun _replace_all_
        (
          new_string_
          old_string_
          source_string_
          /
          position_
        )

        (while
          (setq position_
            (vl-string-search
              old_string_
              source_string_
            )
          )

          (setq source_string_
            (strcat
              (substr source_string_ 1 position_)
              new_string_
              (substr
                source_string_
                (+
                  position_
                  (strlen old_string_)
                  1
                )
              )
            )
          )
        )

        source_string_
      )

      ;remove Font Format:
      ;{\fCentury Gothic|b1|i0|c0|p34;
      (if
        (setq semicolon_position_
          (vl-string-search ";" mtext_string_)
        )
        (setq mtext_string_
          (substr
            mtext_string_
            (+ semicolon_position_ 2)
          )
        )
      )

      ;remove special MText characters
      (setq mtext_string_
        (_replace_all_ "" "\r\n" mtext_string_)
      )
      (setq mtext_string_
        (_replace_all_ "" "\\P" mtext_string_)
      )

      (setq mtext_string_
        (_replace_all_ " " "\\~" mtext_string_)
      )

      (setq mtext_string_
        (_replace_all_ "" "{" mtext_string_)
      )

      (setq mtext_string_
        (_replace_all_ "" "}" mtext_string_)
      )

      ;remove underline and overline codes
      (foreach format_code_
        '(
          "\\L"
          "\\l"
          "\\O"
          "\\o"
          "\\K"
          "\\k"
        )

        (setq mtext_string_
          (_replace_all_
            ""
            format_code_
            mtext_string_
          )
        )
      )

      ;remove duplicate spaces
      (while
        (vl-string-search "  " mtext_string_)
        (setq mtext_string_
          (_replace_all_
            " "
            "  "
            mtext_string_
          )
        )
      )

      ;remove spaces at beginning and end
      (vl-string-trim
        " "
        mtext_string_
      )
    )
  ;
  ;format_FUNC
    (defun format-all-workbook-list (data)
      (progn
        ;; เริ่มต้นเปิดต้น list
        (princ "(")
        (princ (car data)) ; พิมพ์ตัวเลขหลัก
        (princ "\n") ; เว้นบรรทัดเพื่อจัด layout

        ;; ใช้ foreach เพื่อวนลูป book
        (foreach book (cdr data)
          (progn
            (princ "  (")
            (princ (car book)) ; พิมพ์ index ของ book
            (princ " ")
            (princ (cadr book)) ; พิมพ์ชื่อของ book
            (princ " ")
            (princ (caddr book)) ; พิมพ์ object ของ book
            (princ "\n    (\n") ; เว้นบรรทัดสำหรับ sheet list

            ;; วนลูปภายใน sheet list
            (foreach sheet (cadddr book)
              (progn
                (princ "      (")
                (princ (car sheet)) ; พิมพ์ index ของ sheet
                (princ " ")
                (princ (cadr sheet)) ; พิมพ์ชื่อของ sheet
                (princ " ")
                (princ (caddr sheet)) ; พิมพ์ object ของ sheet
                (princ ")\n"))) ; ปิด sheet list
            (princ "    )\n  )\n"))) ; ปิด book และจัด layout
        (princ ")\n")
      )
    )
    (defun format-all-worksheet-list (lst)
      (progn
        ;; พิมพ์ header ของ list
        (princ "(")
        (princ (car lst)) ; พิมพ์ element ตัวแรก
        (princ " ")
        (princ (cadr lst)) ; พิมพ์ element ตัวที่สอง
        (princ " ")
        (princ (caddr lst)) ; พิมพ์ element ตัวที่สาม
        (princ "\n (\n")

        ;; ใช้ foreach สำหรับวนลูป element ย่อย
        (foreach sublist (cadddr lst) ; ส่วนที่เป็น sublist
          (progn
            (princ "  (")
            (princ (car sublist))  ; พิมพ์ element ย่อยตัวแรก
            (princ " ")
            (princ (cadr sublist)) ; พิมพ์ element ย่อยตัวที่สอง
            (princ " ")
            (princ (caddr sublist)) ; พิมพ์ element ย่อยตัวที่สาม
            (princ ")\n")))
        
        ;; ปิดท้าย list
        (princ " )\n)")
      )
    )
    (defun format-data (data)
      (progn
        ;; เริ่มต้นเปิดต้น list
        (princ "(")
        (princ (car data)) ; พิมพ์ตัวเลขหลัก
        (princ "\n") ; เว้นบรรทัดเพื่อจัด layout

        ;; ใช้ foreach เพื่อวนลูป book
        (foreach book (cdr data)
          (progn
            (princ "  (")
            (princ (car book)) ; พิมพ์ index ของ book
            (princ " ")
            (princ (cadr book)) ; พิมพ์ชื่อของ book
            (princ " ")
            (princ (caddr book)) ; พิมพ์ object ของ book
            (princ "\n    (\n") ; เว้นบรรทัดสำหรับ sheet list

            ;; วนลูปภายใน sheet list
            (foreach sheet (cadddr book)
              (progn
                (princ "      (")
                (princ (car sheet)) ; พิมพ์ index ของ sheet
                (princ " ")
                (princ (cadr sheet)) ; พิมพ์ชื่อของ sheet
                (princ " ")
                (princ (caddr sheet)) ; พิมพ์ object ของ sheet
                (princ ")\n"))) ; ปิด sheet list
            (princ "    )\n  )\n"))) ; ปิด book และจัด layout
        (princ ")\n")
      )
    )
  ;
  ;text_convert_
    (defun LM:StringSubst ( new old str / inc len )  
      (if (= (wcmatch  str (strcat "*" old "*") ) T) 
        (progn 
          (setq len (strlen new)
                inc 0
          )
          (while (setq inc (vl-string-search old str inc)) 
            (setq str (vl-string-subst new old str inc)
                  inc (+ inc len)
            )
            str
          )
        )
      )
    )
    (defun TA:Attribute_to_text_ATT2TXT ()
      ;selection_set_for_fillter_blk_name
        (if  ;pre_select_ssget_or_post_select_ssget
          (=
            (setq ss_pre_filter_set_xx_ (ssget "i"
                                              (list
                                                (cons 0 "attdef") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "attdef") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-3d-point (vlax-safearray->list (vlax-variant-value (vla-get-insertionpoint ss_pre_filter_set_xx_obj_)))))
          (setq ss_pre_filter_set_xx_obj_TagString_ (vla-get-tagstring ss_pre_filter_set_xx_obj_))
          (setq ss_pre_filter_set_xx_obj_textheigth (vla-get-height ss_pre_filter_set_xx_obj_))
          (create-text-vla ss_pre_filter_set_xx_obj_ins_ ss_pre_filter_set_xx_obj_TagString_ ss_pre_filter_set_xx_obj_textheigth 0)
          (setq ss_pre_filter_set_xx_i (+ ss_pre_filter_set_xx_i 1))
        )
      ;
      (command "erase" ss_pre_filter_set_xx_ "" )
    )
  ;
  ;CLEANER_FUNC Ta Trai
    (defun TA:get_name_block_in_drawing_to_list ()
      ;get_obj_file_
        (setq multi_blocks_obj (vla-get-blocks (vla-get-ActiveDocument (vlax-get-acad-object))))
        (setq block_list_ ())
      ;
      ;method_for_get_name_block_in_drawing
        ;method_1_get_name_
          (vlax-for block_ multi_blocks_obj 
            (setq block_list_ (append block_list_ (list (vla-get-name block_))))
          )
        ;
        ; ;method_2_get_name_
        ;   (setq block_i 0)
        ;   (while (< block_i (vla-get-count multi_blocks_obj))
        ;     (setq block_ (vla-item multi_blocks_obj block_i))
        ;     (setq block_list_ (append block_list_ (list (vla-get-name block_))))
        ;     (setq block_i (1+ block_i))
        ;   )
        ; ;
      ;
      ;sorting_name_block
        (setq sorted_block_list_ (acad_strlsort block_list_))
      ;
      ;preloop_and_while filtter_
        (setq sorted_block_list_i 0)
        (setq filter_sorted_block_ ())

        (while (< sorted_block_list_i (length sorted_block_list_))
          (setq filter_sorted_block_effectivename_ (nth sorted_block_list_i sorted_block_list_))
          
          (if (/= (substr filter_sorted_block_effectivename_ 1 1) "*") ; ตรวจสอบว่าชื่อเริ่มต้นด้วย *
            (progn
              (setq filter_sorted_block_ (cons filter_sorted_block_effectivename_ filter_sorted_block_))
            )
          )
          (setq sorted_block_list_i (+ sorted_block_list_i 1))
        )
      ;
      ;summary_total_block
        (setq filter_sorted_block_total (length filter_sorted_block_))
        (princ "\n                  |=====================|")
        (princ "\n                  | TOTAL BLOCK IN FILE |")
        (princ (strcat "\n                  |     = " (itoa filter_sorted_block_total) " block         |"))
        (princ "\n                  |          set        |")
        (princ "\n                  |---------------------|")
        (setq filter_sorted_block_ (acad_strlsort filter_sorted_block_))
      ;
    )
    (defun TA:get_name_block_in_drawing_to_list_v2 ()
      ;get_obj_file_
        (setq multi_blocks_obj (vla-get-blocks (vla-get-ActiveDocument (vlax-get-acad-object))))
        (setq block_list_ ())
      ;
      ;method_for_get_name_block_in_drawing
        ;method_1_get_name_
          (vlax-for block_ multi_blocks_obj 
            (setq block_list_ (append block_list_ (list (vla-get-name block_))))
          )
        ;
        ; ;method_2_get_name_
        ;   (setq block_i 0)
        ;   (while (< block_i (vla-get-count multi_blocks_obj))
        ;     (setq block_ (vla-item multi_blocks_obj block_i))
        ;     (setq block_list_ (append block_list_ (list (vla-get-name block_))))
        ;     (setq block_i (1+ block_i))
        ;   )
        ; ;
      ;
      ;sorting_name_block
        (setq sorted_block_list_ (acad_strlsort block_list_))
      ;
      ;preloop_and_while filtter_
        (setq sorted_block_list_i 0)
        (setq filter_sorted_block_ ())
        (setq sorted_block_list_ (acad_strlsort sorted_block_list_))
        (while (< sorted_block_list_i (length sorted_block_list_))
          (setq filter_sorted_block_effectivename_ (nth sorted_block_list_i sorted_block_list_))
          (setq doc (vla-get-ActiveDocument (vlax-get-acad-object)))
          (setq block-def (vla-Item (vla-get-Blocks doc) filter_sorted_block_effectivename_))
          (vla-get-blockscaling block-def )
          (if (/= (substr filter_sorted_block_effectivename_ 1 1) "*") ; ตรวจสอบว่าชื่อเริ่มต้นด้วย *
            (progn
              (setq filter_sorted_block_ (cons (list filter_sorted_block_effectivename_ (vla-get-blockscaling block-def )) filter_sorted_block_))
            )
          )
          (setq sorted_block_list_i (+ sorted_block_list_i 1))
        )
      ;
      ;summary_total_block
        (setq filter_sorted_block_total (length filter_sorted_block_))
        (princ "\n                  |=====================|")
        (princ "\n                  | TOTAL BLOCK IN FILE |")
        (princ (strcat "\n                  |     = " (itoa filter_sorted_block_total) " block         |"))
        (princ "\n                  |          set        |")
        (princ "\n                  |---------------------|")
        (setq filter_sorted_block_ filter_sorted_block_)
      ;
    )
    (defun TA:RE_COLOR_ALL_NORMAL_OBJECT_CHANGE_ (c-main-color)
      (setq all_obj_in_block (ssget "x" 
                                    (list 
                                      ; (cons 0 "insert")       ;type of object
                                      ; (cons 8 "000 - GRID")   ;kind of layer
                                      ; (cons 2 "SSSS")       ;kind of nameblock
                                      ; (cons 62 1)           ;kind of color call sign with color code index
                                    )
                              )
      )
      (command "chprop" all_obj_in_block "" "c" c-main-color "")
    )
    (defun TA:RE_COLOR_ALL_DIM+LEADER_OBJ (dim-main-color)
      ;dim_obj_mode
        ; (setq ss (vlax-get-property (vlax-ename->vla-object (car (entsel))) 'objectname)) ;logic for testing
        ; (setq ss (vlax-dump-object (vlax-ename->vla-object (car (entsel))) 'objectname))  ;logic for testing
        ;user_input_ selection_dim_object
          (setq all_dim_out_block (ssget "x" 
                                          (list 
                                            (cons 0 "dimension")       ;type of object
                                            ; (cons 8 "000 - GRID")   ;kind of layer
                                            ; (cons 2 "SSSS")       ;kind of nameblock
                                            ; (cons 62 1)           ;kind of color call sign with color code index
                                          )
                                  )
          )
        ;
        ; (command "pselect" all_dim_out_block "")
        (if (/= all_dim_out_block nil)
          (progn
            (setq all_dim_out_block_total (sslength all_dim_out_block))
            (setq all_dim_out_block_iii 0)
            (while
              (< all_dim_out_block_iii all_dim_out_block_total)
              (setq all_dim_out_block_ename (ssname all_dim_out_block all_dim_out_block_iii))
              (setq all_dim_out_block_obj (vlax-ename->vla-object all_dim_out_block_ename))
              ; (vlax-dump-object all_dim_out_block_obj)
                (cond 
                  ((and 
                      (= (vlax-get-property all_dim_out_block_obj 'objectname) 
                          "AcDbAlignedDimension"
                      )
                    )
                    (progn 
                      (vla-put-textcolor all_dim_out_block_obj dim-main-color)
                      (vla-put-dimensionlinecolor all_dim_out_block_obj dim-main-color)
                      (vla-put-extensionlinecolor all_dim_out_block_obj dim-main-color)
                    )
                    (princ "\n")
                  )
                  ((and 
                      (= (vlax-get-property all_dim_out_block_obj 'objectname) 
                          "AcDb2LineAngularDimension"
                      )
                    )
                    (progn 
                      (vla-put-textcolor all_dim_out_block_obj dim-main-color)
                      (vla-put-dimensionlinecolor all_dim_out_block_obj dim-main-color)
                      (vla-put-extensionlinecolor all_dim_out_block_obj dim-main-color)
                    )
                  )
                  ((and 
                      (= (vlax-get-property all_dim_out_block_obj 'objectname) 
                          "AcDbRotatedDimension"
                      )
                    )
                    (progn 
                      (vla-put-textcolor all_dim_out_block_obj dim-main-color)
                      (vla-put-dimensionlinecolor all_dim_out_block_obj dim-main-color)
                      (vla-put-extensionlinecolor all_dim_out_block_obj dim-main-color)
                    )
                  )
                  ((and 
                      (= (vlax-get-property all_dim_out_block_obj 'objectname) 
                          "AcDbArcDimension"
                      )
                    )
                    (progn 
                      (vla-put-textcolor all_dim_out_block_obj dim-main-color)
                      (vla-put-dimensionlinecolor all_dim_out_block_obj dim-main-color)
                      (vla-put-extensionlinecolor all_dim_out_block_obj dim-main-color)
                    )
                  )
                  ((and 
                      (= (vlax-get-property all_dim_out_block_obj 'objectname) 
                          "AcDbDiametricDimension" 
                      )
                    )
                    (progn 
                      (vla-put-textcolor all_dim_out_block_obj dim-main-color)
                      (vla-put-dimensionlinecolor all_dim_out_block_obj dim-main-color)
                    )
                  )
                  ((and 
                      (= (vlax-get-property all_dim_out_block_obj 'objectname) 
                          "AcDbOrdinateDimension" 
                      )
                    )
                    (progn 
                      (vla-put-textcolor all_dim_out_block_obj dim-main-color)
                      (vla-put-ExtensionLineColor  all_dim_out_block_obj dim-main-color)
                    )
                  )
                  ((and 
                      (= (vlax-get-property all_dim_out_block_obj 'objectname) 
                          "AcDbRadialDimension" 
                      )
                    )
                    (progn 
                      (vla-put-textcolor all_dim_out_block_obj dim-main-color)
                      (vla-put-dimensionlinecolor all_dim_out_block_obj dim-main-color)
                    )
                  )
                )
              ; (vla-put-textcolor all_dim_out_block_obj dim-main-color)
              ; (vla-put-dimensionlinecolor all_dim_out_block_obj dim-main-color)
              ; ; (vla-put-extensionlinecolor all_dim_out_block_obj dim-main-color)
              (setq all_dim_out_block_iii (+ all_dim_out_block_iii 1))
            )
          )
          (princ "\n")
        )
      ;
      ;leader_obj_mode
        ;user_input_ selection_leader_object    
          (setq all_leader_out_block (ssget "x" 
                                        (list 
                                          (cons 0 "leader")       ;type of object
                                          ; (cons 8 "000 - GRID")   ;kind of layer
                                          ; (cons 2 "SSSS")       ;kind of nameblock
                                          ; (cons 62 1)           ;kind of color call sign with color code index
                                        )
                                )
          )
        ;
          (if (/= all_leader_out_block nil)
            (progn
              (setq all_leader_out_block_total (sslength all_leader_out_block))
              (setq all_leader_out_block_iii 0)
              (while
                (< all_leader_out_block_iii all_leader_out_block_total)
                (setq all_leader_out_block_ename (ssname all_leader_out_block all_leader_out_block_iii))
                (setq all_leader_out_block_obj (vlax-ename->vla-object all_leader_out_block_ename))
                (vla-put-dimensionlinecolor all_leader_out_block_obj dim-main-color)
                (setq all_leader_out_block_iii (+ all_leader_out_block_iii 1))
              )
            )
            (princ "\n")
          )
      ;
    )
  ;
  ;delete_func_
    (defun TA:delete_block_ (selection_set_ efname_val_1 efname_val_2 efname_val_3)
      ;for testing_data_
        ; (setq selection_set_ (ssget ))
        ; (setq efname_val_ "special_block2460499.7018" )
      ;
      ;get_data_
        
      ;
      ;prelooop_and_while
        (setq selection_set_i 0)
        (while  (< selection_set_i (sslength selection_set_))
          (setq selection_set_ename_ (ssname selection_set_ selection_set_i))
          (setq selection_set_ename_obj (vlax-ename->vla-object selection_set_ename_))
          
            ;delete_block_process
              (if
                (and 
                  (/= (LM:effectivename selection_set_ename_obj) efname_val_1)
                  (/= (LM:effectivename selection_set_ename_obj) efname_val_2)
                  (/= (LM:effectivename selection_set_ename_obj) efname_val_3)
                )
                (progn
                  (vla-delete selection_set_ename_obj)
                )
                (princ "/nnext")
              )
            ;
          
          (setq selection_set_i (+ selection_set_i 1))
        )
      ;

    )
  ;
  ;CREATE_OBJECT_FUNC
    ;text
      (defun create-text-vla (pt textString height rotation / acadDoc textObj) 
        (setq acadObj (vlax-get-acad-object))
        (setq doc (vla-get-ActiveDocument acadObj))
        (setq modelSpace (vla-get-ModelSpace doc))
        (setq textObj (vla-addtext modelSpace textString pt height))
        (vla-put-Height textObj height)
        (vla-put-Rotation textObj rotation)
        textObj
      )
    ;
    ;add+pline_data
      (defun TA:vla-AddLightWeightPolyline_(point_list_)
          ;; This example creates a lightweight polyline in model space.
          (setq acadObj (vlax-get-acad-object))
          (setq doc (vla-get-ActiveDocument acadObj))
          
          ;; Define the intersection points
          

          ;; Convert 3D points to a flat 2D list
          (setq points (apply 'append (mapcar '(lambda (pt) (list (car pt) (cadr pt))) point_list_)))

          ;; Convert to safe array
          (setq pointArray (vlax-make-safearray vlax-vbDouble (cons 0 (- (length points) 1))))
          (vlax-safearray-fill pointArray points)
              
          ;; Create a lightweight Polyline object in model space
          (setq modelSpace (vla-get-ModelSpace doc))
          (setq plineObj (vla-AddLightWeightPolyline modelSpace pointArray))
          (vla-ZoomAll acadObj)
      )
      (defun TA:create-pline (points)
        (setq acadApp (vlax-get-acad-object))  ; เข้าถึง AutoCAD application
        (setq doc (vla-get-ActiveDocument acadApp))
        (if (= (getvar "ctab" ) "Model")
          (progn
            (setq ms (vla-get-ModelSpace doc))
          )
          (setq ms (vla-get-paperspace doc))
        )
          ; เข้าถึง Active Document
        
          ; เข้าถึง ModelSpace
        (if (= (type points) 'list)
          (progn
            (setq flatPoints (apply 'append points))
            (setq arr (vlax-make-safearray vlax-vbDouble (cons 0 (1- (length flatPoints)))))
            (vlax-safearray-fill arr flatPoints)
            (setq block (vla-AddPolyline 
                          ms 
                          arr
                        )
            )
          )
        )
        
      )
      (defun create-pline (coords)
        (if (= (length coords) 0)
            nil
          (progn
            ; สร้างพอลีไนจากค่าพิกัด
            (command "pline" (car coords) )
            
            ; วนลูปผ่านพิกัดทั้งหมดและเชื่อมต่อเส้นต่อเนื่อง
            (foreach coord (cdr coords)
              (command coord )
            )
          )
        )
        (command "")
      )
      (defun create-plines (coords close_loop_)
        (if (= (length coords) 0)
            nil
          (progn
            ; สร้างพอลีไนจากค่าพิกัด
            (command "pline" (car coords) )
            
            ; วนลูปผ่านพิกัดทั้งหมดและเชื่อมต่อเส้นต่อเนื่อง
            (foreach coord (cdr coords)
              (command coord )
            )
          )
        )
        (command "")
        (cond
          ( (= close_loop_ "close") 
            (progn 
              (setq new_line_data_ (vlax-ename->vla-object (entlast)))
              (vla-put-closed new_line_data_ :vlax-true)
            )
          )
          ((= close_loop_ "open") 
            (progn 
              (setq new_line_data_ (vlax-ename->vla-object (entlast)))
              (vla-put-closed new_line_data_ :vlax-false)
            )
          )
        )
      )
      (defun TA:vla-addvertex_ (pline_obj_ vertex_num_ point_list_)
        (setq point_list_new (remove_single_list_ 2 point_list_))
        (setq newVertex (vlax-make-safearray vlax-vbDouble '(0 . 1)))
        (vlax-safearray-fill newVertex point_list_new)
        (vla-addvertex pline_obj_ vertex_num_ newVertex)
      )
      (defun TA:add_vertex_point_pline_via_breakpt_ (ename_cut_edge_ ename_intersection_obj_)
        
        ;get_data_main_cut_and_main_intersection_
          (setq bb_obj_ (vlax-ename->vla-object ename_cut_edge_))     
          (setq ss_obj_ (vlax-ename->vla-object ename_intersection_obj_))     
          (setq intersec_ (LM:intersections+0 
                            bb_obj_
                            ss_obj_
                            acextendnone
                          )
          )
          (setq vertex_list_ (TA:Get_Pline_vertext_angle_case1 
                                ename_intersection_obj_
                              )
          )
          (setq intersec_i 0)
        ;
        ;preloop_and_while adding_vertex_point_
          (setq ename_list_ ())
          (setq ssadd_list_ (ssadd))
          (while   (< intersec_i (length intersec_))
            (setq intersec_val_ (nth intersec_i intersec_))
            (command "breakatpoint" ename_intersection_obj_ intersec_val_ "")
            (setq new_E_ (entlast))
            ; (command "pselect" new_E_)
            ; (command "pselect" ss)
            (setq ename_list_ (cons new_E_ ename_list_))
            (setq ssadd_list_ (ssadd new_E_ ssadd_list_))
            (setq ssadd_list_ (ssadd ename_intersection_obj_ ssadd_list_))
            (sslength ssadd_list_)
            (command "_.pedit" "_m" ssadd_list_ "" "_j" "" "")
            (setq ename_intersection_obj_ (entlast))
            (setq intersec_i (+ intersec_i 1))
            
          )
        ;
      )
      (defun TA:add_vertex_point_pline_via_breakpt_1 (ename_cut_edge_ ename_intersection_obj_)
        
            
            ;get_data_main_cut_and_main_intersection_
              (setq bb_obj_ (vlax-ename->vla-object ename_cut_edge_))     
              (setq ss_obj_ (vlax-ename->vla-object ename_intersection_obj_))     
              (setq intersec_ (LM:intersections+0 
                                bb_obj_
                                ss_obj_
                                acextendnone
                              )
              )
              (command "pedit" ename_intersection_obj_ "" "c" "" )
              (setq vertex_list_ (TA:Get_line_ins_point_ 
                                    ename_intersection_obj_
                                  )
              )
              (setq intersec_i 0)
            ;
            ;preloop_and_while adding_vertex_point_
              (setq ename_list_ ())   
              (setq ssadd_list_ (ssadd))
              (while   (< intersec_i (length intersec_))
                (setq intersec_val_ (nth intersec_i intersec_))
                (command "breakatpoint" ename_intersection_obj_ intersec_val_ "")
                
                (setq new_E_ (entlast))
                ; (command "pselect" new_E_)
                ; (command "pselect" ss)
                (setq ename_list_ (cons new_E_ ename_list_))
                (setq ssadd_list_ (ssadd new_E_ ssadd_list_))
                (setq ssadd_list_ (ssadd ename_intersection_obj_ ssadd_list_))
                (sslength ssadd_list_)
                (command "_.pedit" "_m" ssadd_list_ "y" "" "_j" "" "")
                (command "_.pedit" "_m" ssadd_list_ "" "y" )
                (setq ename_intersection_obj_ (entlast))
                (setq intersec_i (+ intersec_i 1))
                
              )
            ;
      )
    ;
    ;add_circle
      (defun TA:vla-addarc_ (center_ rad_ point_list_ )
        ; point_list_ must be two coord set in list
        ; do not vlax-3d_point w/ agument
        ;sub_func_
          (defun CO:sort_by_val_ (val_ list_ )  ;เรียงชุดข้อมูลตามแนวแกน
            (if (< val_ (length (car list_)))
              (progn
                (setq sortedLst (vl-sort list_ (function (lambda (a b) (< (nth val_ a) (nth val_ b))))))
              )
              (setq error_ "The number of val is less than list")
            )
          )
        ;
        ;basic_get_data_
          (setq acadObj (vlax-get-acad-object))
          (setq doc (vla-get-ActiveDocument acadObj))
          (setq modelSpace (vla-get-ModelSpace doc))
        ;
        ;advance_get_data
          ; (setq point_list_ (reverse (append (CO:sort_by_val_ 1 point_list_) (list (car point_list_)))))
          (setq point_list_ (append (CO:sort_by_val_ 1 point_list_) (list (car point_list_))))
        ;
        ;preloop_and_while sorting arc_line
          (setq angle_list_ ())
          (setq point_list_i 0)
          (setq point_list_ii 1)
          (while (< point_list_i (- (length point_list_) 1))
            (setq point_list_set_1 (nth point_list_i point_list_))
            (setq angle_ (atof (angtos (angle center_ point_list_set_1))))
            (setq sum (list
                        point_list_set_1
                        angle_
                      )
            )
            (setq angle_list_ (cons sum angle_list_))
            (setq point_list_i (+ point_list_i 1))
            (setq point_list_ii (+ point_list_ii 1))
          )
        ;
        (setq point_list_ (append (CO:sort_by_val_ 1 angle_list_) (list (car (CO:sort_by_val_ 1 angle_list_) ))) )
        (setq point_list_i 0)
        (setq point_list_ii 1)
        (while (< point_list_i (- (length point_list_) 1))
          (setq point_list_set_1 (car (nth point_list_i point_list_)))
          (setq point_list_set_2 (car (nth point_list_ii point_list_)))
          (setq start_ang_ (angle center_ point_list_set_1))
          (setq end_ang_ (angle center_ point_list_set_2))
          ; (setq rad_ (distance center_ point_list_set_1))
          
          (vla-addarc modelSpace (vlax-3d-point center_) rad_  start_ang_ end_ang_)
          (setq point_list_i (+ point_list_i 1))
          (setq point_list_ii (+ point_list_ii 1))
        )
        
      )
      (defun TA:vla-addarc_half_ (center_ rad_ point_list_ )
        ; point_list_ must be two coord set in list
        ; do not vlax-3d_point w/ agument
        ;sub_func_
          (defun CO:sort_by_val_ (val_ list_ )  ;เรียงชุดข้อมูลตามแนวแกน
            (if (< val_ (length (car list_)))
              (progn
                (setq sortedLst (vl-sort list_ (function (lambda (a b) (< (nth val_ a) (nth val_ b))))))
              )
              (setq error_ "The number of val is less than list")
            )
          )
        ;
        ;basic_get_data_
          (setq acadObj (vlax-get-acad-object))
          (setq doc (vla-get-ActiveDocument acadObj))
          (setq modelSpace (vla-get-ModelSpace doc))
        ;
        ;advance_get_data
          ; (setq point_list_ (reverse (append (CO:sort_by_val_ 1 point_list_) (list (car point_list_)))))
          (setq point_list_ (append (CO:sort_by_val_ 1 point_list_) (list (car point_list_))))
        ;
        ;preloop_and_while sorting arc_line
          (setq angle_list_ ())
          (setq point_list_i 0)
          (setq point_list_ii 1)
          (while (< point_list_i (- (length point_list_) 1))
            (setq point_list_set_1 (nth point_list_i point_list_))
            (setq angle_ (atof (angtos (angle center_ point_list_set_1))))
            (setq sum (list
                        point_list_set_1
                        angle_
                      )
            )
            (setq angle_list_ (cons sum angle_list_))
            (setq point_list_i (+ point_list_i 1))
            (setq point_list_ii (+ point_list_ii 1))
          )
        ;
        (setq point_list_ (append (CO:sort_by_val_ 1 angle_list_) (list (car (CO:sort_by_val_ 1 angle_list_) ))) )
        (setq point_list_i 0)
        (setq point_list_ii 1)
        (while (< point_list_i (- (length point_list_) 2))
          (setq point_list_set_1 (car (nth point_list_i point_list_)))
          (setq point_list_set_2 (car (nth point_list_ii point_list_)))
          (setq start_ang_ (angle center_ point_list_set_1))
          (setq end_ang_ (angle center_ point_list_set_2))
          ; (setq rad_ (distance center_ point_list_set_1))
          
          (vla-addarc modelSpace (vlax-3d-point center_) rad_  start_ang_ end_ang_)
          (setq point_list_i (+ point_list_i 1))
          (setq point_list_ii (+ point_list_ii 1))
        )
        
      )
      (defun TA:add_full_circle_ (center_pt radius)
        ;default adding VLA
          (setq acadObj (vlax-get-acad-object))
          (setq doc (vla-get-ActiveDocument acadObj))
          (setq modelSpace (vla-get-ModelSpace doc))
        ;
        ;vla-addcircle method
          (vla-addcircle modelSpace  
                        (vlax-3d-point center_pt) 
                        radius
          )
          (entlast)
        ;
      )
    ;
    ;add-point
      (defun vla-addpoint_ (point) 
        (setq acadObj (vlax-get-acad-object))
        (setq doc (vla-get-ActiveDocument acadObj))
        (setq modelSpace (vla-get-ModelSpace doc))
        (vla-addpoint modelSpace (vlax-3d-point point))
      )
    ;
    ;get_line
      (defun TA:Get_line_ins_point_ (ename_)
        
        ; (setq ename_ (car (entsel)))
        (setq ename_obj_ (vlax-ename->vla-object ename_))
        (setq ename_obj_str_pt_ (vlax-safearray->list (vlax-variant-value (vla-get-startpoint ename_obj_))))
        (setq ename_obj_end_pt_ (vlax-safearray->list (vlax-variant-value (vla-get-endpoint ename_obj_))))
        (setq sum_ (list
                    ename_obj_str_pt_
                    ename_obj_end_pt_
                  )
        )
      )
      
    ;
    ;offset
      (defun TA:Offset_line (ename num_ )
        ; (setq 1-PL_en_ (car (entsel)))
        (setq 1-PL_en_obj (vlax-ename->vla-object ename))
        (vla-Offset 1-PL_en_obj num_)
      )
      (defun TA:Offset_Pline_multi_vertex_ (ename num_ mode)
        ; ;for_testing_mode
        ;   (setq ename (car (entsel)))
        ;   (setq num_ 0.01)
        ;   (setq mode "min")
        ; ;
        ;test_vla-get-objectname_process
          (if (= (vla-get-objectname (vlax-ename->vla-object ename)) "AcDbPolyline")
            (progn
              (setq Get_Pline_ (entget ename))
              (setq Get_Pline_vtx_pt (vl-remove-if-not '(lambda (x) (= 10 (car x))) Get_Pline_))
              (setq Get_Pline_vtx_pt_ (mapcar 'cdr Get_Pline_vtx_pt))
            )
          )
        ;
        ;test_length_vertex_process
          (if 
            (and
              (= (vla-get-objectname (vlax-ename->vla-object ename)) "AcDbPolyline")
              (> (length Get_Pline_vtx_pt_) 2)
            )
            (progn
              (setq num_plus_ (* num_ 1))
              (setq num_minus_ (* num_ -1))
              (setq 1-PL_en_obj (vlax-ename->vla-object ename))
            )
            (princ "s")
          )
        ;
        ;plus mode process
          (if 
            (and
              (= (vla-get-objectname (vlax-ename->vla-object ename)) "AcDbPolyline")
              (> (length Get_Pline_vtx_pt_) 2)
            )
            (progn
              (setq result_num_plus_ ())
              (vla-Offset 1-PL_en_obj num_plus_)
              (setq num_plus_obj_ (entlast))
              (setq num_plus_area_ (vla-get-area (vlax-ename->vla-object num_plus_obj_)))
              (setq result_num_plus_ (cons num_plus_area_ result_num_plus_))
              (setq result_num_plus_ (cons num_plus_obj_ result_num_plus_))
            )
            (princ "s")
          )
        ;
        ;minus mode process
          (if 
            (and
              (= (vla-get-objectname (vlax-ename->vla-object ename)) "AcDbPolyline")
              (> (length Get_Pline_vtx_pt_) 2)
            )
            (progn
              (setq result_num_minus_ ())
              (vla-Offset 1-PL_en_obj num_minus_)
              (setq num_minus_obj_ (entlast))
              (setq num_minus_area_ (vla-get-area (vlax-ename->vla-object num_minus_obj_)))
              (setq result_num_minus_ (cons num_minus_area_ result_num_minus_))
              (setq result_num_minus_ (cons num_minus_obj_ result_num_minus_))
            )
            (princ "s")
          )
        ;
        ;result_data
          (setq resul_overall_ (append (list result_num_minus_) (list result_num_plus_)))
        ;
        (cond 
          ((and
            (= mode "max")
          )
          (progn
            (setq max_data_ (CO:sort_by_val_ 1 resul_overall_  ))
            (vla-delete (vlax-ename->vla-object (car (nth 0 max_data_))))
            (setq new_data_ (car (nth 1 max_data_)))
          )
          )
          ((= mode "min")
          (progn
            (setq min_data_ (reverse (CO:sort_by_val_ 1 resul_overall_  )))
            (vla-delete (vlax-ename->vla-object (car (nth 0 min_data_))))
            (setq new_data_ (car (nth 1 min_data_)))
            
          )
          )
          
        )
      )
      (defun TA:Offset_object_ ( input_object_ offset_distance_ offset_side_ / input_object_vla_ signed_distance_ offset_result_ )

        ;convert ENAME to VLA-OBJECT
        (setq input_object_vla_
          (cond
            (
              (= (type input_object_) 'ENAME)
              (vlax-ename->vla-object input_object_)
            )
            (
              (= (type input_object_) 'VLA-OBJECT)
              input_object_
            )
          )
        )

        ;calculate signed distance
        (setq signed_distance_
          (*
            (abs offset_distance_)
            (if (< offset_side_ 0)
              -1.0
              1.0
            )
          )
        )

        ;offset
        (if input_object_vla_
          (progn
            (setq offset_result_
              (vl-catch-all-apply
                (function
                  (lambda ()
                    (vlax-invoke
                      input_object_vla_
                      'Offset
                      signed_distance_
                    )
                  )
                )
              )
            )

            (if (vl-catch-all-error-p offset_result_)
              (progn
                (prompt
                  (strcat
                    "\nOffset Error: "
                    (vl-catch-all-error-message offset_result_)
                  )
                )
                (setq offset_result_ nil)
              )
            )
          )
        )

        offset_result_
        (entlast)
      )
      (defun c:MKAHP ()
        
        
        (_startundo doc)
        (setq mkahp_ename_ (ssname (ssget "i" '((0 . "LWPOLYLINE"))) 0))
        (setq mkahp_obj_ (vlax-ename->vla-object mkahp_ename_))
        
        (setq newline_front-ss_ (ssadd))
        (setq newline_mid-ss_ (ssadd))
        (setq newline_back-ss_ (ssadd))
        (setq newline_fold-ss_ (ssadd))
        
        (setq newline_front0 (vlax-vla-object->ename (vla-copy mkahp_obj_ )))
        (setq newline_front1 (TA:Offset_object_ mkahp_obj_ 0.8 1))
        (setq newline_front-ss_ (ssadd newline_front0 newline_front-ss_))
        (setq newline_front-ss_ (ssadd newline_front1 newline_front-ss_))
        (TA:joint_line_JOL newline_front-ss_)
        (vla-put-color (vlax-ename->vla-object (entlast)) 3)
        (vla-put-layer (vlax-ename->vla-object (entlast)) "010 - C07_PANEL_PANEL_CUT_COLOR_3")
        
        (setq newline_mid1 (TA:Offset_object_ mkahp_obj_ 0.8 1))
        (setq newline_mid2 (TA:Offset_object_ mkahp_obj_ 5.5 1))
        (setq newline_mid-ss_ (ssadd newline_mid1 newline_mid-ss_))
        (setq newline_mid-ss_ (ssadd newline_mid2 newline_mid-ss_))
        (TA:joint_line_JOL newline_mid-ss_)
        (vla-put-color (vlax-ename->vla-object (entlast)) 1)
        (vla-put-layer (vlax-ename->vla-object (entlast)) "010 - C07_PANEL_PANEL_CUT_COLOR_1")
        
        (setq newline_back1 (TA:Offset_object_ mkahp_obj_ 5.5 1))
        (setq newline_back2 (TA:Offset_object_ mkahp_obj_ 6 1))
        (setq newline_back-ss_ (ssadd newline_back1 newline_back-ss_))
        (setq newline_back-ss_ (ssadd newline_back2 newline_back-ss_))
        (TA:joint_line_JOL newline_back-ss_)
        (vla-put-color (vlax-ename->vla-object (entlast)) 3)
        (vla-put-layer (vlax-ename->vla-object (entlast)) "010 - C07_PANEL_PANEL_CUT_COLOR_3")
          ; (setq newline_fold1 (TA:Offset_object_ mkahp_obj_ 6 1))
          ; (setq newline_fold2 (TA:Offset_object_ mkahp_obj_ 20 1))
          ; (setq newline_fold-ss_ (ssadd newline_fold1 newline_fold-ss_))
          ; (setq newline_fold-ss_ (ssadd newline_fold2 newline_fold-ss_))
        
        (sslength newline_front-ss_ )



          ; (TA:joint_line_JOL newline_fold-ss_)
          ; (vla-put-color (vlax-ename->vla-object (entlast)) 1)
          
        (_endundo doc)
      )
      
    ;
  ;
  ;Block Editor_FUNC
    (defun TA:vla-insertblock (blockName insertion_point scale rotation)
      (setq acadApp (vlax-get-acad-object))  ; เข้าถึง AutoCAD application
      (setq doc (vla-get-ActiveDocument acadApp))
      (if (and 
            ; (= (getvar "ctab" ) "Model")
            (>= (getvar "cvport") 2)
          )
        (progn
          (setq ms (vla-get-ModelSpace doc))
        )
        (setq ms (vla-get-paperspace doc))
      )
        ; เข้าถึง Active Document
      
        ; เข้าถึง ModelSpace
      
      (setq block (vla-InsertBlock 
                    ms 
                    (vlax-3d-point insertion_point) 
                    blockName 
                    scale scale scale
                    rotation
                  )
      )  ; แทรกบล็อก
    )
    (defun TA:set-block-explodable (block-name allow-exploding) 
      ;example_using
      ;;allow-exploding = :vlax-true or :vlax-false
      ; (set-block-explodable "A$C5b7816c3" :vlax-true)
      ; (set-block-explodable "A$C5b7816c3" :vlax-false)
      ;
      ;for testing code
      ; (setq block-name "000 - DYNAMIC_COMBINE+VIEW_ASSCESSORIES_FAMELINE_GALV.BRACKET_FITTING_U-PROFILE_CC-01-4_COMBINE_VIEW" )
      ; (setq block-name "A$C60bdf5ac" )
      ; (setq block-name "A$C405762cd" )
      ; (setq allow-exploding :vlax-false )
      ; (setq allow-exploding :vlax-true )
      ;
      (setq doc (vla-get-ActiveDocument (vlax-get-acad-object)))
      (setq block-def (vla-Item (vla-get-Blocks doc) block-name))
      (vla-get-Explodable block-def)
      (if (/= block-def nil) 
        (progn 
          (vla-put-Explodable block-def :vlax-true)
          ; (vla-put-Explodable block-def :vlax-false)
        )
        (princ (strcat "\nBlock " block-name " not found."))
      )
    )
    (defun c:allow_explode_block_ALEX ()
      (setq blk_ename_ (car (entsel "specify Object")))
      (setq blk_obj_ (vlax-ename->vla-object blk_ename_))
      (setq ef_name (LM:effectivename blk_obj_))
      (TA:set-block-explodable ef_name :vlax-true)
    )
    (defun TA:set-block-blockscaling (block-name parameter)
      ;example_using
        ;;parameter = acAny or acUniform
        ; (set-block-explodable "A$C5b7816c3" acAny)
        ; (set-block-explodable "A$C5b7816c3" acUniform)
      ;
      (setq doc (vla-get-ActiveDocument (vlax-get-acad-object)))
      (setq block-def (vla-Item (vla-get-Blocks doc) block-name))
      (if block-def
        (vla-put-blockscaling block-def parameter)
        (princ (strcat "\nBlock " block-name " not found."))
      )
    )
    (defun c:ADD_VISIBILITY_multi-mode_ADVSM_ ()
      (setq input_ins_ (getpoint ))
      (setq name_vis_ "view")
      (command "BPARAMETER" "v" "L" name_vis_ input_ins_ 1)
      (command "-Bvstate" "s" "VisibilityState0")
      ;preloop_and_while_ 
      (setq visibility_screw_mode_                    "1 = screw_mode") 
      (setq visibility_view_mode_                     "2 = front_top_side_cut_mode") 
      (setq visibility_number_mode_                   "3 = number_mode") 
      (setq visibility_AL.EXTR-U-Profile_mode_        "4 = AL.EXTR-U-Profile_mode")
      (setq visibility_copy_mode_                     "5 = copy visibility from another dynamic block")
      (setq visibility_copy_mode_                     "6 = Hex bolt ")
      (setq visibility_cutting_plan_mode_             "7 = Cutting Plan ")
      
      (setq visibility_mode_value_ (cond ((getint (strcat visibility_screw_mode_"\n"visibility_view_mode_"\n"visibility_number_mode_"\n"visibility_AL.EXTR-U-Profile_mode_"\n" visibility_copy_mode_"\n" visibility_cutting_plan_mode_ "\n" "<" (rtos (setq visibility_mode_value_ (cond (visibility_mode_value_) (1.0) ) ) ) "> : " ) ) ) (visibility_mode_value_) ) )
      ;Data_visibiity_list_normie_mode_
        (cond
          (;visibility_mode_case_1
            (and
                (= visibility_mode_value_ 1)
            )
            (progn
                (setq visibility_list_ (list
                                        "0_iso_view"
                                        "1_top_view"
                                        "2_side_head"
                                        "3_side_view_19mm."
                                        "4_side_view_25mm."
                                        "5_side_view_50mm."
                                        "6_side_view_75mm."
                                        "7_side_view_100mm."
                                      )
                )
                (princ "visibility_mode_case_1")
            )
          )
          (;visibility_mode_case_2
            (and
                (= visibility_mode_value_ 2) 
            )
            (progn
                (setq visibility_list_ (list
                                        "0_iso_view"
                                        "1_cut_view"
                                        "2_top_view"
                                        "3_front_view"
                                        "4_side_L_view"
                                        "4_side_R_view"
                                        "5_back_view"
                                        "6_bottom_view"
                                        "7_dynamic_length_view"
                                      )
                )
                (princ "visibility_mode_case_2")
            )
          )
          (;visibility_mode_case_3
            (and
                (= visibility_mode_value_ 3)
            )
            (progn
                (setq visibility_list_ (list
                                       "1_"
                                       "2_"
                                       "3_"
                                       "4_"
                                       "5_"
                                       "6_"
                                       "7_"
                                       "8_"
                                       "9_"
                                       "10_"
                                       "11_"
                                       "12_"
                                       "13_"
                                       "14_"
                                       "15_"
                                       "16_"
                                       "17_"
                                       "18_"
                                       "19_"
                                       "20_"
                                       "21_"
                                       "22_"
                                       "23_"
                                       "24_"
                                       "25_"
                                       "26_" 
                                      )
                )
                
                (princ "visibility_mode_case_3")
            )
          )
          (;visibility_mode_case_4
            (and
                (= visibility_mode_value_ 4)
            )
            (progn
                (setq visibility_list_ (list
                                        "1_cut_view_covering_profile"
                                        "2_top_view"
                                        "3_front_view"
                                        "4_side_L_view"
                                        "4_side_R_view"
                                        "5_back_view"
                                        "6_bottom_view"
                                        "7_dynamic_length_view"
                                      )
                )
                (princ "visibility_mode_case_4")
            )
          )
          (;visibility_mode_case_6
            (and
                (= visibility_mode_value_ 6)
            )
            (progn
                (setq visibility_list_ (list
                                        "top_view"
                                        "hex-nut"
                                        "x8mm."
                                        "x10mm."
                                        "x12mm."
                                        "x14mm."
                                        "x15mm."
                                        "x20mm."
                                        "x25mm."
                                        "x30mm."
                                        "x40mm."
                                        "x45mm."
                                        "x50mm."
                                        "x55mm."
                                        "x60mm."
                                        "x65mm."
                                        "x70mm."
                                        "x75mm."
                                        "x80mm."
                                        "x90mm."
                                        "x100mm."
                                      )
                )
                (princ "visibility_mode_case_6")
            )
          )
          (;visibility_mode_case_6
            (and
                (= visibility_mode_value_ 7)
            )
            (progn
                (setq visibility_list_ (list
                                        "NORMAL"
                                        "FOLDING_LINE"
                                        "CUTTING_LINE"
                                      )
                )
                (princ "visibility_mode_case_7")
            )
          )
        )
      ;
      ;visibility_copy_mode_[visibility_copy_mode_
        (if (and (/= visibility_mode_value_ 5) (numberp visibility_mode_value_))
          (progn
            (setq visibility_list_i 0)
            (while (< visibility_list_i (length visibility_list_))
              (setq visibility_list_SEQ (nth visibility_list_i visibility_list_))
              (command "-Bvstate" "n" visibility_list_SEQ "c" )
              (setq visibility_list_i (+ visibility_list_i 1))
            )
          )
          (if (and (= visibility_mode_value_ 5) (numberp visibility_mode_value_))
            (progn          
              (command "_bclose" "s")
              ;while_select_block_on_condition_
                (setq visibility_list_ nil)
                (while (= visibility_list_ nil)
                  (setq vis_ename_ (car (entsel "specify Visibility Object")))
                  (if 
                    (and ;conditional_rule_for_select_object_
                      (/= vis_ename_ nil)
                      (setq vis_obj_ (vlax-ename->vla-object vis_ename_))
                      (= (vla-get-objectname vis_obj_ ) "AcDbBlockReference")
                      (= (vla-get-isdynamicblock vis_obj_ ) :vlax-true)
                      (/= (LM:getdynpropallowedvalues vis_obj_ "view") nil)
                    )
                    (progn
                      (setq visibility_list_ (LM:removenth 0 (LM:getdynpropallowedvalues vis_obj_ "view")) )
                    )
                    (alert "Object invalid Please try again")
                  )
                )
                (setq block_target_ename_ nil)
                (while (= block_target_ename_ nil)
                  (setq block_target_ename_ (car (entsel "specify block_target_ename_ Object")))
                  (if 
                    (and ;conditional_rule_for_select_object_
                      (/= block_target_ename_ nil)
                      (setq block_target_obj_ (vlax-ename->vla-object block_target_ename_))
                      (= (vla-get-objectname block_target_obj_ ) "AcDbBlockReference")
                    )
                    (progn
                      (setq block_target_obj_efname_ (LM:Effectivename block_target_obj_))
                      (command "_bedit" block_target_obj_efname_)
                      (setq visibility_list_i 0)
                      (while (< visibility_list_i (length visibility_list_))
                        (setq visibility_list_SEQ (nth visibility_list_i visibility_list_))
                        (command "-Bvstate" "n" visibility_list_SEQ "c" )
                        (setq visibility_list_i (+ visibility_list_i 1))
                      )
                    )
                    (alert "Object invalid Please try again")
                  )
                )
              ;
            )
          )
        )
      ;  
      ; ;reture_visibility_to_defuat
        (command "-Bvstate" "s" "VisibilityState0"  )
        (command "BVHIDE" (ssget "x") "" "A" )
        (setvar "BVMODE" 1)
        (command "BVSHOW" (ssget "x") "" "C" )
      ;      
    )
    (defun c:dyanamic_rename_array_REAR ()
      (setq BPARAMETER_ename_ (car (entsel "specify Object")))
      (if (/= BPARAMETER_ename_ nil)
        (progn
          (setq BPARAMETER_obj_ (vlax-ename->vla-object BPARAMETER_ename_))
          (vlax-get-property BPARAMETER_obj_ "DistName" )
          (vlax-put-property BPARAMETER_obj_ "DistName" "array_width")
          (vlax-put-property BPARAMETER_obj_ "Grips" 1)
        )
        (setq BPARAMETER_ename_ nil)
      )
      
    )
    (defun c:dynamic_rewidth_array_1_rew1 ()
      ;user_input_
        (setq user_num_ (getreal "specify_num_for_array_width"))
      ;
      ;selection_set
        (setq ss_pre_filter_set_xx_ (ssget "x" 
                                          ; (list 
                                          ;   (cons 0 "INSERT") ;type of object
                                          ;   ; (cons 8 "000 - GRID")   ;kind of layer
                                          ;   ; (cons 2 "000-GRID_LINE_DYN")       ;kind of nameblock
                                          ;   ; (cons 62 1)           ;kind of color call sign with color code index
                                          ; )
                                  )
        )
        (sslength ss_pre_filter_set_xx_)
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_hon_objname_ (vla-get-objectname (vlax-ename->vla-object ss_pre_filter_set_xx_ename_)))
          ; (setq ss_pre_filter_set_xx_i (+ ss_pre_filter_set_xx_i 1))
          ; (TA:dump_obj_ ss_pre_filter_set_xx_ename_)
          
          ;ColumnOffset process
            (if 
              (and
                (= (setq ss_pre_filter_set_xx_hon_objname_ (vla-get-objectname (vlax-ename->vla-object ss_pre_filter_set_xx_ename_))) "AcDbBlockArrayActionEntity")
                (= (strcase (vlax-get-property (vlax-ename->vla-object ss_pre_filter_set_xx_ename_) "ActionType" )) "ARRAY")
                (= (strcase (setq ss_pre_filter_set_xx_name_ (vla-get-name (vlax-ename->vla-object ss_pre_filter_set_xx_ename_)))) "ARRAY_MAIN")
              )
              (progn
                (vlax-put-property (vlax-ename->vla-object ss_pre_filter_set_xx_ename_) "ColumnOffset" user_num_ )
              )
            )
          ;
          ;array_width process
            (if 
              (and
                (= (setq ss_pre_filter_set_xx_hon_objname_ (vla-get-objectname (vlax-ename->vla-object ss_pre_filter_set_xx_ename_))) "AcDbBlockLinearParameterEntity")  
                (= (vlax-get-property (vlax-ename->vla-object ss_pre_filter_set_xx_ename_) "DistName" ) "array_width")        
              )
              (progn
                (setq basepoint_edit_ (list 
                                        (* (/ user_num_ 2) -1)
                                        (cadr (vlax-safearray->list (vlax-variant-value (vlax-get-property (vlax-ename->vla-object ss_pre_filter_set_xx_ename_) "BasePoint" )))) 
                                        (caddr (vlax-safearray->list (vlax-variant-value (vlax-get-property (vlax-ename->vla-object ss_pre_filter_set_xx_ename_) "BasePoint" )))) 
                                      )
                )
                (setq endpoint_edit_ (list 
                                        (* (/ user_num_ 2) 1)
                                        (cadr (vlax-safearray->list (vlax-variant-value (vlax-get-property (vlax-ename->vla-object ss_pre_filter_set_xx_ename_) "endpoint" )))) 
                                        (caddr (vlax-safearray->list (vlax-variant-value (vlax-get-property (vlax-ename->vla-object ss_pre_filter_set_xx_ename_) "endpoint" )))) 
                                      )
                )
                
                
                (vlax-put-property (vlax-ename->vla-object ss_pre_filter_set_xx_ename_) "BasePoint" (vlax-3d-point basepoint_edit_) )
                (vlax-put-property (vlax-ename->vla-object ss_pre_filter_set_xx_ename_) "EndPoint" (vlax-3d-point endpoint_edit_) )
                
                (vlax-put-property (vlax-ename->vla-object ss_pre_filter_set_xx_ename_) "ValueSetIncrement" user_num_ )
                
                (setq Parameter_name_ (vla-get-name (vlax-ename->vla-object ss_pre_filter_set_xx_ename_)  ))
              )
            )
          ;
          ;array_grip_process
            (if 
              (and
                (= (setq ss_pre_filter_set_xx_hon_objname_ (vla-get-objectname (vlax-ename->vla-object ss_pre_filter_set_xx_ename_))) "AcDbBlockLinearGripEntity")  
                (= (vlax-get-property (vlax-ename->vla-object ss_pre_filter_set_xx_ename_) "ParameterName" ) Parameter_name_)        
              )
              (progn
                
                (setq position_edit_ (list 
                                        (* (/ user_num_ 2) 1)
                                        (cadr (vlax-safearray->list (vlax-variant-value (vlax-get-property (vlax-ename->vla-object ss_pre_filter_set_xx_ename_) "Position" )))) 
                                        (caddr (vlax-safearray->list (vlax-variant-value (vlax-get-property (vlax-ename->vla-object ss_pre_filter_set_xx_ename_) "Position" )))) 
                                      )
                )
                
                
                (vlax-put-property (vlax-ename->vla-object ss_pre_filter_set_xx_ename_) "Position" (vlax-3d-point position_edit_) )
                
              )
            )
          ;
          
          
          
          (setq ss_pre_filter_set_xx_i (+ ss_pre_filter_set_xx_i 1))
        )
      ;
    )
    (defun c:dynamic_rewidth_array_2_rew2_ ()
      ;user_input_
        (setq user_num_ (getreal "specify_num_for_array_width"))
      ;
      ;selection_set
        (setq ss_pre_filter_set_xx_ (ssget "x" 
                                          ; (list 
                                          ;   (cons 0 "INSERT") ;type of object
                                          ;   ; (cons 8 "000 - GRID")   ;kind of layer
                                          ;   ; (cons 2 "000-GRID_LINE_DYN")       ;kind of nameblock
                                          ;   ; (cons 62 1)           ;kind of color call sign with color code index
                                          ; )
                                  )
        )
        (sslength ss_pre_filter_set_xx_)
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_hon_objname_ (vla-get-objectname (vlax-ename->vla-object ss_pre_filter_set_xx_ename_)))
          ; (setq ss_pre_filter_set_xx_i (+ ss_pre_filter_set_xx_i 1))
          ; (TA:dump_obj_ ss_pre_filter_set_xx_ename_)
          
          ;ColumnOffset process
            (if 
              (and
                (= (setq ss_pre_filter_set_xx_hon_objname_ (vla-get-objectname (vlax-ename->vla-object ss_pre_filter_set_xx_ename_))) "AcDbBlockArrayActionEntity")
                (= (strcase (vlax-get-property (vlax-ename->vla-object ss_pre_filter_set_xx_ename_) "ActionType" )) "ARRAY")
                (= (strcase (setq ss_pre_filter_set_xx_name_ (vla-get-name (vlax-ename->vla-object ss_pre_filter_set_xx_ename_)))) "ARRAY_MAIN")
              )
              (progn
                (vlax-put-property (vlax-ename->vla-object ss_pre_filter_set_xx_ename_) "ColumnOffset" user_num_ )
              )
            )
          ;
          ;array_width process
            (if 
              (and
                (= (setq ss_pre_filter_set_xx_hon_objname_ (vla-get-objectname (vlax-ename->vla-object ss_pre_filter_set_xx_ename_))) "AcDbBlockLinearParameterEntity")  
                (= (vlax-get-property (vlax-ename->vla-object ss_pre_filter_set_xx_ename_) "DistName" ) "array_width")        
              )
              (progn
                (setq basepoint_edit_ (list 
                                        0 ;(* (/ user_num_ 2) -1)
                                        (cadr (vlax-safearray->list (vlax-variant-value (vlax-get-property (vlax-ename->vla-object ss_pre_filter_set_xx_ename_) "BasePoint" )))) 
                                        (caddr (vlax-safearray->list (vlax-variant-value (vlax-get-property (vlax-ename->vla-object ss_pre_filter_set_xx_ename_) "BasePoint" )))) 
                                      )
                )
                (setq endpoint_edit_ (list 
                                        (* user_num_ 1)
                                        (cadr (vlax-safearray->list (vlax-variant-value (vlax-get-property (vlax-ename->vla-object ss_pre_filter_set_xx_ename_) "endpoint" )))) 
                                        (caddr (vlax-safearray->list (vlax-variant-value (vlax-get-property (vlax-ename->vla-object ss_pre_filter_set_xx_ename_) "endpoint" )))) 
                                      )
                )
                
                
                (vlax-put-property (vlax-ename->vla-object ss_pre_filter_set_xx_ename_) "BasePoint" (vlax-3d-point basepoint_edit_) )
                (vlax-put-property (vlax-ename->vla-object ss_pre_filter_set_xx_ename_) "EndPoint" (vlax-3d-point endpoint_edit_) )
                
                (vlax-put-property (vlax-ename->vla-object ss_pre_filter_set_xx_ename_) "ValueSetIncrement" user_num_ )
                
                (setq Parameter_name_ (vla-get-name (vlax-ename->vla-object ss_pre_filter_set_xx_ename_)  ))
              )
            )
          ;
          ;array_grip_process
            (if 
              (and
                (= (setq ss_pre_filter_set_xx_hon_objname_ (vla-get-objectname (vlax-ename->vla-object ss_pre_filter_set_xx_ename_))) "AcDbBlockLinearGripEntity")  
                (= (vlax-get-property (vlax-ename->vla-object ss_pre_filter_set_xx_ename_) "ParameterName" ) Parameter_name_)        
              )
              (progn
                
                (setq position_edit_ (list 
                                        0 ;(* user_num_ 1) ;incase if i need arrow at the endpoint by TA:Trairat
                                        (cadr (vlax-safearray->list (vlax-variant-value (vlax-get-property (vlax-ename->vla-object ss_pre_filter_set_xx_ename_) "Position" )))) 
                                        (caddr (vlax-safearray->list (vlax-variant-value (vlax-get-property (vlax-ename->vla-object ss_pre_filter_set_xx_ename_) "Position" )))) 
                                      )
                )
                
                
                (vlax-put-property (vlax-ename->vla-object ss_pre_filter_set_xx_ename_) "Position" (vlax-3d-point position_edit_) )
                
              )
            )
          ;
          
          
          
          (setq ss_pre_filter_set_xx_i (+ ss_pre_filter_set_xx_i 1))
        )
      ;
    )
    (defun c:dynamic_ARsaveas_array_()
      ;user_input_
        ; (setq user_num_ (getreal "specify_num_for_array_width"))
      ;
      ;selection_set
        (setq ss_pre_filter_set_xx_ (ssget "x"
                                          ; (list 
                                          ;   (cons 0 "INSERT") ;type of object
                                          ;   ; (cons 8 "000 - GRID")   ;kind of layer
                                          ;   ; (cons 2 "000-GRID_LINE_DYN")       ;kind of nameblock
                                          ;   ; (cons 62 1)           ;kind of color call sign with color code index
                                          ; )
                                  )
        )
        (sslength ss_pre_filter_set_xx_)
      ;
      (setq ss_pre_filter_set_xx_ (ssget)) ;test
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_hon_objname_ (vla-get-objectname (vlax-ename->vla-object ss_pre_filter_set_xx_ename_)))
          ; (setq ss_pre_filter_set_xx_i (+ ss_pre_filter_set_xx_i 1))
          ; (TA:dump_obj_ ss_pre_filter_set_xx_ename_)
          ;
          ;array_width process
            (if 
              (and
                (= (setq ss_pre_filter_set_xx_hon_objname_ (vla-get-objectname (vlax-ename->vla-object ss_pre_filter_set_xx_ename_))) "AcDbBlockLinearParameterEntity")  
                (= (vlax-get-property (vlax-ename->vla-object ss_pre_filter_set_xx_ename_) "DistName" ) "array_width")        
                (/= (vlax-get-property (vlax-ename->vla-object ss_pre_filter_set_xx_ename_) "DistanceDesc" ) "")        
              )
              (progn
                ;saveas new block name process
                  (setq name_block_ (vlax-get-property (vlax-ename->vla-object ss_pre_filter_set_xx_ename_) "DistanceDesc" ))
                  (setq check_2 (vl-string-search "@" name_block_  1))
                  (setq check_22 (substr name_block_ (+ check_2 1) 8))
                  (setq check_222 (vl-string-search "mm." check_22  1))
                  (setq check_2222 (substr check_22 1 check_222))

                  (setq check_1 nil )
                  (setq new_efname_ "ZOO" )
                  (setq get_array_distance (vlax-get-property (vlax-ename->vla-object ss_pre_filter_set_xx_ename_) "Distance" ))
                  (setq i 1)
                  (while
                    (and
                      (/= (type check_1) 'INT)
                      
                      
                      ; (< i (strlen name_block_ ))
                    )
                    (if (/= (vl-string-search "@" name_block_  1) "m")
                      (progn
                        (setq new_efname_ (strcat (substr name_block_ 1 i)))
                        (setq check_1 (vl-string-search "@" new_efname_  1))
                        
                        
                        ; (setq new_efname_1 (strcat (substr name_block_ 26 1)))
                      )
                    )
                    (setq i (+ i 1))
                  )
                  (setq new_efname_val (strcat (substr new_efname_  (strlen new_efname_) 5 ) (rtos get_array_distance 2 0)))
                  (setq new_name_block_ (LM:StringSubst 
                                          new_efname_val 
                                          check_2222 
                                          name_block_ 
                                        )
                  )
                
                  (command "bsaveas" new_name_block_ )
                  (command "_bclose" )
                ;
                ;insertion_block_process_
                  (setq new_block_name new_name_block_  )
                  (TA:set-block-blockscaling new_block_name acUniform)
                  (setq getpoint_ (getpoint))
                  (command "insert" new_block_name  getpoint_ 1 0 )
                ;
                
              )
            )
          ;
          (setq ss_pre_filter_set_xx_i (+ ss_pre_filter_set_xx_i 1))
        )
      ;
    )
    (defun c:dynamic_ARsaveas_array_and_insert_arsins()
      ;user_input_
        ; (setq user_num_ (getreal "specify_num_for_array_width"))
      ;
      ;selection_set
        (setq ss_pre_filter_set_xx_ (ssget "x"
                                          ; (list 
                                          ;   (cons 0 "INSERT") ;type of object
                                          ;   ; (cons 8 "000 - GRID")   ;kind of layer
                                          ;   ; (cons 2 "000-GRID_LINE_DYN")       ;kind of nameblock
                                          ;   ; (cons 62 1)           ;kind of color call sign with color code index
                                          ; )
                                  )
        )
        (sslength ss_pre_filter_set_xx_)
      ;
      (setq ss_pre_filter_set_xx_ (ssget)) ;test
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_hon_objname_ (vla-get-objectname (vlax-ename->vla-object ss_pre_filter_set_xx_ename_)))
          ; (setq ss_pre_filter_set_xx_i (+ ss_pre_filter_set_xx_i 1))
          ; (TA:dump_obj_ ss_pre_filter_set_xx_ename_)
          ;
          ;array_width process
            (if 
              (and
                (= (setq ss_pre_filter_set_xx_hon_objname_ (vla-get-objectname (vlax-ename->vla-object ss_pre_filter_set_xx_ename_))) "AcDbBlockLinearParameterEntity")  
                (= (vlax-get-property (vlax-ename->vla-object ss_pre_filter_set_xx_ename_) "DistName" ) "array_width")        
                (/= (vlax-get-property (vlax-ename->vla-object ss_pre_filter_set_xx_ename_) "DistanceDesc" ) "")        
              )
              (progn
                ;saveas new block name process
                  (setq name_block_ (vlax-get-property (vlax-ename->vla-object ss_pre_filter_set_xx_ename_) "DistanceDesc" ))
                  (setq check_2 (vl-string-search "@" name_block_  1))
                  (setq check_22 (substr name_block_ (+ check_2 1) 8))
                  (setq check_222 (vl-string-search "mm." check_22  1))
                  (setq check_2222 (substr check_22 1 check_222))

                  (setq check_1 nil )
                  (setq new_efname_ "ZOO" )
                  (setq get_array_distance (vlax-get-property (vlax-ename->vla-object ss_pre_filter_set_xx_ename_) "Distance" ))
                  (setq i 1)
                  (while
                    (and
                      (/= (type check_1) 'INT)
                      
                      
                      ; (< i (strlen name_block_ ))
                    )
                    (if (/= (vl-string-search "@" name_block_  1) "m")
                      (progn
                        (setq new_efname_ (strcat (substr name_block_ 1 i)))
                        (setq check_1 (vl-string-search "@" new_efname_  1))
                        
                        
                        ; (setq new_efname_1 (strcat (substr name_block_ 26 1)))
                      )
                    )
                    (setq i (+ i 1))
                  )
                  (setq new_efname_val (strcat (substr new_efname_  (strlen new_efname_) 5 ) (rtos get_array_distance 2 0)))
                  (setq new_name_block_ (LM:StringSubst 
                                          new_efname_val 
                                          check_2222 
                                          name_block_ 
                                        )
                  )
                
                  (command "bsaveas" new_name_block_ )
                  (command "_bclose" )
                ;
                ;insertion_block_process_
                  (setq new_block_name new_name_block_  )
                  (TA:set-block-blockscaling new_block_name acUniform)
                  (setq replace_ename_ (car (entsel "specify Object")))
                  (setq replace_obj_ (vlax-ename->vla-object replace_ename_))
                  (if (= (vla-get-objectname replace_obj_) "AcDbBlockReference")
                    (progn
                      (setq replace_obj_ins_ (vlax-safearray->list (vlax-variant-value (vla-get-insertionpoint replace_obj_))))
                      (setq replace_obj_dynlist_ (LM:getdynprops replace_obj_))
                      (setq replace_obj_rotation_ (rad-to-deg (vla-get-rotation replace_obj_)) )
                    )
                  )
                  (command "insert" new_block_name  replace_obj_ins_ 0.001 replace_obj_rotation_ )
                  (setq newblk_dyn_ename_ (entlast))
                  (setq  newblk_dyn_obj_ (vlax-ename->vla-object  newblk_dyn_ename_))
                  ;preloop_and_while
                    (setq replace_obj_dynlist_i 0)
                    (while (< replace_obj_dynlist_i (length replace_obj_dynlist_))
                      (setq replace_obj_dynlist_val_1 (car (nth  replace_obj_dynlist_i replace_obj_dynlist_)))
                      (setq replace_obj_dynlist_val_2 (cdr (nth  replace_obj_dynlist_i replace_obj_dynlist_)))
                      (if (and
                            (= (wcmatch replace_obj_dynlist_val_1 "Origin") nil)
                          )
                        (progn
                          (LM:setdynpropvalue newblk_dyn_obj_ replace_obj_dynlist_val_1 replace_obj_dynlist_val_2 )
                        )
                      )
                      
                      (setq replace_obj_dynlist_i (+ replace_obj_dynlist_i 1))
                    )
                  ;
                  (vla-delete replace_obj_)

                ;
                
              )
            )
          ;
          (setq ss_pre_filter_set_xx_i (+ ss_pre_filter_set_xx_i 1))
        )
      ;
    )
    (defun c:BasePoint_to_BasePoint_[B2B] ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget 
                                          (list
                                            (cons 0 "INSERT") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      
      ;fillter_main_point_name_object_
      (setq main_point_ename_ERR_CHECK ;Detect the variable's result in case of a function error
        (vl-catch-all-apply 
          (function 
            (lambda () 
              (setq main_point_ename_ "No Selection BLock object")
              (while (= main_point_ename_ "No Selection BLock object")
                ;user_input_data
                  (setq main_point_ename_ (car (entsel "specify Base Point Block Object")))
                ;
                ;fillter_object_type_
                  (if 
                    (and
                      (if (/= main_point_ename_ nil) (progn (setq main_point_obj_ (vlax-ename->vla-object main_point_ename_)) ))
                        (= (vla-get-objectname main_point_obj_) "AcDbBlockReference")
                      )
                    (progn
                      (setq main_point_obj_ins_ (vlax-safearray->list (vlax-variant-value (vla-get-insertionpoint main_point_obj_))))
                    )
                    (setq main_point_ename_ nil)
                  )
                  (if
                    (or
                      (= main_point_ename_ nil)
                      (/= (vla-get-objectname main_point_obj_) "AcDbBlockReference")
                      
                    )
                    (progn
                      (= main_point_ename_ nil)
                      (alert "No selection Block object")
                    )
                  )
                ;
              )
            )
          )
        )
      )
      (if (vl-catch-all-error-p main_point_ename_ERR_CHECK)
        (progn
          (setq detect_error_main_point_ename_ ;Detect the variable's result in case of a function error
            (wcmatch
              (strcase
                (vl-catch-all-error-message
                  main_point_ename_detect_error
                )
              )
              "FUNCTION*,*ERROR*"
            )
          )
        )
        (setq detect_error_main_point_ename_ nil)
      )
      
      ;
      ;user_input_insertionpoint_for_move
        (setq user_input_ins_point_ERR_CHECK nil)
        (setq main_point_ename_ nil)
        (while 
          (and 
            (= main_point_ename_ nil)
            (= user_input_ins_point_ERR_CHECK nil)
          )
          (setq user_input_ins_point_ERR_CHECK ;Detect the variable's result in case of a function error
            (vl-catch-all-apply 
              (function 
                (lambda () 
                  (setq user_input_ins_point_ (getpoint "specify getpoint for new insertionpoint"))
                )
              )
            )
          )
          (cond
            (;blank_case_1
              (and
                (= user_input_ins_point_ERR_CHECK nil)
                (= user_input_ins_point_ nil)
              )
              (progn
                (setq main_point_ename_ nil)
                (setq user_input_ins_point_ERR_CHECK nil)
                (alert "Please selection insertionpoint for move")
                (princ "blank_case_1")
              )
            )
            (;blank_case_2
              (and
                (vl-catch-all-error-p user_input_ins_point_ERR_CHECK)
                (= user_input_ins_point_ nil)
              )
              (progn
                (setq main_point_ename_ nil)
                (setq user_input_ins_point_ERR_CHECK nil)
                (alert "Please selection insertionpoint for move")
                (princ "blank_case_2")
              )
            )
            (;have_Inspt
              (and 
                (= (numberp (car user_input_ins_point_)) T)
                (= (numberp (cadr user_input_ins_point_)) T)
              )
              (progn
                (setq main_point_ename_ "no block object")
                (princ "have_Inspt")
              )
            )
          )
          
        )
        (if 
          (and
            (= user_input_ins_point_ nil)
            (vl-catch-all-error-p user_input_ins_point_ERR_CHECK )
          )
          (progn
            (setq detect_error_user_input_ins_point_ ;Detect the variable's result in case of a function error
              (wcmatch
                (strcase
                  (vl-catch-all-error-message
                    user_input_ins_point_ERR_CHECK
                  )
                )
                "FUNCTION*,*ERROR*,*NIL*"
              )
            )
          )
        )
      ;
      ;main_idea_code
        ;preloop_and_while
          (setq ss_pre_filter_set_xx_i 0)
          (setvar "osmode" 0)
          (while (< ss_pre_filter_set_xx_i (sslength ss_pre_filter_set_xx_))
            (setq ss_pre_filter_set_xx_ename_ (ssname ss_pre_filter_set_xx_ ss_pre_filter_set_xx_i))
            ;main_idea
              ;getins_data
              (setq ss_pre_filter_set_xx_hon_obj_ (vlax-ename->vla-object ss_pre_filter_set_xx_ename_))
              (setq ss_pre_filter_set_xx_hon_obj_ins_ (vlax-safearray->list (vlax-variant-value (vla-get-insertionpoint ss_pre_filter_set_xx_hon_obj_))))
              ;
              ;put_move_data
              (cond
                (;user_input_ins_case_1
                  (and
                      (= (numberp (car user_input_ins_point_)) T)
                      (= (numberp (cadr user_input_ins_point_)) T)
                  )
                  (progn
                    (vla-move ss_pre_filter_set_xx_hon_obj_ 
                              (vlax-3d-point ss_pre_filter_set_xx_hon_obj_ins_)
                              (vlax-3d-point user_input_ins_point_)
                    )
                    (princ "useinput_ins_case_1")
                  )
                )
                (;Block_ins_case_2
                  (and 
                    (= user_input_ins_point_ nil)
                    (= detect_error_user_input_ins_point_ T)
                  )
                  (progn  ;move to ins main block
                          (vla-move ss_pre_filter_set_xx_hon_obj_ 
                                    (vlax-3d-point ss_pre_filter_set_xx_hon_obj_ins_)
                                    (vlax-3d-point main_point_obj_ins_)
                          )
                          (setq user_input_ins_point_ nil)
                          (princ "useinput_ins_case_2")
                  )
                )
              )
              
                
              ;
            ;
            (setq ss_pre_filter_set_xx_i (+ ss_pre_filter_set_xx_i 1))
          )
          (setvar "osmode" 1215)
        ;
      ;
    )
    (defun c:Replace_block_object_Reblock ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget 
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;specify_object_for_filter_by_EFname_
        (setq Filter_target_ename_ (car (entsel "specify TA:EF_Filter_ss_set_ Object")))
        (setq Filter_target_obj_ (vlax-ename->vla-object Filter_target_ename_))
        (setq Filter_target_obj_EFname_ (LM:effectivename Filter_target_obj_))
        (setq ss_post_filter_set_xx_ (TA:EF_Filter_ss_set_ ss_pre_filter_set_xx_ Filter_target_obj_EFname_))
      ;
      ;insert_target_object_process_
        (setq insert_target_ename_ (car (entsel "specify insert_target_ename_  Object")))
        (setq insert_target_obj_ (vlax-ename->vla-object insert_target_ename_))
        (setq insert_target_obj_EFname_ (LM:effectivename insert_target_obj_))
      ;
      ;preloop_and_while
        (setq ss_post_filter_set_xx_i 0)
        (setq ss_newset_ (ssadd))
        ; (sslength ss_newset)
        (while (< ss_post_filter_set_xx_i (sslength ss_post_filter_set_xx_))
          (setq ss_post_filter_set_xx_ename_ (ssname ss_post_filter_set_xx_ ss_post_filter_set_xx_i))
            (setq ss_post_filter_set_xx_hon_obj_ (vlax-ename->vla-object ss_post_filter_set_xx_ename_))
              (setq ss_post_filter_set_xx_hon_obj_ins_ (vlax-safearray->list (vlax-variant-value (vla-get-insertionpoint ss_post_filter_set_xx_hon_obj_))))
              (setq ss_post_filter_set_xx_hon_obj_ro_ (vla-get-rotation ss_post_filter_set_xx_hon_obj_))
              (setvar "osmode" 0)
              (TA:vla-insertblock insert_target_obj_EFname_ ss_post_filter_set_xx_hon_obj_ins_ 1 ss_post_filter_set_xx_hon_obj_ro_ )
              (vla-delete ss_post_filter_set_xx_hon_obj_ )
              (setq new_obj_ (entlast ))
              (setq ss_newset_ (ssadd new_obj_ ss_newset_))
          
          (setq ss_post_filter_set_xx_i (+ ss_post_filter_set_xx_i 1))
        )
      ;

      ;preloop_and_while
        ;while_select_block_on_condition_
          ;first_cond_for_while_loop_input
            (setq getRO_ ;Detect the variable's result in case of a function error
              (vl-catch-all-apply 
                (function 
                  (lambda () 
                    (setq getRO_RO_ (cond ( (getint (strcat "\nspecify get rotation\n<" (rtos (setq getRO_RO_ (cond (getRO_RO_) (1.0) ) ) ) "> : " ) ) ) (getRO_RO_) ) )
                  )
                )
              )
            )
            (while ;start_while-loop_
              (and
                (numberp getRO_)
              )
              (setq ss_newset_i 0)
              (while (< ss_newset_i (sslength ss_newset_))
                (setq ss_newset_ename_ (ssname ss_newset_ ss_newset_i))
                (setq ss_newset_obj_ (vlax-ename->vla-object ss_newset_ename_))
                
                (vla-put-rotation ss_newset_obj_ (deg-to-rad getRO_))
                (setq ss_newset_i (+ ss_newset_i 1))

              )
              ;final_cond_for_while_loop_input_ (ESC for exit while-loop_)
                (setq getRO_ ;Detect the variable's result in case of a function error
                  (vl-catch-all-apply 
                    (function 
                      (lambda () 
                        (setq getRO_RO_ (cond ( (getint (strcat "\nspecify get rotation\n<" (rtos (setq getRO_RO_ (cond (getRO_RO_) (1.0) ) ) ) "> : " ) ) ) (getRO_RO_) ) )
                      )
                    )
                  )
                )
              ;
            )
          ;
        ;
      ;
      ;return_osmode_mode
        (setvar "osmode" 1279)
      ;
    )
    (defun c:replace_block_object_reblock2 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ERR_
        (vl-catch-all-apply
          (function
            (lambda ()
              (setq target_blk_obj_EFNAME_ nil)
              (setq target_blk_ename_ (car (entsel "specify target_blk_ename_")))
              (setq target_blk_obj_ (vlax-ename->vla-object target_blk_ename_))
              (setq target_blk_obj_EFNAME_ (LM:effectivename target_blk_obj_))
            )
          )
        )
      )
      ;preloop_and_while
        (setq ss_pre_filter_set_xx_i 0)
        (setq ss_new_block_ (ssadd))
        (while (and 
                 (= (vl-catch-all-error-p ERR_) nil)
                 (< ss_pre_filter_set_xx_i (sslength ss_pre_filter_set_xx_))
               )
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_ro (rad-to-deg (vla-get-rotation ss_pre_filter_set_xx_obj_ )))
          (TA:vla-insertblock
            target_blk_obj_EFNAME_
            ss_pre_filter_set_xx_obj_ins_
            1
            (deg-to-rad ss_pre_filter_set_xx_obj_ro)
          )
          ;new_blk_entlast object
            (setq new_block_ename (entlast))
            (setq ss_new_block_ (ssadd new_block_ename ss_new_block_) )
          ;
          (setq ss_pre_filter_set_xx_i (+ ss_pre_filter_set_xx_i 1))
        )
      ;
      (setq ERR_temp1
        (vl-catch-all-apply
          (function
            (lambda ()
              (TA:ss-erase ss_pre_filter_set_xx_ )
            )
          )
        )
      )
      (setq Er-msg_detectloop nil)
      (while
        (= (type (setq Er-msg_detectloop (vl-catch-all-apply (function (lambda () (setq ref_ename_ (car (entsel "specify rotaion"))) ) ) ) )) 'ENAME )
        (cond
          ( (and 
                ; (= H Hsub )
                (= (type Er-msg_detectloop) 'ENAME )
            )
            (progn
              ;preloop_and_while
                (setq ss_new_block_i 0)
                (while (< ss_new_block_i (sslength ss_new_block_))
                  (setq ss_new_block_ename_ (ssname ss_new_block_ ss_new_block_i))
                  (setq ss_new_block_obj_ (vlax-ename->vla-object  ss_new_block_ename_))
                  (vla-put-rotation ss_new_block_obj_ 
                                    (setq ref_obj_ro (vla-get-rotation (vlax-ename->vla-object ref_ename_)))
                                    
                  )
                  (setq ss_new_block_i (+ ss_new_block_i 1))
                )
              ;
              
              
            )
          )
        )
      )
    )
    (defun c:replace_block_object_reblock3 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ERR_
        (vl-catch-all-apply
          (function
            (lambda ()
              (setq target_blk_obj_EFNAME_ nil)
              (setq target_blk_ename_ (car (entsel "specify target_blk_ename_")))
              (setq target_blk_obj_ (vlax-ename->vla-object target_blk_ename_))
              (setq target_blk_obj_EFNAME_ (LM:effectivename target_blk_obj_))
            )
          )
        )
      )
      ;preloop_and_while
        (setq ss_pre_filter_set_xx_i 0)
        (setq ss_new_block_ (ssadd))
        (while (and 
                 (= (vl-catch-all-error-p ERR_) nil)
                 (< ss_pre_filter_set_xx_i (sslength ss_pre_filter_set_xx_))
               )
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_ro (rad-to-deg (vla-get-rotation ss_pre_filter_set_xx_obj_ )))
          
          ;special code dynamic length
            (setq distance1_ (LM:getdynpropvalue ss_pre_filter_set_xx_obj_ "distance1"))
          ;
          
          (TA:vla-insertblock
            target_blk_obj_EFNAME_
            ss_pre_filter_set_xx_obj_ins_
            1
            (deg-to-rad ss_pre_filter_set_xx_obj_ro)
          )
          
          
          ;new_blk_entlast object
            (setq new_block_ename (entlast))
            (setq ss_new_block_ (ssadd new_block_ename ss_new_block_) )
            ;special code dynamic length
              (LM:setdynpropvalue (vlax-ename->vla-object  new_block_ename) "distance1" distance1_)
            ;
          ;
          (setq ss_pre_filter_set_xx_i (+ ss_pre_filter_set_xx_i 1))
        )
      ;
      ; (setq ERR_temp1
      ;   (vl-catch-all-apply
      ;     (function
      ;       (lambda ()
      ;         (TA:ss-erase ss_pre_filter_set_xx_ )
      ;       )
      ;     )
      ;   )
      ; )
      (setq Er-msg_detectloop nil)
      (while
        (= (type (setq Er-msg_detectloop (vl-catch-all-apply (function (lambda () (setq ref_ename_ (car (entsel "specify rotaion"))) ) ) ) )) 'ENAME )
        (cond
          ( (and 
                ; (= H Hsub )
                (= (type Er-msg_detectloop) 'ENAME )
            )
            (progn
              ;preloop_and_while
                (setq ss_new_block_i 0)
                (while (< ss_new_block_i (sslength ss_new_block_))
                  (setq ss_new_block_ename_ (ssname ss_new_block_ ss_new_block_i))
                  (setq ss_new_block_obj_ (vlax-ename->vla-object  ss_new_block_ename_))
                  (vla-put-rotation ss_new_block_obj_ 
                                    (setq ref_obj_ro (vla-get-rotation (vlax-ename->vla-object ref_ename_)))
                                    
                  )
                  (setq ss_new_block_i (+ ss_new_block_i 1))
                )
              ;
              
              
            )
          )
        )
      )
    )
    (defun TA:Assembly_block_ (blk_obj_ )
      ; (setq blk_ename_ (car (entsel "specify Object")))
      ; (setq blk_obj_ (vlax-ename->vla-object blk_ename_))
      (setq blk_list_ ())
      (if (= (vla-get-objectname blk_obj_) "AcDbBlockReference")
        (progn
          (setq blkname (cdr (assoc 2 (entget (vlax-vla-object->ename blk_obj_)))))
          (setq bdef (tblobjname "BLOCK" blkname))
          (if (= (vl-prin1-to-string (type bdef)) "ENAME")
            (progn
              (setq nested (entnext bdef))
              
              (while 
                (and nested 
                    (/= (cdr (assoc 0 (entget nested))) "ENDBLK")
                )
                (if (= (cdr (assoc 0 (entget nested))) "INSERT")
                  (progn 


                    (setq nested_obj_ (vlax-ename->vla-object nested))
                    
                    (if (= (vla-get-visible nested_obj_) :vlax-true)
                      (progn
                        (princ (strcat "\n  └─ Nested block: " (LM:effectivename nested_obj_)) )
                        (setq blk_list_ (cons (LM:effectivename nested_obj_) blk_list_))
                      )
                    )
                    
                  )
                )
                (setq nested (entnext nested))
              )
            )
          )
        )
      )
      (TA:Count_item_in_list_ blk_list_ )
      
    
    
    )
    (defun TA:Assembly_vla-obj-block_ (blk_obj_ )
      ; (setq blk_ename_ (car (entsel "specify Object")))
      ; (setq blk_obj_ (vlax-ename->vla-object blk_ename_))
      (setq blk_list_ ())
      (if (= (vla-get-objectname blk_obj_) "AcDbBlockReference")
        (progn
          (setq blkname (cdr (assoc 2 (entget (vlax-vla-object->ename blk_obj_)))))
          (setq bdef (tblobjname "BLOCK" blkname))
          (if (= (vl-prin1-to-string (type bdef)) "ENAME")
            (progn
              (setq nested (entnext bdef))
              
              (while 
                (and nested 
                    (/= (cdr (assoc 0 (entget nested))) "ENDBLK")
                )
                (if (= (cdr (assoc 0 (entget nested))) "INSERT")
                  (progn 


                    (setq nested_obj_ (vlax-ename->vla-object nested))
                    
                    (if (= (vla-get-visible nested_obj_) :vlax-true)
                      (progn
                        (princ (strcat "\n  └─ Nested block: " (LM:effectivename nested_obj_)) )
                        (setq blk_list_ (cons nested_obj_ blk_list_))
                      )
                    )
                    
                  )
                )
                (setq nested (entnext nested))
              )
            )
          )
        )
      )
      (TA:Count_item_in_list_ blk_list_ )
      
    
    
    )
    (defun TA:Assembly_ename_ (blk_obj_ )
      ; (setq blk_ename_ (car (entsel "specify Object")))
      ; (setq blk_obj_ (vlax-ename->vla-object blk_ename_))
      (setq blk_list_ ())
      (if (= (vla-get-objectname blk_obj_) "AcDbBlockReference")
        (progn
          (setq blkname (cdr (assoc 2 (entget (vlax-vla-object->ename blk_obj_)))))
          (setq bdef (tblobjname "BLOCK" blkname))
          (if (= (vl-prin1-to-string (type bdef)) "ENAME")
            (progn
              (setq nested (entnext bdef))
              
              (while 
                (and nested 
                    (/= (cdr (assoc 0 (entget nested))) "ENDBLK")
                )
                (if (= (cdr (assoc 0 (entget nested))) "INSERT")
                  (progn 


                    (setq nested_obj_ (vlax-ename->vla-object nested))
                    
                    (if (= (vla-get-visible nested_obj_) :vlax-true)
                      (progn
                        (princ (strcat "\n  └─ Nested block: " (LM:effectivename nested_obj_)) )
                        (setq blk_list_ (cons nested blk_list_))
                      )
                    )
                    
                  )
                )
                (setq nested (entnext nested))
              )
            )
          )
        )
      )
      (TA:Count_item_in_list_ blk_list_ )
      
    
    
    )
    (defun TA:Assembly_des-name-block_ (blk_obj_ )
      ; (setq blk_ename_ (car (entsel "specify Object")))
      ; (setq blk_obj_ (vlax-ename->vla-object blk_ename_))
      ; (setq blk_obj_ target_block_obj_)
      (setq blk_list_ ())
      (if (= (vla-get-objectname blk_obj_) "AcDbBlockReference")
        (progn
          (setq blk_ename_ (vlax-vla-object->ename blk_obj_) )
          (setq blkname (cdr (assoc 2 (entget blk_ename_))))
          (setq bdef (tblobjname "BLOCK" blkname))
          (if (= (vl-prin1-to-string (type bdef)) "ENAME")
            (progn
              (setq nested (entnext bdef))
              
              (while 
                (and nested 
                    (/= (cdr (assoc 0 (entget nested))) "ENDBLK")
                )
                (if (= (cdr (assoc 0 (entget nested))) "INSERT")
                  (progn 


                    (setq nested_obj_ (vlax-ename->vla-object nested))
                    (setq block-editor_des-name (vla-get-comments (vla-Item (vla-get-Blocks (vla-get-ActiveDocument (vlax-get-acad-object))) (LM:effectivename nested_obj_))))
                    (if 
                      (and 
                        (= (vla-get-visible nested_obj_) :vlax-true)
                        (/= (LM:getvisibilityparametername nested_obj_) nil)
                        (LM:getdynpropvalue nested_obj_ (LM:getvisibilityparametername nested_obj_))
                      )
                      (progn
                        (princ (strcat "\n  └─ Nested block: " (LM:effectivename nested_obj_)) )
                        (setq blk_list_ (cons
                                          (strcat 
                                            (if (or (= block-editor_des-name nil) (= block-editor_des-name "")) (progn (LM:effectivename nested_obj_)) block-editor_des-name)
                                            (substr (LM:getdynpropvalue nested_obj_ (LM:getvisibilityparametername nested_obj_ ) ) 2 20 )
                                          ) 
                                          blk_list_
                                        )
                        )
                      
                      )
                    )
                    
                  )
                )
                (setq nested (entnext nested))
              )
            )
          )
        )
      )
      (TA:Count_item_in_list_ blk_list_ )
    )
    (defun TA:Foreach_Assembly_des-name-block_ (blk_ename_)
      ;preloop_and_while
        (setq sub-block_ ())
        (setq sub-block_ename_ ())
        (setq blkname (cdr (assoc 2 (entget blk_ename_))))
        (setq bdef (tblobjname "BLOCK" blkname))
        (setq nested (entnext bdef))
        (while (/= nested nil )
          (if 
            (and 
              (= (vla-get-objectname (vlax-ename->vla-object nested)) "AcDbBlockReference")
              (= (vla-get-visible (vlax-ename->vla-object nested)) :vlax-true)
              (= (vla-get-isdynamicblock (vlax-ename->vla-object nested)) :vlax-true)
              (/= (LM:getdynpropvalue (vlax-ename->vla-object nested) (LM:getvisibilityparametername (vlax-ename->vla-object nested))) "")
            )
            (progn
              (setq sub-block_ (cons (LM:effectivename (vlax-ename->vla-object nested)) sub-block_))
              (setq sub-block_ename_(cons nested sub-block_ename_))
              ; (length sub-block_)
              ; (length sub-block_ename_)
            )
          )
          (setq nested (entnext nested))
        )
      ;
      (setq blk_list_ ())
      (foreach x sub-block_ename_
        (setq x_obj_ (vlax-ename->vla-object x))
        (princ (strcat "\n  └─ Nested block: " (LM:effectivename x_obj_)) )
        (setq block-editor_des-name (vla-get-comments (vla-Item (vla-get-Blocks (vla-get-ActiveDocument (vlax-get-acad-object))) (LM:effectivename x_obj_))))
        (setq blk_list_ (cons 
                          (strcat 
                            (if (or (= block-editor_des-name nil) (= block-editor_des-name "") ) (progn (LM:effectivename x_obj_)) block-editor_des-name )
                            (substr (LM:getdynpropvalue x_obj_ (LM:getvisibilityparametername x_obj_) ) 2 20 )
                          )
                          blk_list_
                        )
        )
      )
      (TA:Count_item_in_list_ blk_list_ )
    )
    (defun c:DynBlk_make_thread-bolt_mktbolt ()
      (setq visibility_list_              
        (list 
          "top_view"
          "top_view_x8mm."
          "top_view_x10mm."
          "top_view_x12mm."
          "top_view_x14mm."
          "top_view_x15mm."
          "top_view_x20mm."
          "top_view_x25mm."
          "top_view_x30mm."
          "top_view_x35mm."
          "top_view_x40mm."
          "top_view_x45mm."
          "top_view_x50mm."
          "top_view_x55mm."
          "top_view_x60mm."
          "top_view_x65mm."
          "top_view_x70mm."
          "hex-nut" 
          "x8mm." 
          "x10mm."
          "x12mm." 
          "x14mm." 
          "x15mm." 
          "x20mm." 
          "x25mm." 
          "x30mm." 
          "x40mm." 
          "x45mm." 
          "x50mm." 
          "x55mm." 
          "x60mm." 
          "x65mm." 
          "x70mm." 
          "x75mm." 
          "x80mm." 
          "x90mm." 
          "x100mm." 
        )
      )
      ;preloop_and_while
        (setq visibility_list_i 0)
        (while (< visibility_list_i (length visibility_list_))
          (setq visibility_list_ename_ (nth  visibility_list_i visibility_list_))
          (if (wcmatch visibility_list_ename_ "*mm.*")
            (progn
              (command "bvstate" "s" visibility_list_ename_ )
              (command "insert" "000 - PROTOTYPE-DYNAMIC_THREAD_BOLT" (list 0 0 0) 1 270 )
              ;get_new_entlast ename
                (setq new_blk_ename_ (entlast))
                (setq new_blk_obj_ (vlax-ename->vla-object new_blk_ename_))
              ;
              ;dyn_object_
                (LM:setdynpropvalue new_blk_obj_ "thread_dia."  5)
                (LM:setdynpropvalue new_blk_obj_ "array_width" (LM:StringSubst "" "mm." (LM:StringSubst "" "x" visibility_list_ename_ )) )
              ;
            )
          )
          (setq visibility_list_i (+ visibility_list_i 1))
        )
      ;
      
      
    )
    ; (defun c:MKblk () 
      ;   ;selection_set_for_fillter_blk_name
      ;     (if  ;pre_select_ssget_or_post_select_ssget
      ;       (=
      ;         (setq sstarget_ (ssget "i"
      ;                                           (list
      ;                                             ; (cons 0 "INSERT") ;type of object
      ;                                             ; (cons 8 "000 - GRID")   ;kind of layer
      ;                                             ; (cons 2 "000-GRID_LINE_DYN")       ;kind of nameblock
      ;                                             ; (cons 62 1)           ;kind of color call sign with color code index
      ;                                           )
      ;                                     )
      ;         )
      ;         nil
      ;       )
      ;       (progn
      ;         (setq sstarget_ (ssget
      ;                                           (list
      ;                                             ; (cons 0 "INSERT") ;type of object
      ;                                             ; (cons 8 "000 - GRID")   ;kind of layer
      ;                                             ; (cons 2 "000-GRID_LINE_DYN")       ;kind of nameblock
      ;                                             ; (cons 62 1)           ;kind of color call sign with color code index
      ;                                           )
      ;                                     )
      ;         )
      ;       )
      ;       (sslength sstarget_)
      ;     )
      ;   (setvar "osmode" 1215)
      ;   ; (setq pttarget_ (getpoint "specify point for basepoint"))
      ;   (setq ssssasas (TA:ss_vla-getboundingbox sstarget_))
      ;   (setq pttarget_ (car ssssasas))
      ;   (command "point" pttarget_)
      ;   (setq pttarget_torr (list 
      ;                     (+ (car (car ssssasas)) 0) ;ไม่เผื่อก็ ใส่ 0 ปกติใส่ 2.5 เผื่อใบตัด
      ;                     (+ (cadr (car ssssasas)) 0) ;ไม่เผื่อก็ ใส่ 0 ปกติใส่ 2.5 เผื่อใบตัด
                          
      ;                   )
      ;   )
        
      ;   (setvar "osmode" 1215)
      ;   (setq namefile_ (getvar "dwgname"))
      ;   (setq name_ename_ (car (entsel "specify EF name")))
      ;   (setq name_obj_ (vlax-ename->vla-object name_ename_))
      ;   (setq nameblk (LM:StringSubst 
      ;                   ""
      ;                   ","
      ;                   (LM:StringSubst 
      ;                     ""
      ;                     ".dwg"
      ;                     (strcat 
      ;                       namefile_
      ;                       "_"
      ;                       ""
      ;                       (LM:StringSubst "-" "/" (vla-get-textstring name_obj_))
      ;                       ; (rtos (fix (* (car (TA:get_vertex_len_ (ssname sstarget_ 0))) 1000 ) ) 2 0 )
      ;                       ; "mm."
      ;                     )
      ;                   )
      ;                 )
      ;   )
      ;   (if 
      ;     (or 
      ;       (wcmatch
      ;         (vl-princ-to-string
      ;           (vl-catch-all-apply 
      ;             (function 
      ;               (lambda () 
      ;                 (vla-Item (vla-get-Blocks doc) nameblk)
      ;               )
      ;             )
      ;           )
      ;         )
      ;         "*error*,*IAcadBlock*"
      ;       )
      ;     )
      ;     (progn
      ;       (if 
      ;         (and
      ;           (wcmatch
      ;             (vl-princ-to-string
      ;               (vl-catch-all-apply 
      ;                 (function 
      ;                   (lambda () 
      ;                     (vla-delete (vla-Item (vla-get-Blocks doc) nameblk) )
      ;     )
      ;   )
      ;               )
      ;             )
      ;             "*error*,*IAcadBlock*"
      ;           )
      ;         )
      ;         (progn
      ;           (command "_block" nameblk pttarget_torr sstarget_ "" )
      ;           (TA:vla-insertblock nameblk pttarget_torr 1 0 )
      ;         )
      ;       )
      ;     )
      ;   )
      ;   ; ;new_blk_entlast object
      ;   ;   (setq sss_ename (entlast))
      ;   ;   (setq sss_obj (vlax-ename->vla-object sss_ename))
      ;   ;   (command "_copybase" pttarget_ sss_ename ""    )
      ;   ; ;
    ; )
    (defun c:BLKATTsort ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                                (cons 66 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                                (cons 66 1)
                                              )
                                        )
            )
          )
          (sslength ss_pre_filter_set_xx_)
        )
        (setq ss_pre_filter_set_xx_sorted (TA:standard_list_croodinate_sorting ss_pre_filter_set_xx_ "Y"))
      ;
      (setq tag-target_sort_ename_ (car (nentsel "specify TAG Object")))
      (setq tag-target_sort_obj_ (vlax-ename->vla-object tag-target_sort_ename_))
      (setq tag-target_sort_obj_tagname_ (vla-get-tagstring tag-target_sort_obj_ ))
      ;
      ;
      (setq sorting-finder_mode
        (TA:choose_list_v4
          (setq sortinglist_ (list "left to right" "top to below" "custom"))
          "select sorting mode"
          sorting-finder_mode
        )
      )
      (cond
        ( (= sorting-finder_mode "top to below" )
          (progn
            (setq ss_pre_filter_set_xx_sorted_ (TA:TBsort_ ss_pre_filter_set_xx_sorted 5 ))
          )
          
        )
        ( (= sorting-finder_mode "left to right" )
          (progn
            (setq ss_pre_filter_set_xx_sorted_ (TA:LRsort_ ss_pre_filter_set_xx_sorted 5 ))
          )
          
        )
        ( (= sorting-finder_mode "custom" )
          (progn
            ;while selection process
              (setq ERR_ nil)
              (setq ss_pre_filter_set_xx_sorted_ ())pse
              (setq custom-list_ename_ nil)
              (while ;for keep insertion point and dist. fix length one side
                (and
                  (= (vl-catch-all-error-p ERR_) nil)
                  (/= custom-list_ename_ "PASS")
                )
                (setq ERR_
                  (vl-catch-all-apply
                    (function
                      (lambda ()
                        (setvar "selectionpreview" 3)
                        (setq temp-ssblk (ssadd))
                        (setq custom-list_ename_ (car (entsel "specify Object to list")))
                        (setq custom-list_ename_vlains (list custom-list_ename_ (list 0 0 0)))
                        (if (/= custom-list_ename_ nil)
                          (progn
                            (setq ss_pre_filter_set_xx_sorted_ (cons custom-list_ename_vlains ss_pre_filter_set_xx_sorted_) )
                            (setq temp-ssblk (ssadd custom-list_ename_ temp-ssblk))
                            (command "pselect"  temp-ssblk "" )
                          )

                          (setq custom-list_ename_ "PASS")
                        )
                        
                      )
                    )
                  )
                )
              )
              (setvar "selectionpreview" 0)
              (setq ss_pre_filter_set_xx_sorted_ (reverse ss_pre_filter_set_xx_sorted_ ))
            ;
          )
          
        
        )
      )
      (setq prefix-str_list (list 
                           "user input"
                           "MRT PURPLE LINE  4\\PSTATION (PP17 - PP20)"
                           "FL-PJ26-008-PL1065V-\\PLOT-2-PART-"
                           "FL-PJ26-008-PL2065V-\\PLOT-1-PART-"

                         )
      )
      (setq prefix-str_sort_mode
        (TA:choose_list_v4
          prefix-str_list
          "select prefix-str_sort_ mode"
          prefix-str_sort_mode
        )
      )
      (setq BLKATTsort_start_num (cond ( (getint (strcat "\nspecify BLKATTsort_start_num\n<" (rtos (setq BLKATTsort_start_num (cond (BLKATTsort_start_num) (1.0) ) ) ) "> : " ) ) ) (BLKATTsort_start_num) ) )
      (setq BLKATTsort_start_num_i (TA:prefix_value_000 BLKATTsort_start_num))
      ;
      ;preloop_and_while
        (setq ss_pre_filter_set_xx_sorted_i 0)
        (while (< ss_pre_filter_set_xx_sorted_i (length ss_pre_filter_set_xx_sorted_))
          (setq ss_pre_filter_set_xx_sorted_ename_ (car (nth ss_pre_filter_set_xx_sorted_i ss_pre_filter_set_xx_sorted_ )))
          (setq ss_pre_filter_set_xx_sorted_obj_ (vlax-ename->vla-object  ss_pre_filter_set_xx_sorted_ename_))
          
          (LM:vl-setattributevalue ss_pre_filter_set_xx_sorted_obj_ tag-target_sort_obj_tagname_ (strcat prefix-str_sort_mode BLKATTsort_start_num_i))
          (LM:vl-setattributevalue ss_pre_filter_set_xx_sorted_obj_ "TTL_PJ_SHEET_NO" BLKATTsort_start_num_i)
          (LM:vl-setattributevalue ss_pre_filter_set_xx_sorted_obj_ "TTL_PJ_TOTAL_NO" (TA:prefix_value_000 (length ss_pre_filter_set_xx_sorted_)))
          (setq BLKATTsort_start_num_i (TA:prefix_value_000 (setq BLKATTsort_start_num (+ BLKATTsort_start_num 1))))
          
          
          (setq ss_pre_filter_set_xx_sorted_i (+ ss_pre_filter_set_xx_sorted_i 1))
        )
      ;
    )
    (defun c:BLKATTprefixsort ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                                (cons 66 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                                (cons 66 1)
                                              )
                                        )
            )
          )
          (sslength ss_pre_filter_set_xx_)
        )
        (setq ss_pre_filter_set_xx_sorted (TA:standard_list_croodinate_sorting ss_pre_filter_set_xx_ "Y"))
      ;
      (setq tag-target_sort_ename_ (car (nentsel "specify TAG Object")))
      (setq tag-target_sort_obj_ (vlax-ename->vla-object tag-target_sort_ename_))
      (setq tag-target_sort_obj_tagname_ (vla-get-tagstring tag-target_sort_obj_ ))
      ;
      ;
      (setq sorting-finder_mode
        (TA:choose_list_v4
          (setq sortinglist_ (list "left to right" "top to below" "custom"))
          "select sorting mode"
          sorting-finder_mode
        )
      )
      (cond
        ( (= sorting-finder_mode "top to below" )
          (progn
            (setq ss_pre_filter_set_xx_sorted_ (TA:TBsort_ ss_pre_filter_set_xx_sorted 5 ))
          )
          
        )
        ( (= sorting-finder_mode "left to right" )
          (progn
            (setq ss_pre_filter_set_xx_sorted_ (TA:LRsort_ ss_pre_filter_set_xx_sorted 5 ))
          )
          
        )
        ( (= sorting-finder_mode "custom" )
          (progn
            ;while selection process
              (setq ERR_ nil)
              (setq ss_pre_filter_set_xx_sorted_ ())pse
              (setq custom-list_ename_ nil)
              (while ;for keep insertion point and dist. fix length one side
                (and
                  (= (vl-catch-all-error-p ERR_) nil)
                  (/= custom-list_ename_ "PASS")
                )
                (setq ERR_
                  (vl-catch-all-apply
                    (function
                      (lambda ()
                        (setvar "selectionpreview" 3)
                        (setq temp-ssblk (ssadd))
                        (setq custom-list_ename_ (car (entsel "specify Object to list")))
                        (setq custom-list_ename_vlains (list custom-list_ename_ (list 0 0 0)))
                        (if (/= custom-list_ename_ nil)
                          (progn
                            (setq ss_pre_filter_set_xx_sorted_ (cons custom-list_ename_vlains ss_pre_filter_set_xx_sorted_) )
                            (setq temp-ssblk (ssadd custom-list_ename_ temp-ssblk))
                            (command "pselect"  temp-ssblk "" )
                          )

                          (setq custom-list_ename_ "PASS")
                        )
                        
                      )
                    )
                  )
                )
              )
              (setvar "selectionpreview" 0)
              (setq ss_pre_filter_set_xx_sorted_ (reverse ss_pre_filter_set_xx_sorted_ ))
            ;
          )
          
        
        )
      )
      (setq prefix-str_list (list 
                           "user input"
                           "MRT PURPLE LINE  4\\PSTATION (PP17 - PP20)"
                           "FL-PJ-26-008-PL1065V-\\PTYP-"
                           "FL-PJ-26-008-PL2065V-\\PTYP-"
                           "FL-PJ-26-008-PL2065V-\\PLOT-2-PART-"
                           "FL-PJ-26-008-PL1065V-\\PLOT-2-PART-"
                           "FL-PJ-26-031-HK-\\PMEP-PART-"
                           "FL-PJ-26-031-\\PALU-PANEL-PART-"
                           "FL-PJ-26-031-HK-\\PC10-PART-"
                         )
      )
      (setq prefix-str_sort_mode
        (TA:choose_list_v4
          prefix-str_list
          "select prefix-str_sort_ mode"
          prefix-str_sort_mode
        )
      )
      (setq BLKATTsort_start_num (cond ( (getint (strcat "\nspecify BLKATTsort_start_num\n<" (rtos (setq BLKATTsort_start_num (cond (BLKATTsort_start_num) (1.0) ) ) ) "> : " ) ) ) (BLKATTsort_start_num) ) )
      (setq BLKATTsort_start_num_i (TA:prefix_value_000 BLKATTsort_start_num))
      ;
      ;preloop_and_while
        (setq ss_pre_filter_set_xx_sorted_i 0)
        (while (< ss_pre_filter_set_xx_sorted_i (length ss_pre_filter_set_xx_sorted_))
          (setq ss_pre_filter_set_xx_sorted_ename_ (car (nth ss_pre_filter_set_xx_sorted_i ss_pre_filter_set_xx_sorted_ )))
          (setq ss_pre_filter_set_xx_sorted_obj_ (vlax-ename->vla-object  ss_pre_filter_set_xx_sorted_ename_))
          
          (LM:vl-setattributevalue ss_pre_filter_set_xx_sorted_obj_ tag-target_sort_obj_tagname_ (strcat prefix-str_sort_mode BLKATTsort_start_num_i))
          (LM:vl-setattributevalue ss_pre_filter_set_xx_sorted_obj_ "TTL_PJ_SHEET_NO" BLKATTsort_start_num_i)
          (LM:vl-setattributevalue ss_pre_filter_set_xx_sorted_obj_ "TTL_PJ_TOTAL_NO" (TA:prefix_value_000 (length ss_pre_filter_set_xx_sorted_)))
          (setq BLKATTsort_start_num_i (TA:prefix_value_000 (setq BLKATTsort_start_num (+ BLKATTsort_start_num 1))))
          
          
          (setq ss_pre_filter_set_xx_sorted_i (+ ss_pre_filter_set_xx_sorted_i 1))
        )
      ;
    )
    (defun c:MKTblk () 
      ;selection_set_for_fillter_blk_name
        (if  ;pre_select_ssget_or_post_select_ssget
          (=
            (setq sstarget_ (ssget "i"
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq sstarget_ (ssget
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength sstarget_)
        )
      ;
      (setvar "osmode" 1215)
      (setq pttarget_torr (getpoint "specify point for basepoint"))
      
      ; (setq ssssasas (TA:ss_vla-getboundingbox sstarget_))
      ; (setq pttarget_ (car ssssasas))
      ; (setq pttarget_torr (list 
      ;                   (+ (car (car ssssasas)) 0) ;ไม่เผื่อก็ ใส่ 0 ปกติใส่ 2.5 เผื่อใบตัด
      ;                   (+ (cadr (car ssssasas)) 0) ;ไม่เผื่อก็ ใส่ 0 ปกติใส่ 2.5 เผื่อใบตัด
                        
      ;                 )
      ; )
      
      (setvar "osmode" 1215)
      (setq namefile_ (getvar "dwgname"))
      (setq nameblk (LM:StringSubst 
                        ""
                        ".dwg"
                        (strcat 
                          namefile_
                          "_"
                          ""
                          (LM:StringSubst "-" "." (rtos (getvar "cdate") 2 6))
                          ; (rtos (fix (* (car (TA:get_vertex_len_ (ssname sstarget_ 0))) 1000 ) ) 2 0 )
                          ; "mm."
                          (getstring "input_subfix")
                        )
                      )
      )
      (if 
        (or 
          (wcmatch
            (vl-princ-to-string
              (vl-catch-all-apply 
                (function 
                  (lambda () 
                    (vla-Item (vla-get-Blocks doc) nameblk)
                  )
                )
              )
            )
            "*error*,*IAcadBlock*"
          )
        )
        (progn
          (if 
            (and
              (wcmatch
                (vl-princ-to-string
                  (vl-catch-all-apply 
                    (function 
                      (lambda () 
                        (vla-delete (vla-Item (vla-get-Blocks doc) nameblk) )
         )
        )
                  )
                )
                "*error*,*IAcadBlock*"
              )
            )
            (progn
              (setvar  "osmode" 0)
              (command "_block" nameblk pttarget_torr sstarget_ "" )
              (TA:vla-insertblock 
                nameblk 
                (if (= (getvar "worlducs") 0)(progn (trans pttarget_torr 1 0)) pttarget_torr ) 
                1 
                0 
              )
            )
          )
        )
      )
      (setvar "osmode" 1215)
      ; ;new_blk_entlast object
      ;   (setq sss_ename (entlast))
      ;   (setq sss_obj (vlax-ename->vla-object sss_ename))
      ;   (command "_copybase" pttarget_ sss_ename ""    )
      ; ;
    )
    (defun c:MKblk () 
      ;selection_set_for_fillter_blk_name
        (if  ;pre_select_ssget_or_post_select_ssget
          (=
            (setq sstarget_ (ssget "i"
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq sstarget_ (ssget
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength sstarget_)
        )
      ;
      (setvar "osmode" 1215)
      (setq pttarget_torr (getpoint "specify point for basepoint"))
      
      ; (setq ssssasas (TA:ss_vla-getboundingbox sstarget_))
      ; (setq pttarget_ (car ssssasas))
      ; (setq pttarget_torr (list 
      ;                   (+ (car (car ssssasas)) 0) ;ไม่เผื่อก็ ใส่ 0 ปกติใส่ 2.5 เผื่อใบตัด
      ;                   (+ (cadr (car ssssasas)) 0) ;ไม่เผื่อก็ ใส่ 0 ปกติใส่ 2.5 เผื่อใบตัด
                        
      ;                 )
      ; )
      
      (setvar "osmode" 1215)
      (setq namefile_ (getvar "dwgname"))
      (setq nameblk (LM:StringSubst 
                      ""
                      ","
                      (LM:StringSubst 
                        ""
                        ".dwg"
                        (strcat 
                          namefile_
                          "_"
                          ""
                          ; (LM:StringSubst "-" "." (rtos (getvar "cdate") 2 6))
                          ; (rtos (fix (* (car (TA:get_vertex_len_ (ssname sstarget_ 0))) 1000 ) ) 2 0 )
                          ; "mm."
                          (getstring "input_subfix")
                        )
                      )
                    )
      )
      (if 
        (or 
          (wcmatch
            (vl-princ-to-string
              (vl-catch-all-apply 
                (function 
                  (lambda () 
                    (vla-Item (vla-get-Blocks doc) nameblk)
                  )
                )
              )
            )
            "*error*,*IAcadBlock*"
          )
        )
        (progn
          (if 
            (and
              (wcmatch
                (vl-princ-to-string
                  (vl-catch-all-apply 
                    (function 
                      (lambda () 
                        (vla-delete (vla-Item (vla-get-Blocks doc) nameblk))
        )
      )
                  )
                )
                "*error*,*IAcadBlock*"
              )
            )
            (progn
              (command "_block" nameblk pttarget_torr sstarget_ "" )
              (TA:vla-insertblock 
                nameblk 
                (if (= (getvar "worlducs") 0)(progn (trans pttarget_torr 1 0)) pttarget_torr ) 
                1 
                0 
              )
            )
          )
        )
      )
      ; ;new_blk_entlast object
      ;   (setq sss_ename (entlast))
      ;   (setq sss_obj (vlax-ename->vla-object sss_ename))
      ;   (command "_copybase" pttarget_ sss_ename ""    )
      ; ;
    )
    (defun c:MKBREAL () 
      (setvar "osmode" 0)
      (setq sstarget_ (ssadd))
      (setq namefile_ (getvar "dwgname"))
      (setq nameblk_ename_ (car (entsel "specify Object")))
      (setq sstarget_ (ssadd nameblk_ename_ sstarget_))
      (setq nameblk_obj_ (vlax-ename->vla-object nameblk_ename_))
      (setq nameblk_obj_ins_ (vlax-safearray->list (vlax-variant-value (vla-get-insertionpoint nameblk_obj_))))
      (setq nameblk (vla-get-textstring nameblk_obj_))
      
      (if 
        (or 
          (wcmatch
            (vl-princ-to-string
              (vl-catch-all-apply 
                (function 
                  (lambda () 
                    (vla-Item (vla-get-Blocks doc) nameblk)
                  )
                )
              )
            )
            "*error*,*IAcadBlock*"
          )
        )
        (progn
          (if 
            (and
              (wcmatch
                (vl-princ-to-string
                  (vl-catch-all-apply 
                    (function 
                      (lambda () 
                        (vla-delete (vla-Item (vla-get-Blocks doc) nameblk))
                      )
                    )
                  )
                )
                "*error*,*IAcadBlock*"
              )
            )
            (progn
              (command "_block" nameblk nameblk_obj_ins_ sstarget_ "" )
              (TA:vla-insertblock nameblk nameblk_obj_ins_ 1 0 )
            )
          )
        )
      )
      (setvar "osmode" 1215)
      ; ;new_blk_entlast object
      ;   (setq sss_ename (entlast))
      ;   (setq sss_obj (vlax-ename->vla-object sss_ename))
      ;   (command "_copybase" pttarget_ sss_ename ""    )
      ; ;
    )
    (defun c:MKPartBLK_MKP2 () 
      ;selection_set_for_fillter_blk_name
        (if  ;pre_select_ssget_or_post_select_ssget
          (=
            (setq sstarget_ (ssget "i"
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq sstarget_ (ssget
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength sstarget_)
        )
      (setvar "osmode" 1215)
      (setq pttarget_ (getpoint "specify point for basepoint"))
      ; (setq ssssasas (TA:ss_vla-getboundingbox sstarget_))
      ; (setq pttarget_ (car ssssasas))
      ; (command "point" pttarget_)
      (setq pttarget_torr (list 
                        (+ (car pttarget_) 0)
                        (+ (cadr pttarget_) 0)
                        
                      )
      )
      
      (setvar "osmode" 1215)
      (setq namefile_ (getvar "dwgname"))
      (setq name_ename_ (car (entsel "specify EF name")))
      (setq name_obj_ (vlax-ename->vla-object name_ename_))
      (setq nameblk (LM:StringSubst 
                      ""
                      ","
                      (LM:StringSubst 
                        ""
                        ".dwg"
                        (strcat 
                          namefile_
                          "_"
                          ""
                          (LM:StringSubst "-" "/" (vla-get-textstring name_obj_))
                          "_Blanksize-PL"
                          ; (rtos (fix (* (car (TA:get_vertex_len_ (ssname sstarget_ 0))) 1000 ) ) 2 0 )
                          ; "mm."
                        )
                      )
                    )
      )
      (if 
        (or 
          (wcmatch
            (vl-princ-to-string
              (vl-catch-all-apply 
                (function 
                  (lambda () 
                    (vla-Item (vla-get-Blocks doc) nameblk)
                  )
                )
              )
            )
            "*error*,*IAcadBlock*"
          )
        )
        (progn
          (if 
            (and
              (wcmatch
                (vl-princ-to-string
                  (vl-catch-all-apply 
                    (function 
                      (lambda () 
                        (vla-delete (vla-Item (vla-get-Blocks doc) nameblk) )
                      )
                    )
                  )
                )
                "*error*,*IAcadBlock*"
              )
            )
            (progn
              (command "_block" nameblk pttarget_torr sstarget_ "" )
              (TA:vla-insertblock nameblk pttarget_torr 1 0 )
            )
          )
        )
      )
      ; ;new_blk_entlast object
      ;   (setq sss_ename (entlast))
      ;   (setq sss_obj (vlax-ename->vla-object sss_ename))
      ;   (command "_copybase" pttarget_ sss_ename ""    )
      ; ;
    )
    (defun c:MKPartBLK_MKPC06 () 
      ;selection_set_for_fillter_blk_name
        (if  ;pre_select_ssget_or_post_select_ssget
          (=
            (setq sstarget_ (ssget "i"
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq sstarget_ (ssget
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength sstarget_)
        )
      (setvar "osmode" 1215)
      (setq all_blk (TA:get_name_block_in_drawing_to_list))
      (setq all_c06_panel_ (length(TA:wcmatch_list (list "*TA_AHP_PANEL_*") all_blk T)))
      (setq pttarget_ (getpoint "specify point for basepoint"))
      (setq pttarget_torr (list 
                        (+ (car pttarget_) 0)
                        (+ (cadr pttarget_) 0)
                        
                      )
      )
      (setvar "osmode" 1215)
      ; (setq namefile_ (getvar "dwgname"))
      (setq namepanel_ "NAME_PANEL") ;ไม่ต้องมี "_"
      (setq name_ename_ (car (entsel "specify EF name")))
      (setq name_obj_ (vlax-ename->vla-object name_ename_))
      (setq nameblk (LM:StringSubst 
                      ""
                      ","
                      (LM:StringSubst 
                        ""
                        ".dwg"
                        (strcat 
                          namepanel_
                          "_"
                          ""
                          (LM:StringSubst "-" "/" (vla-get-textstring name_obj_))
                          "_TA_AHP_PANEL_"
                          (cond
                            (;_case_1
                               (and
                                  (> (fix all_c06_panel_ ) 0)
                                  (< (fix all_c06_panel_ ) 9)
                               )
                               (progn
                                 (strcat "00" (rtos (+ (fix all_c06_panel_ ) 1) 2 0 ))
                                 
                               )
                            )
                            (;_case_2
                               (and
                                  (>= (fix all_c06_panel_ ) 10)
                                  (<= (fix all_c06_panel_ ) 99)
                               )
                               (progn
                                 (strcat "0" (rtos (+ (fix all_c06_panel_ ) 1) 2 0 ))
                                 
                               )
                            )
                            
                          )
                          ; "mm."
                        )
                      )
                    )
      )
      (if 
        (or 
          (wcmatch
            (vl-princ-to-string
              (vl-catch-all-apply 
                (function 
                  (lambda () 
                    (vla-Item (vla-get-Blocks doc) nameblk)
                  )
                )
              )
            )
            "*error*,*IAcadBlock*"
          )
        )
        (progn
          (if 
            (and
              (wcmatch
                (vl-princ-to-string
                  (vl-catch-all-apply 
                    (function 
                      (lambda () 
                        (vla-delete (vla-Item (vla-get-Blocks doc) nameblk) )
                      )
                    )
                  )
                )
                "*error*,*IAcadBlock*"
              )
            )
            (progn
              (command "_block" nameblk pttarget_torr sstarget_ "" )
              (TA:vla-insertblock nameblk pttarget_torr 1 0 )
            )
          )
        )
      )
      ; ;new_blk_entlast object
      ;   (setq sss_ename (entlast))
      ;   (setq sss_obj (vlax-ename->vla-object sss_ename))
      ;   (command "_copybase" pttarget_ sss_ename ""    )
      ; ;
    )
    (defun c:make_cutting_plan_addATT ()
      
      (command "-attdef" "L" "" "FULL_SIZE_NO." "" "----" "S" "TA" "J" "MC" 0 0 0)
      ;new_blk_entlast object
        (setq att_ename (entlast))
        (setq att_obj_ (vlax-ename->vla-object att_ename))
        (vla-put-alignment att_obj_  12)
        (vla-put-textalignmentpoint att_obj_ (vlax-3d-point 0.02 0.02 0))
        (vla-put-height att_obj_ 0.1)
        (vla-put-lockposition  att_obj_ -1)

      ;
      (command "-attdef" "L" "" "ON_PANEL_SIZE_NO." "" "----" "S" "TA" "J" "BL" att_xyz-ins 0  )
      ;new_blk_entlast object
        (setq att_ename (entlast))
        (setq att_obj_ (vlax-ename->vla-object att_ename))
        (vla-put-alignment att_obj_  12)
        (vla-put-textalignmentpoint att_obj_ (vlax-3d-point 0.02 0.2 0))
        (vla-put-height att_obj_ 0.1)
        (vla-put-lockposition  att_obj_ -1)

      ;
      (command "-attdef" "L" "" "QTY." "" "----" "S" "TA" "J" "BL" att_xyz-ins 0  )
      ;new_blk_entlast object
        (setq att_ename (entlast))
        (setq att_obj_ (vlax-ename->vla-object att_ename))
        (vla-put-alignment att_obj_  12)
        (vla-put-textalignmentpoint att_obj_ (vlax-3d-point 0.4 0.4 0))
        (vla-put-height att_obj_ 0.1)
        (vla-put-lockposition  att_obj_ -1)

      ;

    )
    (defun c:make_cutting_plan_dyndip ()
      (setq pt (getpoint "inputpoint"))
      (setvar "osmode" 0)
      (TA:vla-insertblock "000 - DYNAMIC SYMBOL DIRECTION PAINT" pt 50 0 )
      (setvar "osmode" 1215)
      ; ;new_blk_entlast object
      ;   (TA:vla-insertblock "000 - DYNAMIC SYMBOL DIRECTION PAINT" pt 1 0 )
      ;   (setq sym_ename (entlast))
      ;   (setq sym_obj (vlax-ename->vla-object sym_ename))
      ;   (setq pt2 (polar pt (deg-to-rad 90) 2))
      ; ;

      ;new_blk_entlast object
        (command "_bparameter" "R" pt 4 "0" "" 1)
        
        (command "_bparameter" "L" pt pt2 pt2 1)
        (command "BACTIONTOOL"  "R"    )
        (command "BACTIONTOOL"  "T"    )          
    )
    (defun TA:Switch_lookup (ss_pre_filter_set_xx_ blk_fitter_name_ blk_filter_tag_)
      ;presetting
        ; (setq blk_fitter_name_ "000 - TRANSFER")
        ; (setq blk_filter_tag_ "lookup1")
      ;
      ;selection_set_for_fillter_blk_name
        ; (if  ;pre_select_ssget_or_post_select_ssget
        ;   (=
        ;     (setq ss_pre_filter_set_xx_ (ssget "i"
        ;                                       (list
        ;                                         (cons 0 "INSERT") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;     nil
        ;   )
        ;   (progn
        ;     (setq ss_pre_filter_set_xx_ (ssget
        ;                                       (list
        ;                                         (cons 0 "INSERT") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;   )
        ;   (sslength ss_pre_filter_set_xx_)
        ; )
        ; (setq ss_pre_filter_set_xx_ (TA:EF_Filter_ss_set_ ss_pre_filter_set_xx_ blk_fitter_name_))
      ;
      ;presetting dynamic tag&val
        (setq ss_pre_filter_set_xx_ename_ (ssname ss_pre_filter_set_xx_ 0))
        (setq ss_pre_filter_set_xx_obj_ (vlax-ename->vla-object  ss_pre_filter_set_xx_ename_))
        (setq ss_pre_filter_set_xx_obj_vis-value_ (LM:getdynpropallowedvalues ss_pre_filter_set_xx_obj_ blk_filter_tag_))
        (setq ss_pre_filter_set_xx_obj_vis-length_ (length ss_pre_filter_set_xx_obj_vis-value_))
        (setq ERR_ nil)
        (while 
          (and
            (= (vl-catch-all-error-p ERR_) nil)
          )
          (setq ERR_
            (vl-catch-all-apply
              (function
                (lambda ()
                  (setq vis_value (cond 
                                    ((getint 
                                       (strcat "\n0 = previous \n1 = next \n<" (rtos (setq vis_value (cond (vis_value) (1.0) ) ) ) "> : " )
                                     )
                                    )
                                    (vis_value)
                                  )
                  )
                )
              )
            )
          )
          ;preloop_and_while
            (setq ss_pre_filter_set_xx_i 0)
            (while (and 
                     (= (vl-catch-all-error-p ERR_) nil)
                     (< ss_pre_filter_set_xx_i (sslength ss_pre_filter_set_xx_))
                   ) 
              (setq ss_pre_filter_set_xx_ename_ (ssname ss_pre_filter_set_xx_ ss_pre_filter_set_xx_i))
              (setq ss_pre_filter_set_xx_obj_ (vlax-ename->vla-object  ss_pre_filter_set_xx_ename_))
              (setq ss_pre_filter_set_xx_obj_vis-value_ (LM:getdynpropallowedvalues ss_pre_filter_set_xx_obj_ "lookup1"))
              (setq ss_pre_filter_set_xx_obj_currrent_vis_val_ 
                      (car 
                         (TA:find-all-indexes 
                           (LM:getdynpropvalue ss_pre_filter_set_xx_obj_ "lookup1")
                           ss_pre_filter_set_xx_obj_vis-value_
                         )
                       )
              )
              (if (or 
                    (>= (+ ss_pre_filter_set_xx_obj_currrent_vis_val_ vis_value) ss_pre_filter_set_xx_obj_vis-length_)
                  )
                (progn
                  (LM:setdynpropvalue ss_pre_filter_set_xx_obj_ 
                    blk_filter_tag_ 
                    (nth 0 ss_pre_filter_set_xx_obj_vis-value_)
                  )
                )
                (cond
                  ((and ;plus cond
                    (/= (+ ss_pre_filter_set_xx_obj_currrent_vis_val_ vis_value) ss_pre_filter_set_xx_obj_vis-length_)
                    (>= vis_value 1)
                  )
                    (progn
                      (LM:setdynpropvalue ss_pre_filter_set_xx_obj_ 
                        blk_filter_tag_ 
                        (nth (fix (+ ss_pre_filter_set_xx_obj_currrent_vis_val_ vis_value )) ss_pre_filter_set_xx_obj_vis-value_)
                      )
                    )
                  )
                  ((and ;minus cond
                     (< (- ss_pre_filter_set_xx_obj_currrent_vis_val_ 1) 0)
                     (< vis_value 1)
                   )
                    (progn
                      (LM:setdynpropvalue ss_pre_filter_set_xx_obj_ 
                        blk_filter_tag_ 
                        (nth (fix (- ss_pre_filter_set_xx_obj_vis-length_ 1 )) ss_pre_filter_set_xx_obj_vis-value_)
                      )
                    )
                  )
                  ((and ;minus cond
                     (>= (- ss_pre_filter_set_xx_obj_currrent_vis_val_ 1) 0)
                     (< vis_value 1)
                   )
                    (progn
                      (LM:setdynpropvalue ss_pre_filter_set_xx_obj_ 
                        blk_filter_tag_ 
                        (nth (fix (- ss_pre_filter_set_xx_obj_currrent_vis_val_ 1 )) ss_pre_filter_set_xx_obj_vis-value_)
                      )
                    )
                  )
                )
              )
              
              (setq ss_pre_filter_set_xx_i (+ ss_pre_filter_set_xx_i 1))
            )
          ;
          
        )
      ;

        
      ;
      
    )
    (defun TA:if_found_block_ (block_str_name_)
      ;Note By Code_Developer
      ;The pripicle of codework is desgined for finding block definition in the drawing
      ;example for useing fucntion : (TA:if_found_block_ "A$C26be2c7e" )
      ;
      (if (= 
            (type 
              (vl-catch-all-apply 
                (function 
                  (lambda () 
                    (vla-Item (vla-get-Blocks (vla-get-ActiveDocument (vlax-get-acad-object))) block_str_name_ )
                  )
                )
              )
            )
            'VLA-OBJECT
          )
        (progn
          T
        )
      )
    )
    (defun TA:renameblock_all_dwg (new_replace_str_ old_name_str_)
      (setq all_dwg_block_ (TA:get_name_block_in_drawing_to_list_v2))
      ;preloop_and_while
        (setq all_dwg_block_i 0)
        (while (< all_dwg_block_i (length all_dwg_block_))
          (setq all_dwg_block_efname_ (car (nth  all_dwg_block_i all_dwg_block_)))
          (setq new_efname_ (LM:StringSubst 
                              new_replace_str_
                              old_name_str_
                              all_dwg_block_efname_
                            )
          )
          (command "rename" "b" all_dwg_block_efname_ new_efname_)
          (setq all_dwg_block_i (+ all_dwg_block_i 1))
        )
      ;
    )
    (defun c:rename_block_bycase () 
      ; (setq target-change_ "000 - ASSCESSORIES*")
      ; (setq target-change_ "*C10_PANEL_*")
      ; (setq next-change_ "300-PANEL_")
      (setq target-change_ "*300-PANEL_*")
      (setq next-change_ "C10_PANEL_")
      (setq all-block_indwg_ (TA:get_name_block_in_drawing_to_list_v2))
      
      ;preloop_and_while
        (setq all-block_indwg_i 0)
        (while (< all-block_indwg_i (length all-block_indwg_))
          (setq all-block_indwg_val_ (car (nth  all-block_indwg_i all-block_indwg_)))
          (if (= (wcmatch all-block_indwg_val_ (strcat  target-change_ )) T)
            (progn
              (setq newcut_ (LM:StringSubst "" "*"  target-change_  ))
              (command "rename" "B" all-block_indwg_val_ (LM:StringSubst next-change_ newcut_  all-block_indwg_val_  ))
            )
          )
      
          (setq all-block_indwg_i (+ all-block_indwg_i 1))
        )
      ;
      
    )
    (defun c:get_block_bycase ()
      (setq all-block_indwg_ (TA:get_name_block_in_drawing_to_list_v2))
      (setq wildcard-search_ "*`[ASPG-COMBINE`]*")
      (setq p1 (getpoint "specify point 1"))
      (setq p2 (getpoint p1 "specify point 1"))
      ;preloop_and_while
        (setq all-block_indwg_i 0)
        (setq all-block_indwg_newlist_ ())
        (while (< all-block_indwg_i (length all-block_indwg_))
          (setq all-block_indwg_ename_ (car (nth  all-block_indwg_i all-block_indwg_)))
          (if (= (wcmatch all-block_indwg_ename_ wildcard-search_ ) T )
            (progn
              (setq all-block_indwg_newlist_ (cons all-block_indwg_ename_ all-block_indwg_newlist_ ))
            )
          )
      
          (setq all-block_indwg_i (+ all-block_indwg_i 1))
        )
      ;
      ;preloop_and_while
        (setq all-block_indwg_newlist_i 0)
        (while (< all-block_indwg_newlist_i (length all-block_indwg_newlist_))
          (setq all-block_indwg_newlist_ename_ (nth  all-block_indwg_newlist_i all-block_indwg_newlist_))
          (if (/= (strlen (TA:KeepNumber all-block_indwg_newlist_ename_) ) 3)
            (progn
              (setq new-nameblk_ 
                (TA:renameblock_ 
                  all-block_indwg_newlist_ename_
                  (LM:StringSubst (TA:prefix_value_000 (atoi (TA:KeepNumber all-block_indwg_newlist_ename_ )))   (TA:KeepNumber all-block_indwg_newlist_ename_) all-block_indwg_newlist_ename_)
                )
              )
            )
          )

          
          (setq all-block_indwg_newlist_i (+ all-block_indwg_newlist_i 1))
        )
      ;
      
      
      
    )
    (defun TA:all-block_filter_ (wildcard-search_ )
      (setq all-block_indwg_ (TA:get_name_block_in_drawing_to_list_v2))
      ; (setq wildcard-search_ "*`[ASPG-COMBINE`]*")
      ;preloop_and_while
        (setq all-block_indwg_i 0)
        (setq all-block_indwg_newlist_ ())
        (while (< all-block_indwg_i (length all-block_indwg_))
          (setq all-block_indwg_ename_ (car (nth  all-block_indwg_i all-block_indwg_)))
          (if (= (wcmatch all-block_indwg_ename_ wildcard-search_ ) T )
            (progn
              (setq all-block_indwg_newlist_ (cons all-block_indwg_ename_ all-block_indwg_newlist_ ))
            )
          )
      
          (setq all-block_indwg_i (+ all-block_indwg_i 1))
        )
      ;
      (setq result all-block_indwg_newlist_)
    )
    (defun c:insert_block_list_ ()
      (setq filterlist-blk_ (TA:all-block_filter_ "*`[ASPG-COMBINE`]*"))
      (setq point-1_ (getpoint "specify point 1 "))
      (setq point-2_ (getpoint point-1_ "specify point 2 "))
      ;preloop_and_while
        (setq filterlist-blk_i 0)
        (while (< filterlist-blk_i (length filterlist-blk_))
          (setq filterlist-blk_ename_ (nth  filterlist-blk_i filterlist-blk_))
          (TA:vla-insertblock 
            filterlist-blk_ename_
            point-1_
            1
            0
          )
          ;new_blk_entlast object
            (setq inslist_ename (entlast))
            (setq inslist_obj_ (vlax-ename->vla-object inslist_ename))
            (TA:move_axis_insertionpoint inslist_obj_ "Y" (* (distance point-1_ point-2_) filterlist-blk_i))
          ;
          (setq filterlist-blk_i (+ filterlist-blk_i 1))
        )
      ;
      
    )
  ;
  ;dynamic_block_and_ATTRIBUTE_FUNC
    ;dynamic_Alminium_sheet_FUNC
      (defun c:dynamic_update_U-Carrier_[UCupdate] ()
        
        ;user_input get_effectivename 
          (setq get_effectivename_ nil)
          ; (setq get_effectivename_lasted nil)
          (setq get_effectivename_obj_val_ nil)
        ;
        ;preloop_and_while_
          (while (not get_effectivename_)
            (princ (setq get_effectivename_ (car (entsel "\nPlease Specify Attribute Block\n"))))   
            (if (/= get_effectivename_ nil)
              (progn
                (setq get_effectivename_lasted get_effectivename_)
              )
            )          
                      
            (if 
              (and ;condition rule
                
                (setq B (= (setq type_obj_ (vla-get-objectname (vlax-ename->vla-object (if (= get_effectivename_ nil) (progn get_effectivename_lasted ) get_effectivename_ )))) 
                          "AcDbBlockReference"
                        )
                )
                ; (= (substr (LM:Effectivename (vlax-ename->vla-object get_effectivename_)) 1 72) "000 - DYNAMIC_ARRAY_ASSCESSORIES_FAMELINE_AL._U45-CARRIER_BRACKET_FITTING")
                (setq C 
                        (= 
                          (wcmatch
                          (LM:Effectivename (vlax-ename->vla-object (if (= get_effectivename_ nil) (progn get_effectivename_lasted ) get_effectivename_ ))) 
                          "*000 - DYNAMIC_ARRAY_ASSCESSORIES_FAMELINE_AL._U45-CARRIER_BRACKET_FITTING*"
                          )
                        )
                )
                ; (= (vla-get-hasattributes (vlax-ename->vla-object get_effectivename_)) :vlax-true)
                (setq D (= (vla-get-isdynamicblock (vlax-ename->vla-object (if (= get_effectivename_ nil) (progn get_effectivename_lasted ) get_effectivename_ )))
                          :vlax-true
                        )
                )
              )
              (progn ;add data
                ; (alert "\nplease select block object")
                ; (setq get_effectivename_ nil)
                ; (setq get_effectivename_obj_val_ nil)
                ;get_dynamic_data
                  (setq get_effectivename_ get_effectivename_lasted)
                  (setq get_effectivename_obj_val_ (LM:Effectivename (vlax-ename->vla-object get_effectivename_)))
                  (setq array_width (LM:getdynpropvalue (vlax-ename->vla-object get_effectivename_) "array_width" ))
                  (setq total_u-profile_depth (LM:getdynpropvalue (vlax-ename->vla-object get_effectivename_) "total_u-profile_depth" ))
                  (setq u-profile_width_set (LM:getdynpropvalue (vlax-ename->vla-object get_effectivename_) "u-profile_width_set" ))
                  
                  ; (setq louver_angle_ (LM:getdynpropvalue (vlax-ename->vla-object get_effectivename_) "louver_angle" )) ;ปิดชั่วคราวเปลี่ยนเป็น user input 
                  (setq louver_angle_deg (cond ( (getreal (strcat "\nspecify angle<" (rtos (setq louver_angle_deg (cond (louver_angle_deg) (1.2) ) ) ) "> : " ) ) ) (louver_angle_deg) ) ) ;
                  (setq louver_angle_ (deg-to-rad louver_angle_deg) )

                  ; (setq louver_width_(LM:getdynpropvalue (vlax-ename->vla-object get_effectivename_) "louver_width" )) ;ปิดชั่วคราวเปลี่ยนเป็น user input 
                  (setq louver_width_ (cond ( (getreal (strcat "\nspecify louver_width_<" (rtos (setq louver_width_ (cond (louver_width_) (10) ) ) ) "> : " ) ) ) (louver_width_) ) )
                  (setq u-profile_width_set (LM:getdynpropvalue (vlax-ename->vla-object get_effectivename_) "u-profile_width_set"  ))
                  (setq louver_depth_start_angle_ (deg-to-rad 90))
                  (setq louver_depth_end_angle_ (deg-to-rad (- 180 (+ 90 (rad-to-deg louver_angle_)  ))))
                
                  (setq position_1Y (LM:getdynpropvalue (vlax-ename->vla-object get_effectivename_) "Position1 Y" ))
                ;
                ;reset_block_process_
                  (command "resetblock" get_effectivename_ "" )
                  (setq u-profile_width_set (LM:getdynpropvalue (vlax-ename->vla-object get_effectivename_) "array_width" ))
                  
                ;
                ;trigonmetry_cal
                  ;find_ louver_depth_ formula
                    ;
                      (LM:setdynpropvalue (vlax-ename->vla-object get_effectivename_) "louver_depth" 
                        (if (>= louver_angle_deg 90)
                          (progn
                            louver_width_
                          )
                          (/
                            (* 
                              (sin louver_angle_)
                              louver_width_
                            ) 
                            (sin louver_depth_end_angle_)
                          )
                        )
                      )
                    ;
                  ;
                  ;find_ base_trigon_ formula
                    ;
                      (LM:setdynpropvalue (vlax-ename->vla-object get_effectivename_) "base_trigon" 
                        (if (>= louver_angle_deg 90)
                          (progn
                            louver_width_
                          )
                          (/
                            (* 
                              (sin louver_depth_start_angle_)
                              louver_width_
                            ) 
                            (sin louver_depth_end_angle_)
                          )
                        )
                      )
                    ;
                  ;

                ;
                ;louver_depth_90deg
                  ;
                    (LM:setdynpropvalue (vlax-ename->vla-object get_effectivename_) "louver_depth_90deg" 
                      (if (>= louver_angle_deg 90)
                        (progn
                          (setq louver_depth (cond ( (getreal (strcat "\nspecify louver_depth<" (rtos (setq louver_depth (cond (louver_depth) (1.2) ) ) ) "> : " ) ) ) (louver_depth) ) )
                        )
                        0
                      )
                    )
                  ;
                ;
                ;return_input_data_to_parameter_
                  (LM:setdynpropvalue (vlax-ename->vla-object get_effectivename_) "louver_angle" louver_angle_)
                  
                  ; (LM:setdynpropvalue (vlax-ename->vla-object get_effectivename_) "position1 X" 0)
                  ; (LM:setdynpropvalue (vlax-ename->vla-object get_effectivename_) "position1 Y" position_1Y)
                  
                  (LM:setdynpropvalue (vlax-ename->vla-object get_effectivename_) "louver_width" 
                    (if (>= louver_angle_deg 90)
                      (progn
                        louver_depth
                      )
                      louver_width_
                    )
                  )
                  
                  (LM:setdynpropvalue (vlax-ename->vla-object get_effectivename_) "u-profile_width_set" u-profile_width_set)
                  (LM:setdynpropvalue (vlax-ename->vla-object get_effectivename_) "array_width" array_width)
                  (LM:setdynpropvalue (vlax-ename->vla-object get_effectivename_) "total_u-profile_depth" total_u-profile_depth)
                
                ;
                ;add more
              )
              (setq get_effectivename_ nil)
            )
          )
        ;
      )
    ;
    (defun c:redynamicblock () 
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        ; (setq ss_pre_filter_set_xx_ (TA:EF_Filter_ss_set_ ss_pre_filter_set_xx_ "xxxxxxxxxxxxxxxxxxxxxxxxxxxx"))
      ;
      (TA:interface_text_ T)
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i)) 
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_efname_ (LM:effectivename ss_pre_filter_set_xx_obj_))
          (setq ss_pre_filter_set_xx_obj_ro_ (vla-get-rotation ss_pre_filter_set_xx_obj_))
          (setq ss_pre_filter_set_xx_obj_proplist_ (LM:getdynprops ss_pre_filter_set_xx_obj_ ))
          (TA:vla-insertblock 
            ss_pre_filter_set_xx_obj_efname_
            ss_pre_filter_set_xx_obj_ins_
            1
            ss_pre_filter_set_xx_obj_ro_
          )
          ;preloop_and_while
            (setq ss_pre_filter_set_xx_obj_proplist_i 0)
            (while (< ss_pre_filter_set_xx_obj_proplist_i (length ss_pre_filter_set_xx_obj_proplist_))
              ;new_blk_entlast object
                (setq newnewblk_ename (entlast))
                (setq newnewblk_obj (vlax-ename->vla-object newnewblk_ename))
              ;
              (if (/= (setq ss_pre_filter_set_xx_obj_proplist_tag_ (car (nth  ss_pre_filter_set_xx_obj_proplist_i ss_pre_filter_set_xx_obj_proplist_))) "Origin")
                (progn
                  (LM:setdynpropvalue 
                    newnewblk_obj 
                    (setq ss_pre_filter_set_xx_obj_proplist_tag_ (car (nth  ss_pre_filter_set_xx_obj_proplist_i ss_pre_filter_set_xx_obj_proplist_)))
                    (setq ss_pre_filter_set_xx_obj_proplist_val_ (cdr (nth  ss_pre_filter_set_xx_obj_proplist_i ss_pre_filter_set_xx_obj_proplist_)))
                  )
                )
              )
              (TA:textscr_process_V2 "\nupdate dynamic" ss_pre_filter_set_xx_obj_proplist_i ss_pre_filter_set_xx_obj_proplist_)
              (setq ss_pre_filter_set_xx_obj_proplist_i (+ ss_pre_filter_set_xx_obj_proplist_i 1))
            )
          ;
          (TA:textscr_process_V2 "\nupdate block" ss_pre_filter_set_xx_i ss_pre_filter_set_xx_)
          (vla-delete ss_pre_filter_set_xx_obj_)
          (setq ss_pre_filter_set_xx_i (+ ss_pre_filter_set_xx_i 1))
        )
      ;
    )
    (defun c:makedynamic_point_and_move ()
      ;คำสั่งเฉพาะทาง
      ;ออกแบบมาเพื่อสร้าง dynamic แบบ point เพื่อต้องการให้ move ที่ vertex ของ point
      (setq sstemp_sel_ss (ssget))
      (setq sss_ename_ (car (entsel "specify Object")))
      (setq sss_obj_ (vlax-ename->vla-object sss_ename_))
      (setq vvv_List_ (car (cdr (TA:Get_Pline_vertext_ins_point_ sss_ename_))))
      ;preloop_and_while
        (setq vvv_List_i 1)
        (while (< vvv_List_i (length vvv_List_))
          (setq vvv_List_val_ (nth  vvv_List_i vvv_List_))
          (command "bparameter" "o" vvv_List_val_  (polar vvv_List_val_ (deg-to-rad 45) 2000) "1" )
          (setq upper_ (polar vvv_List_val_ (deg-to-rad 45) 500))
          (setq below_ (polar vvv_List_val_ (deg-to-rad 225) 500))
          ;new_blk_entlast object
            (setq bpara_ename (entlast)) 
            (setq bpara_obj (vlax-ename->vla-object bpara_ename))
            (command "pselect"  bpara_ename "" )
            (command "_.BACTION"  "ST" upper_ below_ sstemp_sel_ss "")
          ;
          (setq vvv_List_i (+ vvv_List_i 1))
        )
      ;
    )
    (defun c:blkattadd ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;keepstring process
        (setq blk-att-add_string_ ;Get-string by keep previous value
            (if
              (or
                (/= (setq blk-att-add_string_val (getstring (strcat "\nSpecify Pattern name <" (if blk-att-add_string_ blk-att-add_string_ "") ">: ") ) ) "" )
              )
                (progn
                  (setq blk-att-add_string_ blk-att-add_string_val)
                  (setq blk-att-add_string_keep_val_ blk-att-add_string_val)
                )
              (setq blk-att-add_string_val blk-att-add_string_keep_val_)
            )
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (if (= ss_pre_filter_set_xx_i 0)
            (progn
              (setq add-minus_val_ ;Get-string by keep previous value
                (if
                  (or
                    (/= (setq add-minus_val_val (getstring (strcat "\nSpecify Pattern name <" (if add-minus_val_ add-minus_val_ "") ">: ") ) ) "" )
                  )
                    (progn
                      (setq add-minus_val_ add-minus_val_val)
                      (setq add-minus_val_keep_val_ add-minus_val_val)
                    )
                  (setq add-minus_val_val add-minus_val_keep_val_)
                )
              )
            )
          )
          (cond
            ( (and 
                  (/= (atoi (LM:vl-getattributevalue ss_pre_filter_set_xx_obj_ blk-att-add_string_ )) 0)
                  (= add-minus_val_ "+" )
                )
              (progn
                (LM:vl-setattributevalue 
                  ss_pre_filter_set_xx_obj_ 
                  blk-att-add_string_ 
                  (+ (atoi (LM:vl-getattributevalue ss_pre_filter_set_xx_obj_ blk-att-add_string_ )) 1)
                )
              )
            )
            ( (and 
                  (/= (atoi (LM:vl-getattributevalue ss_pre_filter_set_xx_obj_ blk-att-add_string_ )) 0)
                  (= add-minus_val_ "-" )
                )
              (progn
                (LM:vl-setattributevalue 
                  ss_pre_filter_set_xx_obj_ 
                  blk-att-add_string_ 
                  (- (atoi (LM:vl-getattributevalue ss_pre_filter_set_xx_obj_ blk-att-add_string_ )) 1)
                )
              )
            )
          )
          (setq ss_pre_filter_set_xx_i (+ ss_pre_filter_set_xx_i 1))
        )
      ;
    )
    (defun c:ATTRIBUTE-TO-CSV_ATT2CSV ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                                (cons 66 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                                (cons 66 1)
                                              )
                                        )
            )
          )
          (sslength ss_pre_filter_set_xx_)
        )
        (setq ss_pre_filter_set_xx_filter_ (TA:EF_Filter_ss_set_ ss_pre_filter_set_xx_ (LM:effectivename (vlax-ename->vla-object (car (entsel "select block "))))))
        (setq ss_pre_filter_set_xx_sorted (TA:standard_list_croodinate_sorting ss_pre_filter_set_xx_ "Y"))
      ;
      ;
      (setq sorting-finder_mode
        (TA:choose_list_v4
          (setq sortinglist_ (list "left to right" "top to below" "custom"))
          "select sorting mode"
          sorting-finder_mode
        )
      )
      (cond
        ( (= sorting-finder_mode "top to below" )
          (progn
            (setq ss_pre_filter_set_xx_sorted_ (TA:TBsort_ ss_pre_filter_set_xx_sorted 5 ))
          )
          
        )
        ( (= sorting-finder_mode "left to right" )
          (progn
            (setq ss_pre_filter_set_xx_sorted_ (TA:LRsort_ ss_pre_filter_set_xx_sorted 5 ))
          )
          
        )
        ( (= sorting-finder_mode "custom" )
          (progn
            ;while selection process
              (setq ERR_ nil)
              (setq ss_pre_filter_set_xx_sorted_ ())pse
              (setq custom-list_ename_ nil)
              (while ;for keep insertion point and dist. fix length one side
                (and
                  (= (vl-catch-all-error-p ERR_) nil)
                  (/= custom-list_ename_ "PASS")
                )
                (setq ERR_
                  (vl-catch-all-apply
                    (function
                      (lambda ()
                        (setvar "selectionpreview" 3)
                        (setq temp-ssblk (ssadd))
                        (setq custom-list_ename_ (car (entsel "specify Object to list")))
                        (setq custom-list_ename_vlains (list custom-list_ename_ (list 0 0 0)))
                        (if (/= custom-list_ename_ nil)
                          (progn
                            (setq ss_pre_filter_set_xx_sorted_ (cons custom-list_ename_vlains ss_pre_filter_set_xx_sorted_) )
                            (setq temp-ssblk (ssadd custom-list_ename_ temp-ssblk))
                            (command "pselect"  temp-ssblk "" )
                          )

                          (setq custom-list_ename_ "PASS")
                        )
                        
                      )
                    )
                  )
                )
              )
              (setvar "selectionpreview" 0)
              (setq ss_pre_filter_set_xx_sorted_ (reverse ss_pre_filter_set_xx_sorted_ ))
            ;
          )
          
        
        )
      )
      ;preloop_and_while stack-att-data
        (setq ss_pre_filter_set_xx_i 0)
        (setq ss_pre_filter_set_xx_obj_proplist_array_ ())
        (while 
          (and 
            (< ss_pre_filter_set_xx_i (length ss_pre_filter_set_xx_sorted_))
            (= (vla-get-hasattributes (vlax-ename->vla-object (car (nth ss_pre_filter_set_xx_i ss_pre_filter_set_xx_sorted_ ))))   :vlax-true)
          )
          (setq ss_pre_filter_set_xx_ename_ (car (nth ss_pre_filter_set_xx_i ss_pre_filter_set_xx_sorted_ )))
          (setq ss_pre_filter_set_xx_obj_ (vlax-ename->vla-object  ss_pre_filter_set_xx_ename_))
          (setq ss_pre_filter_set_xx_obj_proplist_ (LM:vl-getattributevalues ss_pre_filter_set_xx_obj_ ))
          (if (= ss_pre_filter_set_xx_i 0)
            (progn
              (setq ss_pre_filter_set_xx_obj_proplist_tag_ (mapcar '(lambda (item_) (TA:Mtext_format_to_text_ (car item_)) ) ss_pre_filter_set_xx_obj_proplist_ ) )
            )
          )
          
          (setq ss_pre_filter_set_xx_obj_proplist_subval_ (mapcar '(lambda (item_) (TA:Mtext_format_to_text_ (cdr item_)) ) ss_pre_filter_set_xx_obj_proplist_ ) )
          
          (setq ss_pre_filter_set_xx_obj_proplist_array_ (cons ss_pre_filter_set_xx_obj_proplist_subval_  ss_pre_filter_set_xx_obj_proplist_array_) )
          
          ;preloop_and_while
          
          ;
          (setq ss_pre_filter_set_xx_i (+ ss_pre_filter_set_xx_i 1))
        )
      ;
      (setq ss_pre_filter_set_xx_obj_proplist_array_1 (append (list ss_pre_filter_set_xx_obj_proplist_tag_ ) (reverse ss_pre_filter_set_xx_obj_proplist_array_)))
      (setq filepath (getvar "dwgprefix"))
      (setq filename_ (strcat (LM:StringSubst "" ".dwg"  (getvar "dwgname"))  ".csv"))
      (setq filepath_ (strcat filepath filename_))
      (LM:writecsv  ss_pre_filter_set_xx_obj_proplist_array_1 filepath_)
      
    )
    
  ;
  ;hatch_FUNC
    (defun TA:create_hatch_ (hatch_ename_ hatch_ename_getang_ hatch_ename_getsc_)
      ;example_user_input_
        ; (setq obj_name_ (vla-get-objectname (vlax-ename->vla-object (setq hatch_ename_ (car (entsel "specify Object"))))))
        ; (setq hatch_ename_ (car (entsel "specify Object")))
      ;
      ;get_object_name_data
        (setq obj_name_ (vla-get-objectname (vlax-ename->vla-object hatch_ename_)))
      ;
      ;cond for filter objectname_
        (cond
          ( ;first process
            (or
              
              (= obj_name_ "AcDbPolyline")
            )
            (progn
              (= (vla-get-closed (setq hatch_ename_obj_ (vlax-ename->vla-object hatch_ename_))) :vlax-true)
              (setq 1st_process "AcDbPolyline")
            )
          )
          (;first process
            (or
              (= obj_name_ "AcDbBlockReference")
            )
            (progn
              (setq 1st_process "AcDbBlockReference")
              
            )
          )
        )
      ;
      
      ;pre_set_vari_
        ; (if 
        ;   (and 
        ;     (= hatch_ename_getang_ nil)
        ;     (= hatch_ename_getsc_ nil)
        ;   )
        ;   (progn
        ;     (setq  hatch_ename_getang_ 0)
        ;     (setq  hatch_ename_getsc_ 1)
            
        ;   )
        ; )
      ;
      ;presetting_hatch_data_
        (setq hatch_Layer_ "000 - H A T C H")
        (setq hatch_patt_ "ANSI32")
        (setq hatch_color_ 8)
        (setq hatch_background_ 250)
      ;
      ; (setq hatch_ename_getang_ (cond ( (getreal (strcat "\nspecify angle<" (rtos (setq hatch_ename_getang_ (cond (hatch_ename_getang_) (hatch_ename_getsc_) ) ) ) "> : " ) ) ) (hatch_ename_getang_) ) )
      ; (setq hatch_ename_getsc_ (cond ( (getreal (strcat "\nspecify scale<" (rtos (setq hatch_ename_getsc_ (cond (hatch_ename_getsc_) (hatch_ename_getsc_) ) ) ) "> : " ) ) ) (hatch_ename_getsc_) ) )
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               ""
      )
      
      
    )
    (defun TA:create_hatch_ANSI37 (hatch_ename_ hatch_ename_getang_ hatch_ename_getsc_)
      ;example_user_input_
        ; (setq obj_name_ (vla-get-objectname (vlax-ename->vla-object (setq hatch_ename_ (car (entsel "specify Object"))))))
        ; (setq hatch_ename_ (car (entsel "specify Object")))
      ;
      ;get_object_name_data
        (setq obj_name_ (vla-get-objectname (vlax-ename->vla-object hatch_ename_)))
      ;
      ;cond for filter objectname_
        (cond
          ( ;first process
            (or
              
              (= obj_name_ "AcDbPolyline")
            )
            (progn
              (= (vla-get-closed (setq hatch_ename_obj_ (vlax-ename->vla-object hatch_ename_))) :vlax-true)
              (setq 1st_process "AcDbPolyline")
            )
          )
          (;first process
            (or
              (= obj_name_ "AcDbBlockReference")
            )
            (progn
              (setq 1st_process "AcDbBlockReference")
              
            )
          )
        )
      ;
      
      ;pre_set_vari_
        ; (if 
        ;   (and 
        ;     (= hatch_ename_getang_ nil)
        ;     (= hatch_ename_getsc_ nil)
        ;   )
        ;   (progn
        ;     (setq  hatch_ename_getang_ 0)
        ;     (setq  hatch_ename_getsc_ 1)
            
        ;   )
        ; )
      ;
      ;presetting_hatch_data_
        (setq hatch_Layer_ "000 - H A T C H")
        (setq hatch_patt_ "ANSI37")
        (setq hatch_color_ 8)
        (setq hatch_background_ 250)
      ;
      ; (setq hatch_ename_getang_ (cond ( (getreal (strcat "\nspecify angle<" (rtos (setq hatch_ename_getang_ (cond (hatch_ename_getang_) (hatch_ename_getsc_) ) ) ) "> : " ) ) ) (hatch_ename_getang_) ) )
      ; (setq hatch_ename_getsc_ (cond ( (getreal (strcat "\nspecify scale<" (rtos (setq hatch_ename_getsc_ (cond (hatch_ename_getsc_) (hatch_ename_getsc_) ) ) ) "> : " ) ) ) (hatch_ename_getsc_) ) )

      (setq hatch_obj_ (vlax-ename->vla-object hatch_ename_))
      
      
      (command ".-hatch" "s"  hatch_ename_  
                "" 
                "c" hatch_color_ hatch_background_
                "p" hatch_patt_ hatch_ename_getsc_ hatch_ename_getang_ 
                "L" hatch_Layer_ 
                ""  
                ""
      )
      
      
      
    )
    (defun TAS:create_hatch_PPLINE_ (hatch_ename_ hatch_ename_getang_ hatch_ename_getsc_ hatch_mode)
      ;example_user_input_
        ; (setq obj_name_ (vla-get-objectname (vlax-ename->vla-object (setq hatch_ename_ (car (entsel "specify Object"))))))
        ; (setq hatch_ename_ (car (entsel "specify Object")))
      ;
      ;get_object_name_data
        (setq obj_name_ (vla-get-objectname (vlax-ename->vla-object hatch_ename_)))
      ;
      ;cond for filter objectname_
        (cond
          ( ;first process
            (or
              
              (= obj_name_ "AcDbPolyline")
            )
            (progn
              (= (vla-get-closed (setq hatch_ename_obj_ (vlax-ename->vla-object hatch_ename_))) :vlax-true)
              (setq 1st_process "AcDbPolyline")
            )
          )
          (;first process
            (or
              (= obj_name_ "AcDbBlockReference")
            )
            (progn
              (setq 1st_process "AcDbBlockReference")
              
            )
          )
        )
      ;
      
      ;pre_set_vari_
        ; (if 
        ;   (and 
        ;     (= hatch_ename_getang_ nil)
        ;     (= hatch_ename_getsc_ nil)
        ;   )
        ;   (progn
        ;     (setq  hatch_ename_getang_ 0)
        ;     (setq  hatch_ename_getsc_ 1)
            
        ;   )
        ; )
      ;
      ;presetting_hatch_data_
        (setq hatch_Layer_ "000 - H A T C H")
        (setq hatch_patt_
          (cond 
            ( ;hatctpatt_case_
              (and (= hatch_mode 1))
              (progn 
                (setq hatch_patt_ "000_C01")
                (setq hatch_color_ 8)
                (princ hatch_patt_)
              )
            )
            ( ;hatctpatt_case_
              (and (= hatch_mode 2))
              (progn 
                (setq hatch_patt_ "000_C02")
                (setq hatch_color_ 2)
                (princ hatch_patt_)
              )
            )
            ( ;hatctpatt_case_
              (and (= hatch_mode 3))
              (progn 
                (setq hatch_patt_ "000_C03")
                (setq hatch_color_ 2)
                (princ hatch_patt_)
              )
            )
            ( ;hatctpatt_case_
              (and (= hatch_mode 4))
              (progn 
                (setq hatch_patt_ "000_C04")
                (setq hatch_color_ 1)
                (princ hatch_patt_)
              )
            )
            ( ;hatctpatt_case_
              (and (= hatch_mode 5))
              (progn 
                (setq hatch_patt_ "000_C05")
                (setq hatch_color_ 1)
                (princ hatch_patt_)
              )
            )
            ( ;hatctpatt_case_
              (and (= hatch_mode 51))
              (progn 
                (setq hatch_patt_ "000_C05A")
                (setq hatch_color_ 1)
                (princ hatch_patt_)
              )
            )
            ( ;hatctpatt_case_
              (and (= hatch_mode 6))
              (progn 
                (setq hatch_patt_ "000_C06")
                (setq hatch_color_ 3)
                (princ hatch_patt_)
              )
            )
            ( ;hatctpatt_case_
              (and (= hatch_mode 7))
              (progn 
                (setq hatch_patt_ "000_C07")
                (setq hatch_color_ 3)
                (princ hatch_patt_)
              )
            )
            ( ;hatctpatt_case_
              (and (= hatch_mode 8))
              (progn 
                (setq hatch_patt_ "000_C08")
                (setq hatch_color_ 1)
                (princ hatch_patt_)
              )
            )
            ( ;hatctpatt_case_
              (and (= hatch_mode 9))
              (progn 
                (setq hatch_patt_ "000_C09")
                (setq hatch_color_ 1)
                (princ hatch_patt_)
              )
            )
            ( ;hatctpatt_case_
              (and (= hatch_mode 10))
              (progn 
                (setq hatch_patt_ "000_C10")
                (setq hatch_color_ 4)
                (princ hatch_patt_)
              )
            )
            ( ;hatctpatt_case_
              (and (= hatch_mode 11))
              (progn 
                (setq hatch_patt_ "000_C11")
                (setq hatch_color_ 3)
                (princ hatch_patt_)
              )
            )
          )
        )
        
        (setq hatch_background_ 250)
      ;
      ; (setq hatch_ename_getang_ (cond ( (getreal (strcat "\nspecify angle<" (rtos (setq hatch_ename_getang_ (cond (hatch_ename_getang_) (hatch_ename_getsc_) ) ) ) "> : " ) ) ) (hatch_ename_getang_) ) )
      ; (setq hatch_ename_getsc_ (cond ( (getreal (strcat "\nspecify scale<" (rtos (setq hatch_ename_getsc_ (cond (hatch_ename_getsc_) (hatch_ename_getsc_) ) ) ) "> : " ) ) ) (hatch_ename_getsc_) ) )

      (setq hatch_obj_ (vlax-ename->vla-object hatch_ename_))
      
      
      (command ".-hatch" "s"  hatch_ename_  
                "" 
                "c" hatch_color_ hatch_background_
                "p" hatch_patt_ hatch_ename_getsc_ hatch_ename_getang_ 
                "L" hatch_Layer_ 
                ""  
                ""
      )
      
      
      
    )
    (defun TAS:create_Wallhatch_PPLINE_ (hatch_ename_ hatch_ename_getang_ hatch_ename_getsc_ hatch_mode)
      ;example_user_input_
        ; (setq obj_name_ (vla-get-objectname (vlax-ename->vla-object (setq hatch_ename_ (car (entsel "specify Object"))))))
        ; (setq hatch_ename_ (car (entsel "specify Object")))
      ;
      ;get_object_name_data
        (setq obj_name_ (vla-get-objectname (vlax-ename->vla-object hatch_ename_)))
      ;
      ;cond for filter objectname_
        (cond
          ( ;first process
            (or
              
              (= obj_name_ "AcDbPolyline")
            )
            (progn
              (= (vla-get-closed (setq hatch_ename_obj_ (vlax-ename->vla-object hatch_ename_))) :vlax-true)
              (setq 1st_process "AcDbPolyline")
            )
          )
          (;first process
            (or
              (= obj_name_ "AcDbBlockReference")
            )
            (progn
              (setq 1st_process "AcDbBlockReference")
              
            )
          )
        )
      ;
      
      ;pre_set_vari_
        ; (if 
        ;   (and 
        ;     (= hatch_ename_getang_ nil)
        ;     (= hatch_ename_getsc_ nil)
        ;   )
        ;   (progn
        ;     (setq  hatch_ename_getang_ 0)
        ;     (setq  hatch_ename_getsc_ 1)
            
        ;   )
        ; )
      ;
      ;presetting_hatch_data_
        (setq hatch_Layer_ "000 - H A T C H")
        (setq hatch_patt_
          (cond 
            ( ;hatctpatt_case_
              (and (= hatch_mode 1))
              (progn 
                (setq hatch_patt_ "000_W01")
                (setq hatch_color_ 8)
                (princ hatch_patt_)
              )
            )
            ( ;hatctpatt_case_
              (and (= hatch_mode 2))
              (progn 
                (setq hatch_patt_ "000_W02")
                (setq hatch_color_ 2)
                (princ hatch_patt_)
              )
            )
            ( ;hatctpatt_case_
              (and (= hatch_mode 3))
              (progn 
                (setq hatch_patt_ "000_W03")
                (setq hatch_color_ 2)
                (princ hatch_patt_)
              )
            )
            ( ;hatctpatt_case_
              (and (= hatch_mode 4))
              (progn 
                (setq hatch_patt_ "000_W04")
                (setq hatch_color_ 1)
                (princ hatch_patt_)
              )
            )
            ( ;hatctpatt_case_
              (and (= hatch_mode 5))
              (progn 
                (setq hatch_patt_ "000_W05")
                (setq hatch_color_ 1)
                (princ hatch_patt_)
              )
            )
            ( ;hatctpatt_case_
              (and (= hatch_mode 6))
              (progn 
                (setq hatch_patt_ "000_W06")
                (setq hatch_color_ 3)
                (princ hatch_patt_)
              )
            )
            ( ;hatctpatt_case_
              (and (= hatch_mode 7))
              (progn 
                (setq hatch_patt_ "000_W07")
                (setq hatch_color_ 3)
                (princ hatch_patt_)
              )
            )
            ( ;hatctpatt_case_
              (and (= hatch_mode 8))
              (progn 
                (setq hatch_patt_ "000_W08")
                (setq hatch_color_ 1)
                (princ hatch_patt_)
              )
            )
            ( ;hatctpatt_case_
              (and (= hatch_mode 9))
              (progn 
                (setq hatch_patt_ "000_W09")
                (setq hatch_color_ 1)
                (princ hatch_patt_)
              )
            )
            ( ;hatctpatt_case_
              (and (= hatch_mode 10))
              (progn 
                (setq hatch_patt_ "000_W10")
                (setq hatch_color_ 4)
                (princ hatch_patt_)
              )
            )
            ( ;hatctpatt_case_
              (and (= hatch_mode 11))
              (progn 
                (setq hatch_patt_ "000_W11")
                (setq hatch_color_ 3)
                (princ hatch_patt_)
              )
            )
            ( ;hatctpatt_case_
              (and (= hatch_mode 12))
              (progn 
                (setq hatch_patt_ "000_W12")
                (setq hatch_color_ 3)
                (princ hatch_patt_)
              )
            )
            ( ;hatctpatt_case_
              (and (= hatch_mode 13))
              (progn 
                (setq hatch_patt_ "000_W13")
                (setq hatch_color_ 3)
                (princ hatch_patt_)
              )
            )
            ( ;hatctpatt_case_
              (and (= hatch_mode 14))
              (progn 
                (setq hatch_patt_ "000_W14")
                (setq hatch_color_ 3)
                (princ hatch_patt_)
              )
            )
            ( ;hatctpatt_case_
              (and (= hatch_mode 15))
              (progn 
                (setq hatch_patt_ "000_W15")
                (setq hatch_color_ 3)
                (princ hatch_patt_)
              )
            )
            ( ;hatctpatt_case_
              (and (= hatch_mode 16))
              (progn 
                (setq hatch_patt_ "000_W16")
                (setq hatch_color_ 3)
                (princ hatch_patt_)
              )
            )
            ( ;hatctpatt_case_
              (and (= hatch_mode 17))
              (progn 
                (setq hatch_patt_ "000_W17")
                (setq hatch_color_ 3)
                (princ hatch_patt_)
              )
            )
            ( ;hatctpatt_case_
              (and (= hatch_mode 18))
              (progn 
                (setq hatch_patt_ "000_W18")
                (setq hatch_color_ 3)
                (princ hatch_patt_)
              )
            )
            ( ;hatctpatt_case_
              (and (= hatch_mode 19))
              (progn 
                (setq hatch_patt_ "000_W19")
                (setq hatch_color_ 3)
                (princ hatch_patt_)
              )
            )
            ( ;hatctpatt_case_
              (and (= hatch_mode 20))
              (progn 
                (setq hatch_patt_ "000_W20")
                (setq hatch_color_ 3)
                (princ hatch_patt_)
              )
            )
            ( ;hatctpatt_case_
              (and (= hatch_mode 21))
              (progn 
                (setq hatch_patt_ "000_W21")
                (setq hatch_color_ 3)
                (princ hatch_patt_)
              )
            )
            ( ;hatctpatt_case_
              (and (= hatch_mode 22))
              (progn 
                (setq hatch_patt_ "000_W22")
                (setq hatch_color_ 3)
                (princ hatch_patt_)
              )
            )
            ( ;hatctpatt_case_
              (and (= hatch_mode 23))
              (progn 
                (setq hatch_patt_ "000_W23")
                (setq hatch_color_ 3)
                (princ hatch_patt_)
              )
            )
            ( ;hatctpatt_case_
              (and (= hatch_mode 24))
              (progn 
                (setq hatch_patt_ "000_W24")
                (setq hatch_color_ 3)
                (princ hatch_patt_)
              )
            )
            ( ;hatctpatt_case_
              (and (= hatch_mode 25))
              (progn 
                (setq hatch_patt_ "000_W25")
                (setq hatch_color_ 3)
                (princ hatch_patt_)
              )
            )
            ( ;hatctpatt_case_
              (and (= hatch_mode 26))
              (progn 
                (setq hatch_patt_ "000_W26")
                (setq hatch_color_ 3)
                (princ hatch_patt_)
              )
            )
            ( ;hatctpatt_case_
              (and (= hatch_mode 27))
              (progn 
                (setq hatch_patt_ "000_W27")
                (setq hatch_color_ 3)
                (princ hatch_patt_)
              )
            )
            ( ;hatctpatt_case_
              (and (= hatch_mode 28))
              (progn 
                (setq hatch_patt_ "000_W28")
                (setq hatch_color_ 3)
                (princ hatch_patt_)
              )
            )
            ( ;hatctpatt_case_
              (and (= hatch_mode 29))
              (progn 
                (setq hatch_patt_ "000_W29")
                (setq hatch_color_ 3)
                (princ hatch_patt_)
              )
            )
            ( ;hatctpatt_case_
              (and (= hatch_mode 30))
              (progn 
                (setq hatch_patt_ "000_W30")
                (setq hatch_color_ 3)
                (princ hatch_patt_)
              )
            )
          )
        )
        
        (setq hatch_background_ 250)
      ;
      ; (setq hatch_ename_getang_ (cond ( (getreal (strcat "\nspecify angle<" (rtos (setq hatch_ename_getang_ (cond (hatch_ename_getang_) (hatch_ename_getsc_) ) ) ) "> : " ) ) ) (hatch_ename_getang_) ) )
      ; (setq hatch_ename_getsc_ (cond ( (getreal (strcat "\nspecify scale<" (rtos (setq hatch_ename_getsc_ (cond (hatch_ename_getsc_) (hatch_ename_getsc_) ) ) ) "> : " ) ) ) (hatch_ename_getsc_) ) )

      (setq hatch_obj_ (vlax-ename->vla-object hatch_ename_))
      
      
      (command ".-hatch" "s"  hatch_ename_  
                "" 
                "c" hatch_color_ hatch_background_
                "p" hatch_patt_ hatch_ename_getsc_ hatch_ename_getang_ 
                "L" hatch_Layer_ 
                ""  
                ""
      )
      
      
      
    )
    (defun c:hatch_obj_Metal_HHM_ ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - H A T C H")
        (setq hatch_patt_ "ANSI32")
        (setq hatch_color_ 8)
        (setq hatch_background_ 250)
        
      ;
      (setq hatch_ename_getang_ (cond ( (getreal (strcat "\nspecify angle<" (rtos (setq hatch_ename_getang_ (cond (hatch_ename_getang_) (hatch_ename_getsc_) ) ) ) "> : " ) ) ) (hatch_ename_getang_) ) )
      (setq hatch_ename_getsc_ (cond ( (getreal (strcat "\nspecify scale<" (rtos (setq hatch_ename_getsc_ (cond (hatch_ename_getsc_) (hatch_ename_getsc_) ) ) ) "> : " ) ) ) (hatch_ename_getsc_) ) )
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               
      )
      
      
      
    )
    (defun c:hatch_obj_Metal_HHM1_ ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - CONCRETE_PRECAST_HATCH_")
        (setq hatch_patt_ "ANSI31")
        (setq hatch_color_ 1)
        (setq hatch_background_ ".")
        (setq hatch_ename_getang_ 0 )
        (setq hatch_ename_getsc_ 30 )
      ;
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               
      )
      
      
      
    )
    (defun c:hatch_obj_Metal_HHM2_ ()
      ;user_input_
      (setvar "osmode" 0)
      (setq obj_name_ (vla-get-objectname (vlax-ename->vla-object (car (setq hatch_ename_ (nentsel "specify Object"))))))
      (cond
        ( ;first process
          (or
            
            (= obj_name_ "AcDbPolyline")
          )
          (progn
            (= (vla-get-closed (setq hatch_ename_obj_ (vlax-ename->vla-object (car hatch_ename_)))) :vlax-true)
            (setq 1st_process "AcDbPolyline")
          )
        )
        (;first process
          (or
            (= obj_name_ "AcDbBlockReference")
          )
          (progn
            (setq 1st_process "AcDbBlockReference")
            
          )
        )
      )
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - H A T C H")
        (setq hatch_patt_ "ANSI38")
        (setq hatch_color_ 251)
        (setq hatch_background_ ".")
        (setq hatch_ename_getang_ 0 )
        (setq hatch_ename_getsc_ 50 )
      ;
      (setq hatch_obj_ (vlax-ename->vla-object (car hatch_ename_)))
      (create-plines (nth 1 (TA:Get_Pline_vertext_ins_point_ (car hatch_ename_))) "close")
      ;new_blk_entlast object
        (car (nth 1 ( TA:Get_Pline_vertext_ins_point_ (entlast))))
      ;
      (setq hatch_obj_ins (vlax-safearray->list (vlax-variant-value (vla-get-insertionpoint (vlax-ename->vla-object (nth 0 (car (reverse hatch_ename_))))))))
      (vla-move 
        (vlax-ename->vla-object (setq kuy_mk (entlast)))
        (vlax-3d-point 0 0 0 )
        (vlax-3d-point hatch_obj_ins)
        
      )
      (command ".-hatch" "s"  (entlast)  
                "" 
                "c" hatch_color_ hatch_background_
                "p" hatch_patt_ hatch_ename_getsc_ hatch_ename_getang_ 
                "L" hatch_Layer_ 
                ""  
               
      )
      
      ; (command "erase" kuy_mk "")
      (setvar "osmode" 1215)
    )
    (defun c:hatch_obj_Subfame_HHSF_ ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - H A T C H")
        (setq hatch_patt_ "000_GL1200")
        (setq hatch_color_ 6)
        (setq hatch_background_ ".")
        
      ;
      ; (setq hatch_ename_getang_ (cond ( (getreal (strcat "\nspecify angle<" (rtos (setq hatch_ename_getang_ (cond (hatch_ename_getang_) (hatch_ename_getsc_) ) ) ) "> : " ) ) ) (hatch_ename_getang_) ) )
      (setq hatch_ename_getang_ 270 )
      ; (setq hatch_ename_getsc_ (cond ( (getreal (strcat "\nspecify scale<" (rtos (setq hatch_ename_getsc_ (cond (hatch_ename_getsc_) (hatch_ename_getsc_) ) ) ) "> : " ) ) ) (hatch_ename_getsc_) ) )
      (setq hatch_ename_getsc_ 1 )
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                "T" 40
                ""
      )
      ; (vla-setpattern (setq s_obj_ (vlax-ename->vla-object (entlast))) acHatchPatternTypePreDefined "solid") 
    )
    (defun c:hatch_obj_Solid_HHSolid_ ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - H A T C H")
        (setq hatch_patt_ "ANSI32")
        (setq hatch_color_ 250)
        (setq hatch_background_ 250)
        
      ;
      (setq hatch_ename_getang_ (cond ( (getreal (strcat "\nspecify angle<" (rtos (setq hatch_ename_getang_ (cond (hatch_ename_getang_) (hatch_ename_getsc_) ) ) ) "> : " ) ) ) (hatch_ename_getang_) ) )
      (setq hatch_ename_getsc_ (cond ( (getreal (strcat "\nspecify scale<" (rtos (setq hatch_ename_getsc_ (cond (hatch_ename_getsc_) (hatch_ename_getsc_) ) ) ) "> : " ) ) ) (hatch_ename_getsc_) ) )
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
      )
      (vla-setpattern (setq s_obj_ (vlax-ename->vla-object (entlast))) acHatchPatternTypePreDefined "solid") 
    )
    (defun c:hatch_obj_Dot_HHCON_ ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - H A T C H")
        (setq hatch_patt_ "AR-CONC")
        (setq hatch_color_ 8)
        (setq hatch_background_ 250)
        
      ;
      (setq hatch_ename_getang_ (cond ( (getreal (strcat "\nspecify angle<" (rtos (setq hatch_ename_getang_ (cond (hatch_ename_getang_) (hatch_ename_getsc_) ) ) ) "> : " ) ) ) (hatch_ename_getang_) ) )
      (setq hatch_ename_getsc_ (cond ( (getreal (strcat "\nspecify scale<" (rtos (setq hatch_ename_getsc_ (cond (hatch_ename_getsc_) (hatch_ename_getsc_) ) ) ) "> : " ) ) ) (hatch_ename_getsc_) ) )
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
      )
      
      
    )
    (defun c:hatch_obj_Dot_HHD_ ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setq hatch_Layer_ "000 - H A T C H")
        (setq hatch_patt_ "DOTS")
        (setq hatch_color_ 8)
        (setq hatch_background_ 250)
        
      ;
      (setq hatch_ename_getang_ (cond ( (getreal (strcat "\nspecify angle<" (rtos (setq hatch_ename_getang_ (cond (hatch_ename_getang_) (hatch_ename_getsc_) ) ) ) "> : " ) ) ) (hatch_ename_getang_) ) )
      (setq hatch_ename_getsc_ (cond ( (getreal (strcat "\nspecify scale<" (rtos (setq hatch_ename_getsc_ (cond (hatch_ename_getsc_) (hatch_ename_getsc_) ) ) ) "> : " ) ) ) (hatch_ename_getsc_) ) )
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
      )
      
      
    )
    (defun c:multi_hatch_obj_MHB ()
      ;selection_set
        (if  ;pre_select_ssget_or_post_select_ssget
          (= 
            (setq ss_pre_filter_set_xx_ (ssget "I" 
                                              (list 
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "lwpolyline") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      ;user_input_data_
        (if 
          (and 
            (= hatch_ename_getang_ nil)
            (= hatch_ename_getsc_ nil)
          )
          (progn
            (setq  hatch_ename_getang_ 0)
            (setq  hatch_ename_getsc_ 1)
            
          )
        )
        (setq hatch_ename_getang_ (cond ( (getreal (strcat "\nspecify angle<" (rtos (setq hatch_ename_getang_ (cond (hatch_ename_getang_) (hatch_ename_getsc_) ) ) ) "> : " ) ) ) (hatch_ename_getang_) ) )
        (setq hatch_ename_getsc_ (cond ( (getreal (strcat "\nspecify scale<" (rtos (setq hatch_ename_getsc_ (cond (hatch_ename_getsc_) (hatch_ename_getsc_) ) ) ) "> : " ) ) ) (hatch_ename_getsc_) ) )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))

            (TA:create_hatch_ ss_pre_filter_set_xx_ename_ hatch_ename_getang_ hatch_ename_getsc_)  

          (setq ss_pre_filter_set_xx_i (+ ss_pre_filter_set_xx_i 1))
        )
      ;
    )
    (defun c:multi_hatch_obj_MHB2 ()
      ;hatch_setting_value_
        (setq hatch_Layer_ "000 - H A T C H")
        (setq hatch_patt_ (getstring (strcat "\nSpecify Pattern name <" (if hatch_patt_ hatch_patt_ "") ">: ") ) )
        (setq hatch_patt_ (if (/= hatch_patt_ "") (progn (setq hatch_patt_ hatch_patt_) (setq hatch_patt_pre hatch_patt_) ) (setq hatch_patt_ hatch_patt_pre ) ))
        (setq hatch_color_ 8)
        (setq hatch_background_ 250)
      ;
      ; ;selection_set
      ;   (if  ;pre_select_ssget_or_post_select_ssget
      ;     (= 
      ;       (setq ss_pre_filter_set_xx_ (ssget "I" 
      ;                                         (list 
      ;                                           (cons 0 "lwpolyline") ;type of object
      ;                                           ; (cons 8 "000 - GRID")   ;kind of layer
      ;                                           ; (cons 2 "000-GRID_LINE_DYN")       ;kind of nameblock
      ;                                           ; (cons 62 1)           ;kind of color call sign with color code index
      ;                                         )
      ;                                   )
      ;       )
      ;       nil
      ;     )
      ;     (progn 
      ;       (setq ss_pre_filter_set_xx_ (ssget 
      ;                                     (list 
      ;                                       (cons 0 "lwpolyline") ;type of object
      ;                                       ; (cons 8 "000 - GRID")   ;kind of layer
      ;                                       ; (cons 2 "000-GRIDLINE_DYN")       ;kind of nameblock
      ;                                       ; (cons 62 1)           ;kind of color call sign with color code index
      ;                                     )
      ;                                   )
      ;       )
      ;     )
      ;     (sslength ss_pre_filter_set_xx_)
      ;   )
      ; ;
      ;user_input_data_
        (if 
          (and 
            (= hatch_ename_getang_ nil)
            (= hatch_ename_getsc_ nil)
          )
          (progn
            (setq  hatch_ename_getang_ 0)
            (setq  hatch_ename_getsc_ 1)
            
          )
        )
        (setq hatch_ename_getang_ (cond ( (getreal (strcat "\nspecify angle<" (rtos (setq hatch_ename_getang_ (cond (hatch_ename_getang_) (hatch_ename_getsc_) ) ) ) "> : " ) ) ) (hatch_ename_getang_) ) )
        (setq hatch_ename_getsc_ (cond ( (getreal (strcat "\nspecify scale<" (rtos (setq hatch_ename_getsc_ (cond (hatch_ename_getsc_) (hatch_ename_getsc_) ) ) ) "> : " ) ) ) (hatch_ename_getsc_) ) )
      ;
      ;preloop_and_while
        ; (setq ss_pre_filter_set_xx_i 0)
        ; (while (< ss_pre_filter_set_xx_i (sslength ss_pre_filter_set_xx_))
        ;   (setq ss_pre_filter_set_xx_ename_ (ssname ss_pre_filter_set_xx_ ss_pre_filter_set_xx_i))

            (command "_-hatch" pause
            )  


            ;new_blk_entlast object
              (setq newhatch_ename (entlast))
              (setq newhatch_obj_ (vlax-ename->vla-object newhatch_ename))
              (command "_-hatchedit" newhatch_ename "P" hatch_patt_ hatch_ename_getsc_ hatch_ename_getang_   )
              (command "_-hatchedit" newhatch_ename "Co" hatch_color_ hatch_background_  )
            ;

              

        ;   (setq ss_pre_filter_set_xx_i (+ ss_pre_filter_set_xx_i 1))
        ; )
      ;
    )
    (defun c:multi_hatch_obj_MHB3 ()
      ;hatch_setting_value_
        (setq hatch_Layer_ "000 - H A T C H")
        (setq hatch_mode (cond ( (getint (strcat "\nspecify hatch_mode <" (rtos (setq hatch_mode (cond (hatch_mode) (1.0) ) ) ) "> : " ) ) ) (hatch_mode) ) )       
        (setq hatch_color_ 8)
        (setq hatch_background_ 250)
      ;
      ;selection_set
        (if  ;pre_select_ssget_or_post_select_ssget
          (= 
            (setq ss_pre_filter_set_xx_ (ssget "I" 
                                              (list 
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "lwpolyline,region") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      ;user_input_data_
        (if 
          (and 
            (= hatch_ename_getang_ nil)
            (= hatch_ename_getsc_ nil)
          )
          (progn
            (setq  hatch_ename_getang_ 0)
            (setq  hatch_ename_getsc_ 1)
            
          )
        )
         
        ;(setq hatch_ename_getang_ (cond ( (getreal (strcat "\nspecify angle<" (rtos (setq hatch_ename_getang_ (cond (hatch_ename_getang_) (hatch_ename_getsc_) ) ) ) "> : " ) ) ) (hatch_ename_getang_) ) ) ;ปิดใช้งานไปก่อน ให้ใช้ 45degree 750sc
        (setq hatch_ename_getang_ 45 )
        ;(setq hatch_ename_getsc_ (cond ( (getreal (strcat "\nspecify scale<" (rtos (setq hatch_ename_getsc_ (cond (hatch_ename_getsc_) (hatch_ename_getsc_) ) ) ) "> : " ) ) ) (hatch_ename_getsc_) ) )
        (setq hatch_ename_getsc_ 300 )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))

            (TAS:create_hatch_PPLINE_ ss_pre_filter_set_xx_ename_ hatch_ename_getang_ hatch_ename_getsc_ hatch_mode)    

          (setq ss_pre_filter_set_xx_i (+ ss_pre_filter_set_xx_i 1))
        )
      ;
    )
    (defun c:multi_hatch_obj_MHB4 ()
      
      ;selection_set
        (if  ;pre_select_ssget_or_post_select_ssget
          (= 
            (setq ss_pre_filter_set_xx_ (ssget "I" 
                                              (list 
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "lwpolyline") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      ;hatch_setting_value_
        (setq hatch_Layer_ "000 - H A T C H")
        (setq hatch_mode (cond ( (getint (strcat "\nspecify hatch_mode <" (rtos (setq hatch_mode (cond (hatch_mode) (1.0) ) ) ) "> : " ) ) ) (hatch_mode) ) )       
        (setq hatch_color_ 8)
        (setq hatch_background_ 250)
      ;
      ;user_input_data_
        (if 
          (and 
            (= hatch_ename_getang_ nil)
            (= hatch_ename_getsc_ nil)
          )
          (progn
            (setq  hatch_ename_getang_ 0)
            (setq  hatch_ename_getsc_ 1)
            
          )
        )
         
        ; (setq hatch_ename_getang_ (cond ( (getreal (strcat "\nspecify angle<" (rtos (setq hatch_ename_getang_ (cond (hatch_ename_getang_) (hatch_ename_getsc_) ) ) ) "> : " ) ) ) (hatch_ename_getang_) ) )
        (setq hatch_ename_getang_ 45 )
        (setq hatch_ename_getsc_ 750 )
        ; (setq hatch_ename_getsc_ (cond ( (getreal (strcat "\nspecify scale<" (rtos (setq hatch_ename_getsc_ (cond (hatch_ename_getsc_) (hatch_ename_getsc_) ) ) ) "> : " ) ) ) (hatch_ename_getsc_) ) )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))

            (TAS:create_Wallhatch_PPLINE_ ss_pre_filter_set_xx_ename_ hatch_ename_getang_ hatch_ename_getsc_ hatch_mode)    

          (setq ss_pre_filter_set_xx_i (+ ss_pre_filter_set_xx_i 1))
        )
      ;
    )
    (defun c:select_hacth_SFH ()
      ;selection_set
        (if  ;pre_select_ssget_or_post_select_ssget
          (= 
            (setq ss_pre_filter_set_xx_ (ssget "I" 
                                              (list 
                                                (cons 0 "hatch") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "hatch") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      (command "pselect" ss_pre_filter_set_xx_ "" ) 
    )
    (defun c:Recrete_hatch_SSRHB_ ()
      ;selection_set_for_fillter_blk_name
        (if  ;pre_select_ssget_or_post_select_ssget
          (=
            (setq ss_pre_filter_set_xx_ (ssget "i"
                                              (list
                                                (cons 0 "HATCH") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "HATCH") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          
          (command "_-hatchedit" ss_pre_filter_set_xx_ename_  "B" "" "Y")
          
          
          (setq ss_pre_filter_set_xx_i (+ ss_pre_filter_set_xx_i 1))
        )
      ;
    )
    (defun c:hatch_orgin_move_axis_X_HHX ()
      ;set paremeter for moving
        (setq move_length_ 25)
      ;
      ;user_input_
        (initget "Yes No")
        (setq ss_ ;Detect the variable's result in case of a function error
          (vl-catch-all-apply 
            (function 
              (lambda () 
                (setq DELETE_OBJ_ (not (eq "No" (getkword "\nKeep Existing point with object? [Yes/No] <Y>: "))))
              )
            )
          )
        )
      ;
      (cond
        (;delete_case_1
          (and
              (= DELETE_OBJ_ nil)
          )
          (progn
            (setq ssset_ (ssget))
            (princ "delete_case_1")
          )
        )
        (;delete_case_2
          (and
              (= DELETE_OBJ_ nil)
          )
          (progn
            (setq ssset_ ssset_)
            (princ "delete_case_2")
          )
        )
      )
      
      (while
        (= ;condition
          (wcmatch 
            (vl-princ-to-string 
              (setq direction_val_ ;Detect the variable's result in case of a function error
                (vl-catch-all-apply 
                  (function 
                    (lambda () 
                      (setq direction_ (cond ( (getint (strcat "\nspecify get\n1 = +\n0 = -\n<" (rtos (setq direction_ (cond (direction_) (1.0) ) ) ) "> : " ) ) ) (direction_) ) )
                    )
                  )
                )
              )
            ) 
            "*error*"
          )
          nil
        )
        ;properties hacth
          (setq ssset_ename_ (ssname ssset_ 0))
          (setq ssset_obj_ (vlax-ename->vla-object ssset_ename_))
          (setq ssset_obj_origin_ (vlax-safearray->list 
                                  (vlax-variant-value (vla-get-origin ssset_obj_))
                                )
          )
        ;
        (cond
          (
            (and 
              (/= ssset_ nil)
              (= direction_val_ 1)
            )
            (setq sss_obj_putins_ (list 
                                    (+ (car ssset_obj_origin_) move_length_)
                                    (cadr ssset_obj_origin_)
                                    0
                                  )
            )
            (command "HATCHSETORIGIN" ssset_ "" sss_obj_putins_ )
          )
          (
            (and 
              (/= ssset_ nil)
              (= direction_val_ 0)
            )
            (setq sss_obj_putins_ (list 
                                    (- (car ssset_obj_origin_) move_length_)
                                    (cadr ssset_obj_origin_)
                                    0
                                  )
            )
            (command "HATCHSETORIGIN" ssset_ "" sss_obj_putins_ )
          )
        )
        
      )
    )
    (defun c:hatch_orgin_move_axis_Y_HHY ()
      ;set paremeter for moving
        (setq move_length_ 25)
      ;
      ;user_input_
        (initget "Yes No")
        (setq ss_ ;Detect the variable's result in case of a function error
          (vl-catch-all-apply 
            (function 
              (lambda () 
                (setq DELETE_OBJ_ (not (eq "No" (getkword "\nKeep Existing point with object? [Yes/No] <Y>: "))))
              )
            )
          )
        )
      ;
      (cond
        (;delete_case_1
          (and
              (= DELETE_OBJ_ nil)
          )
          (progn
            (setq ssset_ (ssget))
            (princ "delete_case_1")
          )
        )
        (;delete_case_2
          (and
              (= DELETE_OBJ_ nil)
          )
          (progn
            (setq ssset_ ssset_)
            (princ "delete_case_2")
          )
        )
      )
      
      (while
        (= ;condition
          (wcmatch 
            (vl-princ-to-string 
              (setq direction_val_ ;Detect the variable's result in case of a function error
                (vl-catch-all-apply 
                  (function 
                    (lambda () 
                      (setq direction_ (cond ( (getint (strcat "\nspecify get\n1 = +\n0 = -\n<" (rtos (setq direction_ (cond (direction_) (1.0) ) ) ) "> : " ) ) ) (direction_) ) )
                    )
                  )
                )
              )
            ) 
            "*error*"
          )
          nil
        )
        ;properties hacth
          (setq ssset_ename_ (ssname ssset_ 0))
          (setq ssset_obj_ (vlax-ename->vla-object ssset_ename_))
          (setq ssset_obj_origin_ (vlax-safearray->list 
                                  (vlax-variant-value (vla-get-origin ssset_obj_))
                                )
          )
        ;
        (cond
          (
            (and 
              (/= ssset_ nil)
              (= direction_val_ 1)
            )
            (setq sss_obj_putins_ (list 
                                    (car ssset_obj_origin_)
                                    (+ (cadr ssset_obj_origin_) move_length_)
                                    0
                                  )
            )
            (command "HATCHSETORIGIN" ssset_ "" sss_obj_putins_ )
          )
          (
            (and 
              (/= ssset_ nil)
              (= direction_val_ 0)
            )
            (setq sss_obj_putins_ (list 
                                    (car ssset_obj_origin_)
                                    (- (cadr ssset_obj_origin_) move_length_)
                                    0
                                  )
            )
            (command "HATCHSETORIGIN" ssset_ "" sss_obj_putins_ )
          )
        )
        
      )
    )
    (defun c:ins-mul-hatch_mul04 ()
      ;preseting_data_
        (setq hatch_Layer_ "000_AREA_C04_HATCH_")
        (setq hatch_patt_ "000_C04")
        (setq hatch_color_ 251)
        (setq hatch_background_ ".")
        (setq hatch_ename_getang_ 45 )
        (setq hatch_ename_getsc_ 250 )
      ;
      ;selection_set_for_fillter_blk_name
        (if  ;pre_select_ssget_or_post_select_ssget
          (=
            (setq ss_pre_filter_set_xx_ (ssget "i"
                                              (list
                                                (cons 0 "lwpolyline") ;type of object
                                                (cons 8 "000_AREA_C04_MAIN_COLOR_1")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "lwpolyline") ;type of object
                                                (cons 8 "000_AREA_C04_MAIN_COLOR_1")   ;kind of layer
                                                ; (cons 2 "000-GRID_LINE_DYN")       ;kind of nameblock
                                                ; (cons 62 1)           ;kind of color call sign with color code index
                                              )
                                        )
            )
          )
          (sslength ss_pre_filter_set_xx_)
        )
      ;
      
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (command ".-hatch" "s"  ss_pre_filter_set_xx_ename_ 
                    "" 
                    "c" hatch_color_ hatch_background_
                    "p" hatch_patt_ hatch_ename_getsc_ hatch_ename_getang_ 
                    "L" hatch_Layer_ 
                    ""  
                    ""  
                    ""  
                    ""  

          )
          (setq ss_pre_filter_set_xx_i (+ ss_pre_filter_set_xx_i 1))
        )
      ;
    )
    (defun c:ins-mul-hatch_mul05 ()
      ;preseting_data_
        (setq hatch_Layer_ "000_AREA_C05_HATCH_")
        (setq hatch_patt_ "000_C05")
        (setq hatch_color_ 251)
        (setq hatch_background_ ".")
        (setq hatch_ename_getang_ 45 )
        (setq hatch_ename_getsc_ 250 )
      ;
      ;selection_set_for_fillter_blk_name
        (if  ;pre_select_ssget_or_post_select_ssget
          (=
            (setq ss_pre_filter_set_xx_ (ssget "i"
                                              (list
                                                (cons 0 "lwpolyline") ;type of object
                                                (cons 8 "000_AREA_C05_MAIN_COLOR_1")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "lwpolyline") ;type of object
                                                (cons 8 "000_AREA_C05_MAIN_COLOR_1")   ;kind of layer
                                                ; (cons 2 "000-GRID_LINE_DYN")       ;kind of nameblock
                                                ; (cons 62 1)           ;kind of color call sign with color code index
                                              )
                                        )
            )
          )
          (sslength ss_pre_filter_set_xx_)
        )
      ;
      
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (command ".-hatch" "s"  ss_pre_filter_set_xx_ename_ 
                    "" 
                    "c" hatch_color_ hatch_background_
                    "p" hatch_patt_ hatch_ename_getsc_ hatch_ename_getang_ 
                    "L" hatch_Layer_ 
                    ""  
                    ""  
                    ""  
                    ""  

          )
          (setq ss_pre_filter_set_xx_i (+ ss_pre_filter_set_xx_i 1))
        )
      ;
    )
    (defun c:ins-mul-hatch_mul06 ()
      ;preseting_data_
        (setq hatch_Layer_ "000_AREA_C06_HATCH_")
        (setq hatch_patt_ "000_C06")
        (setq hatch_color_ 251)
        (setq hatch_background_ ".")
        (setq hatch_ename_getang_ 45 )
        (setq hatch_ename_getsc_ 250 )
      ;
      ;selection_set_for_fillter_blk_name
        (if  ;pre_select_ssget_or_post_select_ssget
          (=
            (setq ss_pre_filter_set_xx_ (ssget "i"
                                              (list
                                                (cons 0 "lwpolyline") ;type of object
                                                (cons 8 "000_AREA_C06_MAIN_COLOR_1")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "lwpolyline") ;type of object
                                                (cons 8 "000_AREA_C06_MAIN_COLOR_1")   ;kind of layer
                                                ; (cons 2 "000-GRID_LINE_DYN")       ;kind of nameblock
                                                ; (cons 62 1)           ;kind of color call sign with color code index
                                              )
                                        )
            )
          )
          (sslength ss_pre_filter_set_xx_)
        )
      ;
      
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (command ".-hatch" "s"  ss_pre_filter_set_xx_ename_ 
                    "" 
                    "c" hatch_color_ hatch_background_
                    "p" hatch_patt_ hatch_ename_getsc_ hatch_ename_getang_ 
                    "L" hatch_Layer_ 
                    ""  
                    ""  
                    ""  
                    ""  

          )
          (setq ss_pre_filter_set_xx_i (+ ss_pre_filter_set_xx_i 1))
        )
      ;
    )
    (defun c:ins-mul-hatch_mul08 ()
      ;preseting_data_
        (setq hatch_Layer_ "000_AREA_C08_HATCH_")
        (setq hatch_patt_ "000_C08")
        (setq hatch_color_ 251)
        (setq hatch_background_ ".")
        (setq hatch_ename_getang_ 45 )
        (setq hatch_ename_getsc_ 250 )
      ;
      ;selection_set_for_fillter_blk_name
        (if  ;pre_select_ssget_or_post_select_ssget
          (=
            (setq ss_pre_filter_set_xx_ (ssget "i"
                                              (list
                                                (cons 0 "lwpolyline") ;type of object
                                                (cons 8 "000_AREA_C08_MAIN_COLOR_1")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "lwpolyline") ;type of object
                                                (cons 8 "000_AREA_C08_MAIN_COLOR_1")   ;kind of layer
                                                ; (cons 2 "000-GRID_LINE_DYN")       ;kind of nameblock
                                                ; (cons 62 1)           ;kind of color call sign with color code index
                                              )
                                        )
            )
          )
          (sslength ss_pre_filter_set_xx_)
        )
      ;
      
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (command ".-hatch" "s"  ss_pre_filter_set_xx_ename_ 
                    "" 
                    "c" hatch_color_ hatch_background_
                    "p" hatch_patt_ hatch_ename_getsc_ hatch_ename_getang_ 
                    "L" hatch_Layer_ 
                    ""  
                    ""  
                    ""  
                    ""  

          )
          (setq ss_pre_filter_set_xx_i (+ ss_pre_filter_set_xx_i 1))
        )
      ;
    )
    (defun c:ckst_mk_hatch_area ()
      (setvar "CMDECHO" 0)
      ;preseting_data_
        ; (setq hatch_Layer_ "000_AREA_C08_HATCH_")
        ; (setq hatch_patt_ "000_C08")
        (setq hatch_color_ "bylayer")
        (setq hatch_background_ ".")
        (setq hatch_ename_getang_ 45 )
        (setq hatch_ename_getsc_ 1000 )
      ;
      ;selection_set_for_fillter_blk_name
        (if  ;pre_select_ssget_or_post_select_ssget
          (=
            (setq ss_pre_filter_set_xx_ (ssget "i"
                                              (list
                                                (cons 0 "lwpolyline") ;type of object
                                                (cons 8 "000_AREA_C02_MAIN_COLOR_1,000_AREA_C03_MAIN_COLOR_1,000_AREA_C04_MAIN_COLOR_1,000_AREA_C05_MAIN_COLOR_1,000_AREA_C06_MAIN_COLOR_1,000_AREA_C07_MAIN_COLOR_1,000_AREA_C08_MAIN_COLOR_1,000_AREA_C09_MAIN_COLOR_1,000_AREA_C10_MAIN_COLOR_1,000_AREA_C11_MAIN_COLOR_1")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "lwpolyline") ;type of object
                                                (cons 8 "000_AREA_C02_MAIN_COLOR_1,000_AREA_C03_MAIN_COLOR_1,000_AREA_C04_MAIN_COLOR_1,000_AREA_C05_MAIN_COLOR_1,000_AREA_C06_MAIN_COLOR_1,000_AREA_C07_MAIN_COLOR_1,000_AREA_C08_MAIN_COLOR_1,000_AREA_C09_MAIN_COLOR_1,000_AREA_C10_MAIN_COLOR_1,000_AREA_C11_MAIN_COLOR_1")   ;kind of layer
                                                ; (cons 2 "000-GRID_LINE_DYN")       ;kind of nameblock
                                                ; (cons 62 1)           ;kind of color call sign with color code index
                                              )
                                        )
            )
          )
          
        )
      ;
      ;preloop_and_while
        (setq ss_pre_filter_set_xx_i 0)
        (while (and 
                 (/= ss_pre_filter_set_xx_ nil)
                 (< ss_pre_filter_set_xx_i (sslength ss_pre_filter_set_xx_))
               )
          (setq ss_pre_filter_set_xx_ename_ (ssname ss_pre_filter_set_xx_ ss_pre_filter_set_xx_i))
          (setq ss_pre_filter_set_xx_obj_ (vlax-ename->vla-object  ss_pre_filter_set_xx_ename_))
          (setq hatch_patt_ nil)
          (setq hatch_Layer_ nil)
          (cond
            (;_case_1
               (and
                  (= (vla-get-layer ss_pre_filter_set_xx_obj_) "000_AREA_C02_MAIN_COLOR_1")
               )
               (progn
                 (setq hatch_patt_ "000_C02")
                 (setq hatch_Layer_ "000_AREA_C02_HATCH_")
               )
            )
            (;_case_2
               (and
                  (= (vla-get-layer ss_pre_filter_set_xx_obj_) "000_AREA_C03_MAIN_COLOR_1")
               )
               (progn
                 (setq hatch_patt_ "000_C03")
                 (setq hatch_Layer_ "000_AREA_C03_HATCH_")
               )
            )
            (;_case_3
               (and
                  (= (vla-get-layer ss_pre_filter_set_xx_obj_) "000_AREA_C04_MAIN_COLOR_1")
               )
               (progn
                 (setq hatch_patt_ "000_C04")
                 (setq hatch_Layer_ "000_AREA_C04_HATCH_")
               )
            )
            (;_case_4
               (and
                  (= (vla-get-layer ss_pre_filter_set_xx_obj_) "000_AREA_C05_MAIN_COLOR_1")
               )
               (progn
                 (setq hatch_patt_ "000_C05")
                 (setq hatch_Layer_ "000_AREA_C05_HATCH_")
               )
            )
            (;_case_4
               (and
                  (= (vla-get-layer ss_pre_filter_set_xx_obj_) "000_AREA_C06_MAIN_COLOR_1")
               )
               (progn
                 (setq hatch_patt_ "000_C06")
                 (setq hatch_Layer_ "000_AREA_C06_HATCH_")
               )
            )
            (;_case_4
               (and
                  (= (vla-get-layer ss_pre_filter_set_xx_obj_) "000_AREA_C07_MAIN_COLOR_1")
               )
               (progn
                 (setq hatch_patt_ "000_C07")
                 (setq hatch_Layer_ "000_AREA_C07_HATCH_")
               )
            )
            (;_case_4
               (and
                  (= (vla-get-layer ss_pre_filter_set_xx_obj_) "000_AREA_C08_MAIN_COLOR_1")
               )
               (progn
                 (setq hatch_patt_ "000_C08")
                 (setq hatch_Layer_ "000_AREA_C08_HATCH_")
               )
            )
            (;_case_4
               (and
                  (= (vla-get-layer ss_pre_filter_set_xx_obj_) "000_AREA_C09_MAIN_COLOR_1")
               )
               (progn
                 (setq hatch_patt_ "000_C09")
                 (setq hatch_Layer_ "000_AREA_C09_HATCH_")
               )
            )
            (;_case_4
               (and
                  (= (vla-get-layer ss_pre_filter_set_xx_obj_) "000_AREA_C10_MAIN_COLOR_1")
               )
               (progn
                 (setq hatch_patt_ "000_C10")
                 (setq hatch_Layer_ "000_AREA_C10_HATCH_")
               )
            )
            (;_case_4
               (and
                  (= (vla-get-layer ss_pre_filter_set_xx_obj_) "000_AREA_C11_MAIN_COLOR_1")
               )
               (progn
                 (setq hatch_patt_ "000_C11")
                 (setq hatch_Layer_ "000_AREA_C11_HATCH_")
               )
            )
          )
          (if (/= hatch_patt_ nil )
            (progn
              (command ".-hatch" "s"  ss_pre_filter_set_xx_ename_ 
                    "" 
                    "c" hatch_color_ hatch_background_
                    "p" hatch_patt_ hatch_ename_getsc_ hatch_ename_getang_ 
                    "L" hatch_Layer_ 
                    ""  
              )
            )
          )
          
          (setq ss_pre_filter_set_xx_i (+ ss_pre_filter_set_xx_i 1))
        )
      ;
    )
    (defun TA:create-multipleboundaryhatch_mulbohatch (ss_pre_filter_set_xx_ename_ )
      ;example for ssset
        ; ;selection_set_for_fillter_blk_name
        ;   (if  ;pre_select_ssget_or_post_select_ssget
        ;     (=
        ;       (setq ss_pre_filter_set_xx_ (ssget "i"
        ;                                         (list
        ;                                           (cons 0 "hatch") ;type of object
        ;                                           ; (cons 8 "000 - GRID")   ;kind of layer
        ;                                           ; (cons 2 "000-GRID_LINE_DYN")       ;kind of nameblock
        ;                                           ; (cons 62 1)           ;kind of color call sign with color code index
        ;                                         )
        ;                                   )
        ;       )
        ;       nil
        ;     )
        ;     (progn
        ;       (setq ss_pre_filter_set_xx_ (ssget
        ;                                         (list
        ;                                           (cons 0 "hatch") ;type of object
        ;                                           ; (cons 8 "000 - GRID")   ;kind of layer
        ;                                           ; (cons 2 "000-GRID_LINE_DYN")       ;kind of nameblock
        ;                                           ; (cons 62 1)           ;kind of color call sign with color code index
        ;                                         )
        ;                                   )
        ;       )
        ;     )
        ;     (sslength ss_pre_filter_set_xx_)
        ;   )
        ; ;
        ; ;preloop_and_while
        ;   (setq ss_pre_filter_set_xx_i 0)
        ;   (while (< ss_pre_filter_set_xx_i (sslength ss_pre_filter_set_xx_))
        ;     (setq ss_pre_filter_set_xx_ename_ (ssname ss_pre_filter_set_xx_ ss_pre_filter_set_xx_i))
        ;     (setq ss_pre_filter_set_xx_obj_ (vlax-ename->vla-object  ss_pre_filter_set_xx_ename_))
        ;     (command "_-hatchedit" ss_pre_filter_set_xx_ename_ "B" "p" "Y")
        ;     (setq ss_pre_filter_set_xx_i (+ ss_pre_filter_set_xx_i 1))
        ;   )
        ; ;
      ;
      
      (if (= (vla-get-objectname (vlax-ename->vla-object ss_pre_filter_set_xx_ename_ )) "AcDbHatch")
        (progn
          (command "_-hatchedit" ss_pre_filter_set_xx_ename_ "B" "p" "Y")
        )
        (print "not hatch object")
      )
    )
    (defun c:create-multipleboundaryhatch_mulbohatch ()
      ;selection_set_for_fillter_blk_name
        (if  ;pre_select_ssget_or_post_select_ssget
          (=
            (setq ss_pre_filter_set_xx_ (ssget "i"
                                              (list
                                                (cons 0 "hatch") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "hatch") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (TA:create-multipleboundaryhatch_mulbohatch ss_pre_filter_set_xx_ename_ )
          
          (setq ss_pre_filter_set_xx_i (+ ss_pre_filter_set_xx_i 1))
        )
      ;
    )
    (defun c:mulckstboline ()
      ;selection_set_for_fillter_blk_name
        (if  ;pre_select_ssget_or_post_select_ssget
          (=
            (setq ss_pre_filter_set_xx_ (ssget "i"
                                              (list
                                                (cons 0 "hatch") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "hatch") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (TA:create-multipleboundaryhatch_mulbohatch ss_pre_filter_set_xx_ename_ )
          (if (testexpr)
            (progn
              (thenexpr)
            )
          )
          (setq ss_pre_filter_set_xx_i (+ ss_pre_filter_set_xx_i 1))
        )
      ;
    )
    (defun c:ckst_sum_hatch_area ()
      ;selection_set_for_fillter_blk_name
        (if  ;pre_select_ssget_or_post_select_ssget
          (=
            (setq ss_pre_filter_set_xx_ (ssget "i"
                                              (list
                                                (cons 0 "hatch") ;type of object
                                                (cons 8 "000_AREA_C02_HATCH_,000_AREA_C03_HATCH_,000_AREA_C04_HATCH_,000_AREA_C05_HATCH_,000_AREA_C06_HATCH_,000_AREA_C07_HATCH_,000_AREA_C08_HATCH_,000_AREA_C09_HATCH_,000_AREA_C10_HATCH_,000_AREA_C11_HATCH_" )   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "hatch") ;type of object
                                                (cons 8 "000_AREA_C02_HATCH_,000_AREA_C03_HATCH_,000_AREA_C04_HATCH_,000_AREA_C05_HATCH_,000_AREA_C06_HATCH_,000_AREA_C07_HATCH_,000_AREA_C08_HATCH_,000_AREA_C09_HATCH_,000_AREA_C10_HATCH_,000_AREA_C11_HATCH_" )   ;kind of layer
                                                ; (cons 2 "000-GRID_LINE_DYN")       ;kind of nameblock
                                                ; (cons 62 1)           ;kind of color call sign with color code index
                                              )
                                        )
            ) 
          )
          (sslength ss_pre_filter_set_xx_) 
        )
      ;
      ;preloop_and_while_founding area error
        (setq ss_pre_filter_set_xx_i 0)
        (setq ss_for_error (ssadd))
        (setq Er-msg_ 0.00)
        (while 
              (and
                ;  (= (type Er-msg_ ) 'real)
                 (< ss_pre_filter_set_xx_i (sslength ss_pre_filter_set_xx_))
               )
          (setq ss_pre_filter_set_xx_ename_ (ssname ss_pre_filter_set_xx_ ss_pre_filter_set_xx_i))
          (setq ss_pre_filter_set_xx_obj_ (vlax-ename->vla-object  ss_pre_filter_set_xx_ename_))
          (setq Er-msg_
            (vl-catch-all-apply 
              (function 
                (lambda () 
                  (vla-get-area ss_pre_filter_set_xx_obj_)
                )
              )
            )
          )
          (if (= (type Er-msg_) 'VL-CATCH-ALL-APPLY-ERROR)
            (progn
              (setq ss_for_error (ssadd ss_pre_filter_set_xx_ename_ ss_for_error ))
            )
          )
          
    
          
          (setq ss_pre_filter_set_xx_i (+ ss_pre_filter_set_xx_i 1))
        )
      ;
      (if (/= (sslength ss_for_error) 0) (progn (command "pselect"  ss_for_error "" ) ) )
      (if (= (sslength ss_for_error) 0) 
        (progn  
          ;preloop_and_while
            (setq ss_pre_filter_set_xx_i 0)
            (setq ss_pre_filter_set_xx_obj_layer_list_ ())
            (while (and 
                      (= (type Er-msg_ ) 'real)
                      (< ss_pre_filter_set_xx_i (sslength ss_pre_filter_set_xx_))
                  )
              (setq ss_pre_filter_set_xx_ename_ (ssname ss_pre_filter_set_xx_ ss_pre_filter_set_xx_i)) 
              (setq ss_pre_filter_set_xx_obj_ (vlax-ename->vla-object  ss_pre_filter_set_xx_ename_))
              (setq temp (list 
                          (vla-get-layer ss_pre_filter_set_xx_obj_)
                          (/ (vla-get-area ss_pre_filter_set_xx_obj_) 1000000.0 )
                        )
              )
              (setq ss_pre_filter_set_xx_obj_layer_list_ (cons temp ss_pre_filter_set_xx_obj_layer_list_ )  )
              
              
              (setq ss_pre_filter_set_xx_i (+ ss_pre_filter_set_xx_i 1))
            )
          ;
          (setq ss_pre_filter_set_xx_obj_layer_list_ (cons (list "000_AREA_C02_HATCH_" 0) ss_pre_filter_set_xx_obj_layer_list_))
          (setq ss_pre_filter_set_xx_obj_layer_list_ (cons (list "000_AREA_C03_HATCH_" 0) ss_pre_filter_set_xx_obj_layer_list_))
          (setq ss_pre_filter_set_xx_obj_layer_list_ (cons (list "000_AREA_C04_HATCH_" 0) ss_pre_filter_set_xx_obj_layer_list_))
          (setq ss_pre_filter_set_xx_obj_layer_list_ (cons (list "000_AREA_C05_HATCH_" 0) ss_pre_filter_set_xx_obj_layer_list_))
          (setq ss_pre_filter_set_xx_obj_layer_list_ (cons (list "000_AREA_C06_HATCH_" 0) ss_pre_filter_set_xx_obj_layer_list_))
          (setq ss_pre_filter_set_xx_obj_layer_list_ (cons (list "000_AREA_C07_HATCH_" 0) ss_pre_filter_set_xx_obj_layer_list_))
          (setq ss_pre_filter_set_xx_obj_layer_list_ (cons (list "000_AREA_C08_HATCH_" 0) ss_pre_filter_set_xx_obj_layer_list_))
          (setq ss_pre_filter_set_xx_obj_layer_list_ (cons (list "000_AREA_C09_HATCH_" 0) ss_pre_filter_set_xx_obj_layer_list_))
          (setq ss_pre_filter_set_xx_obj_layer_list_ (cons (list "000_AREA_C10_HATCH_" 0) ss_pre_filter_set_xx_obj_layer_list_))
          (setq ss_pre_filter_set_xx_obj_layer_list_ (cons (list "000_AREA_C11_HATCH_" 0) ss_pre_filter_set_xx_obj_layer_list_))
          (setq Collection_hatch_val_ (TA:GroupSum_ ss_pre_filter_set_xx_obj_layer_list_ ))
          ;TA:stanndard_lambda_sorting
            (setq Collection_hatch_val_sorted_ (vl-sort Collection_hatch_val_  ;bigest open indent list
                                                      (function 
                                                        (lambda (a b) 
                                                          (< (car a) (car b))
                                                          ;(("000_AREA_C02_HATCH_" 29827.5) ("000_AREA_C03_HATCH_" 334326.0) ("000_AREA_C04_HATCH_" 1.64657e+06)) ;example format list data
                                                        )
                                                      )
                                  ) ;bigest close indent list
            )
          ;
          ;print_result_
            (princ (strcat "\n----"(LM:StringSubst "" ".dwg" (getvar "dwgname")) "----") )
            (princ "\n----Area Hatch Summary Report----")
            (princ "\n--------------------------------------------------------------------------------------------")
            (foreach item Collection_hatch_val_sorted_
              (princ (strcat "\nLayer : " (car item) "  |  Area (sq.m) : " (rtos (cadr item) 2 2) ) )
            )
            (princ "\n--------------------------------------------------------------------------------------------")
          
            (TA:copytext->clipboard (strcat 
                                      "----"(LM:StringSubst "" ".dwg" (getvar "dwgname")) "---"
                                      "\n----Area Hatch Summary Report----\n--------------------------------------------------------------------------------------------\n" 
                                      (apply 'strcat
                                        (mapcar 
                                          (function 
                                            (lambda (item) 
                                              (strcat "Layer : " (car item) "  |  Area (sq.m) : " (rtos (cadr item) 2 2) "\n" )
                                            )
                                          ) 
                                          Collection_hatch_val_sorted_
                                        )
                                      )
                                      "--------------------------------------------------------------------------------------------"
                            )
            )
          ;
        ) 
      )
    )
    (defun c:temptx ()
      (setvar "osmode" 1215)
      (command "ucs" "w")
      (setq getpoint_ref (getpoint "specify point for insert text"))
      (setvar "osmode" 0)
      (setq text_ename_ (car (entsel "specify Object")))
      (setq text_obj_ (vlax-ename->vla-object text_ename_))
      (vla-put-layer text_obj_ "0")
      (vla-put-height text_obj_ 1500)
      (vla-put-stylename text_obj_ "Arial")
      (vlax-dump-object text_obj_ )
      (vla-put-LineSpacingDistance  text_obj_ 2500)
      (vla-put-width  text_obj_ 80000)
      (setq text_obj_ins_ (vlax-safearray->list (vlax-variant-value (vla-get-insertionpoint text_obj_))))
      (setvar "osmode" 0)
      (vla-put-insertionpoint 
        text_obj_
        (vlax-3d-point 
          (- (car getpoint_ref) 70000.000000 )
          (- (cadr getpoint_ref) 2000.000000 )
          0
        )
      )
      (if (= (TA:if_found_block_ "A$C26be2c7e") T)
        (progn
          (TA:vla-insertblock
            "A$C26be2c7e"
            getpoint_ref
            1
            0
          )
        )
      )
      
      (setvar "osmode" 1215)
    )
    (defun  c:ckst_ck_hatch_Hlap ()
      ;selection_set_for_fillter_blk_name
        (if  ;pre_select_ssget_or_post_select_ssget
          (=
            (setq ss_pre_filter_set_xx_ (ssget "i"
                                              (list
                                                (cons 0 "hatch") ;type of object
                                                (cons 8 "000_AREA_C02_HATCH_,000_AREA_C03_HATCH_,000_AREA_C04_HATCH_,000_AREA_C05_HATCH_,000_AREA_C06_HATCH_,000_AREA_C07_HATCH_,000_AREA_C08_HATCH_,000_AREA_C09_HATCH_,000_AREA_C10_HATCH_,000_AREA_C11_HATCH_" )   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "hatch") ;type of object
                                                (cons 8 "000_AREA_C02_HATCH_,000_AREA_C03_HATCH_,000_AREA_C04_HATCH_,000_AREA_C05_HATCH_,000_AREA_C06_HATCH_,000_AREA_C07_HATCH_,000_AREA_C08_HATCH_,000_AREA_C09_HATCH_,000_AREA_C10_HATCH_,000_AREA_C11_HATCH_" )   ;kind of layer
                                                ; (cons 2 "000-GRID_LINE_DYN")       ;kind of nameblock
                                                ; (cons 62 1)           ;kind of color call sign with color code index
                                              )
                                        )
            ) 
          )
          (sslength ss_pre_filter_set_xx_) 
        )
      ;
      (if (= (LM:intersectionsinset ss_pre_filter_set_xx_) nil)
        (progn
          (alert "No Hatch Overlap Found!")
        )
        (alert "Hatch Overlap Found!")
      )
    )
    (defun c:ckst_hatch_origin_point_hori_ ()
      (if (= (ssget "i" (list (cons 0 "hatch") ) ) nil)
        (progn
          (setq e (car (entsel "\nSelect Hatch: ")))
        )
        (setq e (ssname (ssget (list (cons 0 "hatch") ) ) 0))
      )
      (if (/= e nil)
        (progn
          
          (setq d (entget e))
          
          (setq origin_x (cdr (assoc 43 d)))
          (setq origin_y (cdr (assoc 44 d)))
          (command "ucs"  "w")
          (command "ucs" (list origin_x  origin_y ) "")
        )
      )
      
    )
    (defun c:C03_input-acs ()
      (if (= (ssget "i" (list (cons 0 "hatch") ) ) nil)
        (progn
          
          (setq e (car (entsel "\nSelect Hatch: ")))
        )
        (setq e (ssname (ssget (list (cons 0 "hatch") ) ) 0))
      )
      (if (/= e nil)
        (progn
          (setq eori (vlax-safearray->list (vlax-variant-value (vla-get-Origin (vlax-ename->vla-object e)))))
          (setq d (entget e))
          (setq origin_x (cdr (assoc 43 d)))
          (setq origin_y (cdr (assoc 44 d)))
          (command "ucs"  "w")
          (command "ucs" (list origin_x  origin_y ) "")
        )
      )
      ;new_blk_entlast object clamp-rail
        (vla-copy (vlax-ename->vla-object e) )
        (setq e_ename (entlast))
        (setq e_obj (vlax-ename->vla-object e_ename))
        (vla-SetPattern e_obj 1 "000_GL600")
        (vla-put-color e_obj 1)
        
        (command "HATCHSETORIGIN" e_ename "" (trans (list 0  0 ) 0 1   ))
        
      ;
      ;new_blk_entlast object clamp-rail
        (vla-copy (vlax-ename->vla-object e) )
        (setq e_ename (entlast))
        (setq e_obj (vlax-ename->vla-object e_ename))
        (vla-SetPattern e_obj 1 "000_GL1200")
        (vla-put-color e_obj 3)
        
        (command "HATCHSETORIGIN" e_ename "" (trans (list 0  0 ) 0 1   ))
        
      ;
      ;
        
      ;
    )
    (defun TA:add_hatch_scale (sss_ename_ )
      (setq hatch_scale_list_ (list 
                               "1:1"
                               "1:2"
                               "1:5"
                               "1:10"
                               "1:20"
                               "1:25"
                               "1:50"
                               "1:75"
                               "1:100"
                               "1:500"
                             )
      )
      ; (setq sss_ename_ (car (entsel "specify Object")))
      ; (setq sss_obj_ (vlax-ename->vla-object sss_ename_))
      ; (vlax-dump-object sss_obj_)
      ;preloop_and_while
        (setq hatch_scale_list_i 0)
        (while (< hatch_scale_list_i (length hatch_scale_list_))
          (setq hatch_scale_list_val_ (nth  hatch_scale_list_i hatch_scale_list_))
            (setq Er-msg_ 
              (vl-catch-all-apply 
                (function 
                  (lambda () 
                    (command "objectscale" sss_ename_ "" "add" hatch_scale_list_val_ "" )
                  )
                )
              )
            )
          
          
          
      
          (setq hatch_scale_list_i (+ hatch_scale_list_i 1))
        )
      ;
    )
    (defun c:create_wall_hatch_WALLBLOCKHATCH ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setvar "hpannotative" 1)
        (setq hatch_Layer_ "000 - CONCRETE_WALL_HATCH_")
        (setq hatch_patt_ "ANSI37")
        (setq hatch_color_ "bylayer")
        (setq hatch_background_ ".")
        (setq hatch_ename_getang_ 0 )
        (setq hatch_ename_getsc_ 0.1 )
      ;
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               
      )
      ;new_blk_entlast object
        (setq newhatch_ename (entlast))
        (setq newhatch_obj (vlax-ename->vla-object newhatch_ename))
        
      ;
      (TA:add_hatch_scale newhatch_ename)
      
      
    )
    (defun c:create_wall_hatch_METALHATCH ()
      ;presetting layer
        ; (setq TA:if_found_layer_(TA:if_found_layer_ ""))
      ;
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setvar "hpannotative" 1)
        (setq hatch_Layer_ "0")
        (setq hatch_patt_ "ANSI32")
        (setq hatch_color_ "bylayer")
        (setq hatch_background_ ".")
        (setq hatch_ename_getang_ 0 )
        (setq hatch_ename_getsc_ 0.1 )
      ;
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               
      )
      ;new_blk_entlast object
        (setq newhatch_ename (entlast))
        (setq newhatch_obj (vlax-ename->vla-object newhatch_ename))
        
      ;
      (TA:add_hatch_scale newhatch_ename)
      
      
    )
    (defun c:create_sand_hatch_SANDHATCH ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setvar "hpannotative" 1)
        (setq hatch_Layer_ "000 - CONCRETE_WALL_HATCH_")
        (setq hatch_patt_ "AR-SAND")
        (setq hatch_color_ "bylayer")
        (setq hatch_background_ ".")
        (setq hatch_ename_getang_ 0 )
        (setq hatch_ename_getsc_ 0.01 )
      ;
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               
      )
      ;new_blk_entlast object
        (setq newhatch_ename (entlast))
        (setq newhatch_obj (vlax-ename->vla-object newhatch_ename))
      ;
      (TA:add_hatch_scale newhatch_ename)
      
      
    )
    (defun c:create_concrete_hatch_CONHATCH ()
      ;user_input_
      (setq obj_name_ (vla-get-objectname (vlax-ename->vla-object (setq hatch_ename_ (car (entsel "specify Object"))))))
      
      (cond
        ( ;first process
          (or
            
            (= obj_name_ "AcDbPolyline")
          )
          (progn
            (= (vla-get-closed (setq hatch_ename_obj_ (vlax-ename->vla-object hatch_ename_))) :vlax-true)
            (setq 1st_process "AcDbPolyline")
          )
        )
        (;first process
          (or
            (= obj_name_ "AcDbBlockReference")
          )
          (progn
            (setq 1st_process "AcDbBlockReference")
            
          )
        )
      )
      
      
      (if 
        (and 
          (= hatch_ename_getang_ nil)
          (= hatch_ename_getsc_ nil)
        )
        (progn
          (setq  hatch_ename_getang_ 0)
          (setq  hatch_ename_getsc_ 1)
          
        )
      )
      ;preseting_data_
        (setvar "hpannotative" 1)
        (setq hatch_Layer_ "000 - CONCRETE_COL_HATCH_")
        (setq hatch_patt_ "AR-CONC")
        (setq hatch_color_ "bylayer")
        (setq hatch_background_ ".")
        (setq hatch_ename_getang_ 0 )
        (setq hatch_ename_getsc_ 0.5 )
      ;
      (setq hatch_obj_ (vlax-ename->vla-object hatch_ename_))

      
      (command ".-hatch" "s"  hatch_ename_  
                "" 
                "c" hatch_color_ hatch_background_
                "p" hatch_patt_ hatch_ename_getsc_ hatch_ename_getang_ 
                "L" hatch_Layer_ 
                ""  
               
      )
      ;new_blk_entlast object
        (setq newhatch_ename (entlast))
        (setq newhatch_obj (vlax-ename->vla-object newhatch_ename))
      ;
      (TA:add_hatch_scale newhatch_ename)
      
      
    )
    
    ;HATCH_FUNC-DEEP-MATCHING
      (defun c:TA_HATCH_DEEP-MA_DOT
            (/
              nent_data_
              hatch_ename_
              hatch_obj_
              error_result_
            )

        (vl-load-com)
        (setq H-NAME "DOTS")
        ;; ไม่รับค่าศูนย์และค่าติดลบ แต่กด Enter ได้
        (initget 6)

        ;; ถาม Hatch Scale และจำค่าครั้งก่อน
        (setq input_hatch_scale (cond ( (getreal (strcat "\nSpecify Hatch Scale <" (rtos (setq input_hatch_scale (cond (input_hatch_scale) (1.0) ) ) 2 2 ) ">: " ) ) ) (input_hatch_scale) ) )

        (while
          (and
            (not hatch_ename_)
            (setq nent_data_
              (nentsel "\nSelect Hatch: ")
            )
          )

          (setq hatch_ename_ (car nent_data_)
                hatch_obj_
                (vlax-ename->vla-object hatch_ename_)
          )

          (if (/= "AcDbHatch"
                  (vla-get-ObjectName hatch_obj_)
              )
            (progn
              (prompt "\nSelected object is not a Hatch.")
              (setq hatch_ename_ nil)
            )
          )
        )

        (if hatch_ename_
          (progn
            (setq error_result_
              (vl-catch-all-apply
                (function
                  (lambda ()
                    ;; เปลี่ยน Pattern
                    (vla-SetPattern
                      hatch_obj_
                      1
                      H-NAME
                    )

                    ;; กำหนด Scale
                    (vla-put-PatternScale
                      hatch_obj_
                      input_hatch_scale
                    )
                    (TA:add_hatch_scale hatch_ename_)
                    (vla-Evaluate hatch_obj_)
                  )
                )
              )
            )

            (if (vl-catch-all-error-p error_result_)
              (prompt
                (strcat
                  "\nUnable to change Hatch: "
                  (vl-catch-all-error-message error_result_)
                )
              )
              (progn
                (vla-Regen
                  (vla-get-ActiveDocument
                    (vlax-get-acad-object)
                  )
                  1
                )

                (prompt
                  (strcat
                    "\nHatch changed to ANSI33, Scale = "
                    (rtos input_hatch_scale 2 2)
                  )
                )
              )
            )
          )
        )

        (princ)
      )
      (defun c:TA_HATCH_DEEP-MA_SAND
            (/
              nent_data_
              hatch_ename_
              hatch_obj_
              error_result_
            )

        (vl-load-com)
        (setq H-NAME "AR-SAND")
        ;; ไม่รับค่าศูนย์และค่าติดลบ แต่กด Enter ได้
        (initget 6)

        ;; ถาม Hatch Scale และจำค่าครั้งก่อน
        (setq input_hatch_scale (cond ( (getreal (strcat "\nSpecify Hatch Scale <" (rtos (setq input_hatch_scale (cond (input_hatch_scale) (1.0) ) ) 2 2 ) ">: " ) ) ) (input_hatch_scale) ) )

        (while
          (and
            (not hatch_ename_)
            (setq nent_data_
              (nentsel "\nSelect Hatch: ")
            )
          )

          (setq hatch_ename_ (car nent_data_)
                hatch_obj_
                (vlax-ename->vla-object hatch_ename_)
          )

          (if (/= "AcDbHatch"
                  (vla-get-ObjectName hatch_obj_)
              )
            (progn
              (prompt "\nSelected object is not a Hatch.")
              (setq hatch_ename_ nil)
            )
          )
        )

        (if hatch_ename_
          (progn
            (setq error_result_
              (vl-catch-all-apply
                (function
                  (lambda ()
                    ;; เปลี่ยน Pattern
                    (vla-SetPattern
                      hatch_obj_
                      1
                      H-NAME
                    )

                    ;; กำหนด Scale
                    (vla-put-PatternScale
                      hatch_obj_
                      input_hatch_scale
                    )
                    (TA:add_hatch_scale hatch_ename_)
                    (vla-Evaluate hatch_obj_)
                  )
                )
              )
            )

            (if (vl-catch-all-error-p error_result_)
              (prompt
                (strcat
                  "\nUnable to change Hatch: "
                  (vl-catch-all-error-message error_result_)
                )
              )
              (progn
                (vla-Regen
                  (vla-get-ActiveDocument
                    (vlax-get-acad-object)
                  )
                  1
                )

                (prompt
                  (strcat
                    "\nHatch changed to ANSI33, Scale = "
                    (rtos input_hatch_scale 2 2)
                  )
                )
              )
            )
          )
        )

        (princ)
      )
      (defun c:TA_HATCH_DEEP-MA_ANSI32
            (/
              nent_data_
              hatch_ename_
              hatch_obj_
              error_result_
            )

        (vl-load-com)
        (setq H-NAME "ANSI32")
        ;; ไม่รับค่าศูนย์และค่าติดลบ แต่กด Enter ได้
        (initget 6)

        ;; ถาม Hatch Scale และจำค่าครั้งก่อน
        (setq input_hatch_scale
          (cond
            (
              (getreal
                (strcat
                  "\nSpecify Hatch Scale <"
                  (rtos
                    (setq input_hatch_scale
                      (cond
                        (input_hatch_scale)
                        (1.0)
                      )
                    )
                    2
                    2
                  )
                  ">: "
                )
              )
            )
            (input_hatch_scale)
          )
        )

        (while
          (and
            (not hatch_ename_)
            (setq nent_data_
              (nentsel "\nSelect Hatch: ")
            )
          )

          (setq hatch_ename_ (car nent_data_)
                hatch_obj_
                (vlax-ename->vla-object hatch_ename_)
          )

          (if (/= "AcDbHatch"
                  (vla-get-ObjectName hatch_obj_)
              )
            (progn
              (prompt "\nSelected object is not a Hatch.")
              (setq hatch_ename_ nil)
            )
          )
        )

        (if hatch_ename_
          (progn
            (setq error_result_
              (vl-catch-all-apply
                (function
                  (lambda ()
                    ;; เปลี่ยน Pattern
                    (vla-SetPattern
                      hatch_obj_
                      1
                      H-NAME
                    )

                    ;; กำหนด Scale
                    (vla-put-PatternScale
                      hatch_obj_
                      input_hatch_scale
                    )
                    (TA:add_hatch_scale hatch_ename_)
                    (vla-Evaluate hatch_obj_)
                  )
                )
              )
            )

            (if (vl-catch-all-error-p error_result_)
              (prompt
                (strcat
                  "\nUnable to change Hatch: "
                  (vl-catch-all-error-message error_result_)
                )
              )
              (progn
                (vla-Regen
                  (vla-get-ActiveDocument
                    (vlax-get-acad-object)
                  )
                  1
                )

                (prompt
                  (strcat
                    "\nHatch changed to ANSI32, Scale = "
                    (rtos input_hatch_scale 2 2)
                  )
                )
              )
            )
          )
        )

        (princ)
      )
      (defun c:TA_HATCH_DEEP-MA_ANSI33
            (/
              nent_data_
              hatch_ename_
              hatch_obj_
              error_result_
            )

        (vl-load-com)
        (setq H-NAME "ANSI33")
        ;; ไม่รับค่าศูนย์และค่าติดลบ แต่กด Enter ได้
        (initget 6)

        ;; ถาม Hatch Scale และจำค่าครั้งก่อน
        (setq input_hatch_scale
          (cond
            (
              (getreal
                (strcat
                  "\nSpecify Hatch Scale <"
                  (rtos
                    (setq input_hatch_scale
                      (cond
                        (input_hatch_scale)
                        (1.0)
                      )
                    )
                    2
                    2
                  )
                  ">: "
                )
              )
            )
            (input_hatch_scale)
          )
        )
        (setq input_hatch_angle
          (cond
            (
              (getreal
                (strcat
                  "\nSpecify Hatch Angle <"
                  (rtos
                    (setq input_hatch_angle
                      (cond
                        (input_hatch_angle)
                        (1.0)
                      )
                    )
                    2
                    2
                  )
                  ">: "
                )
              )
            )
            (input_hatch_angle)
          )
        )

        (while
          (and
            (not hatch_ename_)
            (setq nent_data_
              (nentsel "\nSelect Hatch: ")
            )
          )

          (setq hatch_ename_ (car nent_data_)
                hatch_obj_
                (vlax-ename->vla-object hatch_ename_)
          )

          (if (/= "AcDbHatch"
                  (vla-get-ObjectName hatch_obj_)
              )
            (progn
              (prompt "\nSelected object is not a Hatch.")
              (setq hatch_ename_ nil)
            )
          )
        )

        (if hatch_ename_
          (progn
            (setq error_result_
              (vl-catch-all-apply
                (function
                  (lambda ()
                    ;; เปลี่ยน Pattern
                    (vla-SetPattern
                      hatch_obj_
                      1
                      H-NAME
                    )

                    ;; กำหนด Scale
                    (vla-put-PatternScale
                      hatch_obj_
                      input_hatch_scale
                    )
                    (vla-put-patternangle
                      hatch_obj_
                      (deg-to-rad input_hatch_angle)
                    )
                    (TA:add_hatch_scale hatch_ename_)
                    (vla-Evaluate hatch_obj_)
                  )
                )
              )
            )

            (if (vl-catch-all-error-p error_result_)
              (prompt
                (strcat
                  "\nUnable to change Hatch: "
                  (vl-catch-all-error-message error_result_)
                )
              )
              (progn
                (vla-Regen
                  (vla-get-ActiveDocument
                    (vlax-get-acad-object)
                  )
                  1
                )

                (prompt
                  (strcat
                    "\nHatch changed to ANSI33, Scale = "
                    (rtos input_hatch_scale 2 2)
                  )
                )
              )
            )
          )
        )

        (princ)
      )
    ;
  ;
  ;symbol_FUNC_
    (defun c:add_breakline_to_rectangle_ADBK ()
      ;user_input_
        (setq rec_ename_ (car (entsel "specify Object")))
        (setq dynamic_scale_ (cond ( (getreal (strcat "\nspecify_dynamic_scale_<" (rtos (setq dynamic_scale_ (cond (dynamic_scale_) (1.0) ) ) ) "> : " ) ) ) (dynamic_scale_) ) )
        
      ;

      ;get_data_
        (setq rec_obj_ (vlax-ename->vla-object rec_ename_))
        (setq rec_obj_objname_  (vla-get-objectname rec_obj_))
      
        (setq vertex_list (TA:Get_Pline_vertext_angle_case1 rec_ename_))
        (setq vertex_list_ (remove_member_list_ 2 vertex_list))
      ;
      ;preloop_and_while insertion_breakline_dynblock
        (setq vertex_list_i 0)
        (setq vertex_list_ii 1)
        (while (< vertex_list_i (length vertex_list_))
          (cond ;insert_block_case_
            (;_case_1
              (and
                  (/= vertex_list_i (- (length vertex_list_ ) 1))
              )
              (progn
                  (setq vertex_list_ename_set1 (nth  vertex_list_i vertex_list_))
                  (setq vertex_list_ename_set2 (nth  vertex_list_ii vertex_list_))
                  
                  (setq vertex_list_ename_midpoint_ (TA:midpoint (car vertex_list_ename_set1) (car vertex_list_ename_set2)))
                  (setq vertex_list_ename_distance_set1 (distance (car vertex_list_ename_set1)  vertex_list_ename_midpoint_ ))
                  (setq vertex_list_ename_distance_set2 (distance (car vertex_list_ename_set2)  vertex_list_ename_midpoint_))
                  
                  ;main_idea_code
                    (command "insert" "000SYM-BREAK_LINE_DYNBLOCK_" vertex_list_ename_midpoint_ dynamic_scale_ (cadr vertex_list_ename_set1) )
                    (setq new_dynamic_block_ (entlast))
                    (setq new_dynamic_block_obj_ (vlax-ename->vla-object new_dynamic_block_))
                    (LM:setdynpropvalue new_dynamic_block_obj_ "right_width" vertex_list_ename_distance_set1)
                    (LM:setdynpropvalue new_dynamic_block_obj_ "left_width" vertex_list_ename_distance_set2)
                    (cond
                      (;_case_1
                        (and (>= (cadr vertex_list_ename_set1) 90 ) (<= (cadr vertex_list_ename_set1) 135 ))
                        (progn
                          (LM:setdynpropvalue new_dynamic_block_obj_ "flip state1"  1)

                          
                          (princ "_case_1")
                        )
                      )
                      (;_case_2
                        (or
                            (and (>= (cadr vertex_list_ename_set1) 135 ) (<= (cadr vertex_list_ename_set1) 180 ))
                        )
                        (progn
                          (LM:setdynpropvalue new_dynamic_block_obj_ "flip state1"  0)

                          
                          
                          (princ "_case_2")
                        )
                      )
                      (;_case_3
                        (or
                            (and (>= (cadr vertex_list_ename_set1) 180 ) (<= (cadr vertex_list_ename_set1) 360 ))
                        )
                        (progn
                          (LM:setdynpropvalue new_dynamic_block_obj_ "flip state1"  1)
                          (princ "_case_3")
                        )
                      )
                    )
                  ;
                  (princ "_case_1")
              )
            )
            (;_case_2
              (and
                  (= vertex_list_i (- (length vertex_list_ ) 1))
              )
              (progn
                  (setq vertex_list_ename_set1 (nth  vertex_list_i vertex_list_))
                  (setq vertex_list_ename_set2 (nth  0 vertex_list_))
                  
                  (setq vertex_list_ename_midpoint_ (TA:midpoint (car vertex_list_ename_set1) (car vertex_list_ename_set2)))
                  (setq vertex_list_ename_distance_set1 (distance (car vertex_list_ename_set1)  vertex_list_ename_midpoint_ ))
                  (setq vertex_list_ename_distance_set2 (distance (car vertex_list_ename_set2)  vertex_list_ename_midpoint_))
                
                  ;main_idea_code
                    (command "insert" "000SYM-BREAK_LINE_DYNBLOCK_" vertex_list_ename_midpoint_ dynamic_scale_ (rad-to-deg (angle (car vertex_list_ename_set1) (car vertex_list_ename_set2) )) )
                    (setq new_dynamic_block_ (entlast))
                    (setq new_dynamic_block_obj_ (vlax-ename->vla-object new_dynamic_block_))
                    (LM:setdynpropvalue new_dynamic_block_obj_ "right_width" vertex_list_ename_distance_set1)
                    (LM:setdynpropvalue new_dynamic_block_obj_ "left_width" vertex_list_ename_distance_set2)
                    (LM:setdynpropvalue new_dynamic_block_obj_ "flip state1"  1)
                    
                  ;
                (princ "_case_2")
              )
            )
          )
          
          (setq vertex_list_i (+ vertex_list_i 1))
          (setq vertex_list_ii (+ vertex_list_ii 1))
        )
      ;
      
      
      
    )
    (defun c:edit_breakline_to_rectangle_EDBK ()
      ;selection_set_user_input
        (if  ;pre_select_ssget_or_post_select_ssget
          (= 
            (setq ss_pre_filter_set_xx_ (ssget "I" 
                                              (list 
                                                (cons 0 "LINE,ARC,CIRCLE,POLYLINE,LWPOLYLINE,ELLIPSE,SPLINE,INSERT") ;type of object
                                                ; (cons 8 "000 - GRID")   ;kind of layer
                                                
                                                ; (cons 62 1)           ;kind of color call sign with color code index
                                              )
                                        )
            )
            nil
          )
          (progn 
            (setq ss_pre_filter_set_xx_ (ssget 
                                          (list 
                                            (cons 0 "INSERT") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      ;filter_object_to_new_ssget_
        (setq ss_set_ (TA:EF_Filter_ss_set_ ss_pre_filter_set_xx_ "000SYM-BREAK_LINE_DYNBLOCK_"))
        ;preloop_and_while
          (setq ss_set_i 0)
          (while (< ss_set_i (sslength ss_set_))
            ;get_data_in_ssget_
            (setq ss_set_ename_ (ssname ss_set_ ss_set_i))
            (setq ss_get_obj_ (vlax-ename->vla-object ss_set_ename_))
            (setq ss_get_obj_rotation_ (rad-to-deg (vla-get-rotation ss_get_obj_ )))
            
            (cond
              (;rotation_cond_case_1
                (and
                    (= ss_get_obj_rotation_ 0 )
                )
                (progn
                    (LM:setdynpropvalue ss_get_obj_ "distance1" 40 )
                    (LM:setdynpropvalue ss_get_obj_ "visibility1"  1)
                    (command "draworder" ss_set_ename_ "" "f" )
                  (princ "rotation_cond_case_1")
                )
              )
              (;rotation_cond_case_2
                (and
                    (= ss_get_obj_rotation_ 90)
                    
                )
                  (progn
                      (LM:setdynpropvalue ss_get_obj_ "distance1" 0 )
                      (LM:setdynpropvalue ss_get_obj_ "visibility1"  2)
                    (princ "rotation_cond_case_2")
                  )
              )
              (;rotation_cond_case_3
                (and
                    (= ss_get_obj_rotation_ 180)
                    
                )
                (progn
                    (LM:setdynpropvalue ss_get_obj_ "distance1" 40 )
                    (LM:setdynpropvalue ss_get_obj_ "visibility1"  1)
                    (command "draworder" ss_set_ename_ "" "f" )
                    (princ "rotation_cond_case_3")
                )
              )
              (;rotation_cond_case_4
                (and
                    (= ss_get_obj_rotation_ 270)
                    
                )
                (progn
                  (LM:setdynpropvalue ss_get_obj_ "distance1" 0 )
                  (LM:setdynpropvalue ss_get_obj_ "visibility1"  2)
                  (princ "rotation_cond_case_4")
                )
              )
            )
            
            
            
            
          (setq ss_set_i (+ ss_set_i 1))
        )
      ;
      ;
    )
    (defun c:make_detail_box_mkbx_ ()
      ;get_point_data_
        (setq get_pt_ (getpoint ))
        ; (setvar "orthomode" 1)
      ;
      ;get_honrizontal_data_
        (setq dist_hon (getdist get_pt_ ) )
        (setq hon_pt_ (polar get_pt_ 0.0 dist_hon))
        (setq hon_pt_- (polar get_pt_ (deg-to-rad 180.00) dist_hon))
      ;
      ;get_vertical_data_
        (setq dist_ver (getdist get_pt_ ) )
        (setq ver_pt_ (polar get_pt_ (deg-to-rad 90.00) dist_ver))
        (setq ver_pt_- (polar get_pt_ (deg-to-rad 270.00) dist_ver))
      ;
      ;sorting_max_legth_
        (setq length_list_rec (list
                                dist_hon
                                dist_ver
                              )
        )
        (setq min-length (car (vl-sort  length_list_rec '<)))
      ;
      ;get_conner_
        (setq top_conner_ (list
                            (car hon_pt_)
                            (cadr ver_pt_)
                          )
        )
        (setq bot_conner_ (list
                            (car hon_pt_-)
                            (cadr ver_pt_-)
                          )
        )
      ;
    
      ;use_input_for_specify_fllet_rec_
        (setq fllet_rec_val "not pass" )
        (while (= fllet_rec_val "not pass")
          
          (setq fllet_rec_ (cond ( (getint (strcat "\nspecify fllet_rec_<" (rtos (setq fllet_rec_ (cond (fllet_rec_) (1.0) ) ) ) "> : " ) ) ) (fllet_rec_) ) )
          (if
            (< (LM:round (* min-length 0.9)) fllet_rec_)
            (progn
              (setq fllet_rec_val "not pass" )
              (alert "fllet rectangle more than min-length ractangle ")
            )
            (setq fllet_rec_val "pass" )
          )
        )
      ;
      ; ;make_new_object_
      ;   (command "point" get_pt_)
      ;   (command "point" top_conner_)
      ;   (command "point" bot_conner_)
        (command "rectangle" bot_conner_ top_conner_  )
        (command "fillet" "p" "r" fllet_rec_ "L" )
      ;
      ;put_prop_data_
        (setq entlast_ename_ (entlast))
        (vla-get-linetype (setq entlast_obj_ (vlax-ename->vla-object entlast_ename_)))
        (vla-put-linetype (setq entlast_obj_ (vlax-ename->vla-object entlast_ename_)) "byblock")
      ;

      
    )
    (defun c:move_to_zero_xyz_M20 ()
      ;example_user_input_main_object
        (setq main_ename_ (car (entsel "specify Object")))
      ;
      ;get_data_form_user_input_
        (setq main_obj_ (vlax-ename->vla-object main_ename_))
        (setq main_obj_get_object_name_ (vla-get-objectname main_obj_))
      ;
      ;condoitional_for_diferent_acad_object_
        (cond  ;condoitional_for_diferent_acad_object_
          ( ;conditional_case_1
          (and 
            (= main_obj_get_object_name_ "AcDbPolyline")
          )
          (progn 
              (setq center_object_ (TA:find_center main_ename_))
              (princ "conditional_case_1")
          )
          )
          ( ;conditional_case_2
          (and 
            (= main_obj_get_object_name_ "AcDbCircle")
          )
          (progn 
              (setq center_object_ (setq _obj_ins_ (vlax-safearray->list (vlax-variant-value (vla-get-center main_obj_ )))))
              (princ "conditional_case_2")
          )
          )
          ( ;conditional_case_3
          (and 
            (= main_obj_get_object_name_ "AcDbBlockReference")
          )
          (progn 
              (setq center_object_ (vlax-safearray->list (vlax-variant-value (vla-get-insertionpoint main_obj_))))
              (princ "conditional_case_3")
          )
          )
        )
      ;
      ;move_command_process_
        (vla-move main_obj_  (vlax-3d-point center_object_) (vlax-3d-point 0 0 0)  )
      ;
        

    )
    (defun c:Multi_wipeout_mlwe ()
      ;selection_set
        (if  ;pre_select_ssget_or_post_select_ssget
          (= 
            (setq ss_pre_filter_set_xx_ (ssget "I" 
                                              (list 
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "lwpolyline") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx_)
        )
      ;
      ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_hon_obj_ (vlax-ename->vla-object ss_pre_filter_set_xx_ename_))
        (setq ss_pre_filter_set_xx_ename_close_line (vla-put-closed ss_pre_filter_set_xx_hon_obj_ :vlax-true))
        
          (command "wipeout" "p"  ss_pre_filter_set_xx_ename_ "n" )
          (setq wipeput_ename_ (entlast))
          (setq wipeput_ename_obj_ (vlax-ename->vla-object wipeput_ename_))
          (vla-put-layer wipeput_ename_obj_ "000 - WIPEOUT")
          (vla-put-color wipeput_ename_obj_ 256)
          (command "_draworder" wipeput_ename_ "" "b" )
          
      
        (setq ss_pre_filter_set_xx_i (+ ss_pre_filter_set_xx_i 1))
      )
      ;
      
      
      
      
      
      
      
    )
  ;
  ;xclip_FUNC
    (defun c:MULTI_XCILP_OBJECT_MXCV ()
      ;note_from_DEV
      ;READMORE PROCESS IN ALERT MESSAGE
        (alert
          "
          1 - selection_set_for_blk_object_
          2 - selection_circle_object_
          3 - whileloop ssname for XCILP process
          4 - complete ? not sure
          "
        )
      ;
      ;user_input_blk_object_
        ;selection_set
          (princ "selection_set_BLKOBJECT_process")
          (if  ;pre_select_ssget_or_post_select_ssget
            (= 
              (setq ss_pre_selection_blkobject_set_ (ssget "I" 
                                                (list 
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn 
              (setq ss_pre_selection_blkobject_set_ (ssget 
                                            (list 
                                              (cons 0 "INSERT") ;type of object
                                              ; (cons 8 "000 - GRID")   ;kind of layer
                                              ; (cons 2 "000-GRIDLINE_DYN")       ;kind of nameblock
                                              ; (cons 62 1)           ;kind of color call sign with color code index
                                            )
                                          )
              )
            )
            (sslength ss_pre_selection_blkobject_set_)
          )
        ;
      ;

      ;user_input_circle
        ;selection_set
          (princ "ss_for_circle_")
          (if  ;pre_select_ssget_or_post_select_ssget
            (= 
              (setq ss_for_circle_ (ssget "I" 
                                                (list 
                                                  (cons 0 "CIRCLE,lwpolyline") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn 
              (setq ss_for_circle_ (ssget 
                                            (list 
                                              (cons 0 "CIRCLE,lwpolyline") ;type of object
                                              ; (cons 8 "000 - GRID")   ;kind of layer
                                              ; (cons 2 "000-GRIDLINE_DYN")       ;kind of nameblock
                                              ; (cons 62 1)           ;kind of color call sign with color code index
                                            )
                                          )
              )
            )
            (sslength ss_for_circle_)
          )
        ;
      ;
      (cond 
        (;UCS_Detect_variable_
          (and
              (= (getvar "WORLDUCS") 0)
          )
          (progn
            (alert "Please reset Worlducs variable")
          )
        )
        (;object_case_1_polygon_case
          (and
              (= (vla-get-objectname (vlax-ename->vla-object (ssname ss_for_circle_ 0))) "AcDbPolyline")
              (= (getvar "WORLDUCS") 1)
          )
          (progn
            (setq ucs_detect_error_ 1)
            (setvar "osmode" 0)
            (setq new_polygon_ename_ (ssname ss_for_circle_ 0))
            (setvar "osmode" 1279)
            (princ "object_case_1")
          )
        )
        (;object_case_2_circle_obejct_
          (and
              (= (vla-get-objectname (vlax-ename->vla-object (ssname ss_for_circle_ 0))) "AcDbCircle")
              (= (getvar "WORLDUCS") 1)
          )
          (progn
              ;tranfer_circle_to_polyogn_process
                (setvar "osmode" 0)
                (setq segment_curve_ (cond ( (getint (strcat "\nspecify fllet_rec_<" (rtos (setq segment_curve_ (cond (segment_curve_) (1.0) ) ) ) "> : " ) ) ) (segment_curve_) ) )
                (setq center_circle_ (vlax-safearray->list (vlax-variant-value (vla-get-center (vlax-ename->vla-object (ssname ss_for_circle_ 0))))))
                (setq rad_circle_ (vla-get-radius (vlax-ename->vla-object (ssname ss_for_circle_ 0))))
                (command "polygon" segment_curve_ center_circle_ "i"  rad_circle_ )
                (setq new_polygon_ename_ (entlast))
                (setq new_polygon_obj_ (vlax-ename->vla-object new_polygon_ename_))
                (setvar "osmode" 1279)
              ;
            (princ "object_case_2")
          )
        )
      )
      
      

      ;multi_xcilp_process_
        ;preloop_and_while
          (setq ss_pre_selection_blkobject_set_i 0)
          (while 
            (and
              (= (getvar "WORLDUCS") 1)
              (< ss_pre_selection_blkobject_set_i (sslength ss_pre_selection_blkobject_set_))
            )
            (setq ss_pre_selection_blkobject_set_ename_ (ssname ss_pre_selection_blkobject_set_ ss_pre_selection_blkobject_set_i))
              (command "xclip"  ss_pre_selection_blkobject_set_ename_  "" "n" "s" new_polygon_ename_)
            (setq ss_pre_selection_blkobject_set_i (+ ss_pre_selection_blkobject_set_i 1))
          )
        ;
        ;delete_object_
          (vla-delete  new_polygon_obj_)
        ;
      ;
    )
  ;
  ;scale_FUNC
    (defun c:save_dynamic_scale_scdyn_ ()
      ;user_input_
        (setq get_dynblock_ename_ (car (entsel "specify Object")))
        (setq dynamic_scale_ (cond ( (getreal (strcat "\nspecify_scale<" (rtos (setq dynamic_scale_ (cond (dynamic_scale_) (1.0) ) ) ) "> : " ) ) ) (dynamic_scale_) ) )
      ;
    
      (if (and ;condition rule
            ; (/= get_effectivename_ nil)
            (= (vla-get-isdynamicblock (vlax-ename->vla-object get_dynblock_ename_)) :vlax-true)
            ; (/= (vla-get-isdynamicblock (vlax-ename->vla-object get_effectivename_)) :vlax-true)
          )
        (progn ;add data
          ; (alert "\nplease select block object")
          ; (setq get_effectivename_ nil)
          ; (setq get_effectivename_obj_val_ nil)
          (setq get_effectivename_obj_val_ (LM:Effectivename (vlax-ename->vla-object get_dynblock_ename_)))
          (setq REF_get_att_list_ (LM:getdynprops (vlax-ename->vla-object get_dynblock_ename_)))
          (setq REF_get_att_list_total (length REF_get_att_list_))
          ;add more
        )
        (setq get_effectivename_ nil)
      )
      ;rescale_
        (setq dynamic_scale_x (if (> (vla-get-xscalefactor (vlax-ename->vla-object get_dynblock_ename_)  )0 ) (progn dynamic_scale_ ) (* dynamic_scale_ -1) ))
        (setq dynamic_scale_y (if (> (vla-get-yscalefactor (vlax-ename->vla-object get_dynblock_ename_)  )0 ) (progn dynamic_scale_ ) (* dynamic_scale_ -1) ))
        (setq dynamic_scale_z dynamic_scale_)
         
        (setq basescale_ (vlax-3d-point dynamic_scale_x dynamic_scale_y dynamic_scale_y ) )
        (vla-put-xscalefactor (vlax-ename->vla-object get_dynblock_ename_) dynamic_scale_x )
        (vla-put-yscalefactor (vlax-ename->vla-object get_dynblock_ename_) dynamic_scale_y )
        (vla-put-zscalefactor (vlax-ename->vla-object get_dynblock_ename_) dynamic_scale_z )
      ;
      ;preloop_and_while
        (setq REF_get_att_list_i 0)
        (while (< REF_get_att_list_i (length REF_get_att_list_))
          ;get_dynamic_data
            (setq REF_get_att_list_dynamicset_ (nth  REF_get_att_list_i REF_get_att_list_))
            (setq REF_get_att_list_dynamicset_name_ (nth 0 REF_get_att_list_dynamicset_) )
            (setq REF_get_att_list_dynamicset_val_ (cdr REF_get_att_list_dynamicset_))
          ;
          ;get_vis_data_
            (setq vis_name_ (LM:getvisibilityparametername (vlax-ename->vla-object get_dynblock_ename_) ))
            (setq vis_stage_ (LM:getvisibilitystate (vlax-ename->vla-object get_dynblock_ename_) ))
            (LM:SetVisibilityState (vlax-ename->vla-object get_dynblock_ename_) vis_stage_ )
          ;
          ;get_filp_data_
            (setq Flip_data_ (LM:toggleflipstate (vlax-ename->vla-object get_dynblock_ename_)))
          ;
          
          
          (if (/= REF_get_att_list_dynamicset_name_ "Origin")
            (progn
              (LM:setdynpropvalue (vlax-ename->vla-object get_dynblock_ename_) REF_get_att_list_dynamicset_name_ REF_get_att_list_dynamicset_val_ )
            )
            (princ "next ")
          )
          
          (setq REF_get_att_list_i (+ REF_get_att_list_i 1))
        )
      ;
    )
  ;
  ;EF_NAME_TO_ATT_TEXT_BLOCK_FUNC
    (defun TA:renameblock_  ( old_block_name_ new_block_name_ / doc_ blocks_ block_def_ error_result_ )
      (vl-load-com)
      (cond
        ;; ชื่อเก่าหรือชื่อใหม่ต้องเป็น String
        (
          (not
            (and
              (= (type old_block_name_) 'STR)
              (= (type new_block_name_) 'STR)
            )
          )
          (prompt "\nError: Old Block name and New Block name must be String.")
          nil
        )

        ;; ห้ามชื่อว่าง
        (
          (or
            (= (vl-string-trim " " old_block_name_) "")
            (= (vl-string-trim " " new_block_name_) "")
          )
          (prompt "\nError: Block name cannot be blank.")
          nil
        )

        ;; ไม่ต้องเปลี่ยนหากชื่อเดิมและใหม่เหมือนกัน
        (
          (= (strcase old_block_name_) (strcase new_block_name_))
          (prompt "\nBlock name is unchanged.")
          old_block_name_
        )

        ;; ตรวจว่ามี Block ชื่อเดิมจริง
        (
          (not (tblsearch "BLOCK" old_block_name_))
          (prompt (strcat "\nError: Block not found: " old_block_name_))
          nil
        )

        ;; ห้ามตั้งชื่อซ้ำกับ Block ที่มีอยู่แล้ว
        (
          (tblsearch "BLOCK" new_block_name_)
          (prompt (strcat "\nError: New Block name already exists: " new_block_name_))
          nil
        )

        ;; Rename Block
        (T
          (setq doc_ (vla-get-ActiveDocument (vlax-get-acad-object)))
          (setq blocks_ (vla-get-Blocks doc_))

          (setq error_result_
            (vl-catch-all-apply
              'vla-Item
              (list blocks_ old_block_name_)
            )
          )
          (if
            (vl-catch-all-error-p error_result_)
            (progn
              (prompt
                (strcat
                  "\nError: Cannot access Block Definition: "
                  (vl-catch-all-error-message error_result_)
                )
              )
              nil
            )
            (progn
              (setq block_def_ error_result_)
              (setq error_result_ (vl-catch-all-apply 'vla-put-Name (list block_def_ new_block_name_) ) )
              (if
                (vl-catch-all-error-p error_result_)
                (progn
                  (prompt (strcat "\nError: Cannot rename Block: " (vl-catch-all-error-message error_result_) ) )
                  nil
                )

                (progn
                  (prompt (strcat "\nBlock renamed: " old_block_name_ " -> " new_block_name_ ) )
                  new_block_name_
                )
              )
            )
          )
        )
      )
    )
    (defun TA:fillter_block_name_ (blk_ename_ )
      ;LEE-MAC_SUB_FUNC
        (defun LM:StringSubst ( new old str / inc len )
          (setq len (strlen new)
                inc 0
          )
          (while (setq inc (vl-string-search old str inc))
              (setq str (vl-string-subst new old str inc)
                    inc (+ inc len)
              )
          )
          str
        )
      ;
      ;Example_for_testing_
        ; (setq blk_ename_ (car (entsel "specify Object")))
      ;
      ;
      (setq blk_obj_ (vlax-ename->vla-object blk_ename_))

      (if (= (vla-get-objectname blk_obj_ ) "AcDbBlockReference")
        (progn
          (setq blk_raw_efname_ (LM:effectivename blk_obj_ ))
          ;user_setting_for_filter_ename_
            ; (setq blk_raw_efname_ "000 - DYNAMIC_VIEW_ASSCESSORIES_PHILLIPS_HEAD_SELF_DRILLING_SCREW_No.8_COMBINE_VIEW") ;FOR EXAMPLE CODING 
            (setq blk_raw_efname_ (LM:StringSubst "" "000 - " blk_raw_efname_))
            (setq blk_raw_efname_ (LM:StringSubst "" "DYNAMIC" blk_raw_efname_))
            (setq blk_raw_efname_ (LM:StringSubst "" "VIEW" blk_raw_efname_))
            (setq blk_raw_efname_ (LM:StringSubst "" "ASSCESSORIES" blk_raw_efname_))
            (setq blk_raw_efname_ (LM:StringSubst "" "COMBINE+" blk_raw_efname_))
            (setq blk_raw_efname_ (LM:StringSubst "" "FRONT" blk_raw_efname_))
            (setq blk_raw_efname_ (LM:StringSubst "" "TOP" blk_raw_efname_))
            (setq blk_raw_efname_ (LM:StringSubst "" "SIDE" blk_raw_efname_))
            (setq blk_raw_efname_ (LM:StringSubst "" "BOT" blk_raw_efname_))
            (setq blk_raw_efname_ (LM:StringSubst "" "BACK" blk_raw_efname_))
            (setq blk_raw_efname_ (LM:StringSubst "" "CUT" blk_raw_efname_))
            (setq blk_raw_efname_ (LM:StringSubst "" "ARRAY+" blk_raw_efname_))
            (setq blk_raw_efname_ (LM:StringSubst "" "ARRAY" blk_raw_efname_))
            (setq blk_raw_efname_ (LM:StringSubst "" "SET" blk_raw_efname_))
            (setq blk_raw_efname_ (LM:StringSubst "_" "__" blk_raw_efname_))
            (setq blk_raw_efname_ (LM:StringSubst "_" "___" blk_raw_efname_))
            (setq blk_raw_efname_ (LM:StringSubst "_" "____" blk_raw_efname_))
            
          ;
          ;front_name_setting_
            ;preloop_and_while_for_delete "_"
              (setq i 0)
              (setq ii 1)
              (setq test_text_ (substr blk_raw_efname_ ii 1))
              (while (= test_text_ "_")
                (setq test_text_ (substr blk_raw_efname_ ii 1))
                (if (/= i 0)
                  (progn
                    (setq ii (+ ii 1))
                    (setq i (+ i 1))
                  )
                  (setq i (+ i 1))
                )
              )
              (setq blk_raw_efname__strlen (strlen blk_raw_efname_))
              (if (= ii 1)
                (progn
                  (setq final_text_ blk_raw_efname_)
                )
                (setq final_text_ (substr blk_raw_efname_ (setq new_i (- ii 1)) blk_raw_efname__strlen))
              )
              

          ;
          ;bot_name_setting_
            (setq l 0)
            (setq ll 1)
            (setq final_text_l (strlen final_text_))
            (setq test_text_ (substr final_text_ final_text_l 1))
            (while (= test_text_ "_")
              (setq test_text_ (substr final_text_ final_text_l 1))
              (setq final_text_l (- final_text_l 1))
            )
            (setq final_text_last (+ final_text_l 1))
            (setq final_text_final (substr final_text_ 1 final_text_last))
          ;
        )
      )
    )
    (defun TA:remove_att_value_ (att_obj_ except_att_list_ )
      ;Note By Code_Developer
      ;This command is designed to work exclusively with attribute blocks only.
      ;It will remove all attributes in the block, but it allows certain attributes to be excluded by adding their names to an exception list.
      ;att_obj_ = vla-ename > object
      ;except_att_list_ = (list "att1" "att2" etc.)
      ;example code (TA:remove_att_value_ att_obj_ (list))
      ;example_code (setq except_att_list_ (list "NO.CODE")) 
      ;The operation of the command will read the block's attribute values and generate a set of text. n 
      ;

      ;fillter_EF_name_object_
        ; (setq att_ename_ nil)
        ; (setq att_obj_ nil)
        ; (while (= att_ename_ nil)
          ;user_input_data_  
            ; (setq att_ename_ (car (entsel "specify Object")))
          ;
          ;fillter_object_type_
            (if 
              (and
                ; (if (/= att_ename_ nil) (progn (setq att_obj_ (vlax-ename->vla-object att_ename_)) ))
                (= (vla-get-objectname att_obj_) "AcDbBlockReference")
                (= (vla-get-hasattributes att_obj_) :vlax-true )
              )
              (progn
                (setq att_tag_list_ (LM:vl-getattributevalue-tag-TA-Modifies att_obj_))
              )
              ; (setq att_ename_ nil)
            )
            (if 
              (or
                ; (= att_ename_ nil)
                (/= (vla-get-objectname att_obj_) "AcDbBlockReference")
                (if (= (vla-get-objectname att_obj_) "AcDbBlockReference") (progn (/= (vla-get-hasattributes att_obj_) :vlax-true ) ))
              )
              (progn
                (alert "Please selection attribute object")
              )
            )
          ;
        ; )
      ;
      ;preloop_and_while_for_make_sequnce_attribute
        (setq att_tag_list_i 0)
        (while (< att_tag_list_i (length att_tag_list_))
          (setq att_tag_list_tagname_ (nth  att_tag_list_i att_tag_list_))
          (if (= (TA:FIND_DUPLICATE_LIST att_tag_list_tagname_ except_att_list_) "N" )
            (progn
              (LM:vl-setattributevalue att_obj_ att_tag_list_tagname_ "" )
            )
          )
          (setq att_tag_list_i (+ att_tag_list_i 1))
        )
      ;
      
    )
    (defun c:fillter_blockname_to_text_b2text ()
      ;NOTE-FROM_DEV
        ;this is code for filler_efectivename_block_name
      ;
      ;preloop_and_while
        (setq return_code_ nil)
        (while (and 
                (= return_code_ nil)
                
              )
          ;user_input_
            (setq eee_ename_ (car (entsel "specify Object for fillter_block_name")))
            (setq fillter_block_name_ (TA:fillter_block_name_ eee_ename_))
            (setq dynamic_ename_ (car (entsel "specify Object for input fillter_block_name")))
            (setq dynamic_obj_ (vlax-ename->vla-object dynamic_ename_))
          ;
          (if (and 
                (= (setq alert_val_1 (vla-get-objectname dynamic_obj_)) "AcDbBlockReference")
                (= (setq alert_val_2 (LM:effectivename dynamic_obj_)) "CONTENT NAME3 LEFT - BUBBLE v6")
                (/= eee_ename_ dynamic_ename_)
              )
            (progn
              (LM:vl-setattributevalue dynamic_obj_ "name1" fillter_block_name_)
              (setq return_code_"full")
            )
            (setq return_code_ nil)
          )
          (if (and 
                (= return_code_ nil)
                (/= alert_val_1 "AcDbBlockReference")
              )
            (progn
              (alert (strcat "this object is " alert_val_1 "\n" "block name = nil\n" "something is incorrect"  ))
              (setq return_code_ nil)
            )

          )

        )
      ;
    )
    (defun c:effectivename_to_att_EF2text ()
      ;NOTE-FROM_DEV
        ;this is code for filler_efectivename_block_name
      ;
      ;preloop_and_while
        (setq return_code_ nil)
        (while (and 
                (= return_code_ nil)
                
              )
          ;user_input_
            (setq eee_ename_ (car (entsel "specify Object for fillter_block_name")))
            (setq fillter_block_name_ (LM:effectivename (setq eee_ename_obj_ (vlax-ename->vla-object eee_ename_))))
            (setq dynamic_ename_ (car (entsel "specify Object for input fillter_block_name")))
            (setq dynamic_obj_ (vlax-ename->vla-object dynamic_ename_))
          ;
          (if (and 
                (= (setq alert_val_1 (vla-get-objectname dynamic_obj_)) "AcDbBlockReference")
                (or
                  (= (setq alert_val_2 (LM:effectivename dynamic_obj_)) "000 - BOX_EF_NAME")
                  (= (setq alert_val_2 (LM:effectivename dynamic_obj_)) "000 - BOX_EF_NAME_REV02")
                )
                (/= eee_ename_ dynamic_ename_)
              )
            (progn
              (LM:vl-setattributevalue dynamic_obj_ "nameblk" fillter_block_name_)
              (setq return_code_"full")
            )
            (setq return_code_ nil)
          )
          (if (and 
                (= return_code_ nil)
                (/= alert_val_1 "AcDbBlockReference")
              )
            (progn
              (alert (strcat "this object is " alert_val_1 "\n" "block name = nil\n" "something is incorrect"  ))
              (setq return_code_ nil)
            )

          )

        )
      ;
    )
    (defun c:rename_block_RENBLKV2_RENB2 ()
      ;NOTE-FROM_DEV
        ;this is code for filler_efectivename_block_name
      ;
      ;user_input
        (setq eee_ename_ (car (entsel "specify Object for fillter_block_name")))
        (setq old_block_name_ (LM:effectivename (setq eee_ename_obj_ (vlax-ename->vla-object eee_ename_))))
        (setq new_ename_ (car (entsel "specify Object for input fillter_block_name")))
        (setq new_ename_obj_ (vlax-ename->vla-object new_ename_))
      ;
      ;checking_process
        (if 
          (and 
            (= (setq alert_val_1 (vla-get-objectname eee_ename_obj_)) "AcDbBlockReference")
            (= (setq alert_val_2 (LM:effectivename new_ename_obj_)) "000 - BOX_EF_NAME_REV02")
            (/= eee_ename_ dynamic_ename_)
          )
          (progn
            ;get_data_old_EF_NAME_
              (setq old_block_name_ (LM:effectivename (setq eee_ename_obj_ (vlax-ename->vla-object eee_ename_))))
            ;
            ;get_data

              (setq new_ef_name_  (strcat 
                                    (setq new_ef_KINDBLK (LM:vl-getattributevalue new_ename_obj_ "KINDBLK" ) )
                                    (setq new_ef_nameblk (LM:vl-getattributevalue new_ename_obj_ "nameblk" ) )
                                    (setq new_ef_NAME_CODE (LM:vl-getattributevalue new_ename_obj_ "NAME_CODE" ) )
                                    (setq new_ef_NAME_VIEW (LM:vl-getattributevalue new_ename_obj_ "NAME_VIEW" ) )
                                  )
              )
            ;
          )
          (alert "SOMETHING BAD")
        )
      ;
      ;Rename_process
        (command "rename" "B" old_block_name_ new_ef_name_)
      ;
          


    )
    (defun c:rename_block_RENBLKV2_RENB3 ()
      (setq text1_ename_ (car (entsel "specify Old Object")))
      (setq text1_obj_ (vlax-ename->vla-object text1_ename_))
      (setq text2_ename_ (car (entsel "specify New Object")))
      (setq text2_obj_ (vlax-ename->vla-object text2_ename_))
      (command "rename" "b" (vla-get-textstring text1_obj_) (vla-get-textstring text2_obj_))
    )
    (defun c:rename_block_RENBLKV2_RENB3x
      ( / text1_ename_ text1_obj_ text2_ename_ text2_obj_ old_block_name_ new_block_name_ blocks_ block_def_ error_result_ )
      (vl-load-com)
      
      (if
        (and
          (setq text1_ename_
            (car (entsel "\nSpecify Old Block Name Text: "))
          )
          (setq text2_ename_
            (car (entsel "\nSpecify New Block Name Text: "))
          )
        )
        (progn
          (setq text1_obj_ (vlax-ename->vla-object text1_ename_)
                text2_obj_ (vlax-ename->vla-object text2_ename_)
                old_block_name_ (vla-get-TextString text1_obj_)
                new_block_name_ (vla-get-TextString text2_obj_)
                blocks_
                  (vla-get-Blocks
                    (vla-get-ActiveDocument (vlax-get-acad-object))
                  )
          )

          (setq error_result_
            (vl-catch-all-apply
              'vla-Item
              (list blocks_ old_block_name_)
            )
          )

          (if
            (vl-catch-all-error-p error_result_)
            (prompt
              (strcat
                "\nBlock not found: "
                old_block_name_
              )
            )
            (progn
              (setq block_def_ error_result_)

              (setq error_result_
                (vl-catch-all-apply
                  'vla-put-Name
                  (list block_def_ new_block_name_)
                )
              )

              (if
                (vl-catch-all-error-p error_result_)
                (prompt
                  (strcat
                    "\nUnable to rename block: "
                    (vl-catch-all-error-message error_result_)
                  )
                )
                (prompt
                  (strcat
                    "\nBlock renamed: "
                    old_block_name_
                    " -> "
                    new_block_name_
                  )
                )
              )
            )
          )
        )
      )

      (princ)
    )
    (defun c:rename_block_RENBLK ()
      ;NOTE-FROM_DEV
        ;this is code for filler_efectivename_block_name
      ;
      ;user_input
        (setq eee_ename_ (car (entsel "specify Object for fillter_block_name")))
        (setq old_block_name_ (LM:effectivename (setq eee_ename_obj_ (vlax-ename->vla-object eee_ename_))))
        (setq new_ename_ (car (entsel "specify Object for input fillter_block_name")))
        (setq new_ename_obj_ (vlax-ename->vla-object new_ename_))
      ;
      ;checking_process
        (if 
          (and 
            (= (setq alert_val_1 (vla-get-objectname eee_ename_obj_)) "AcDbBlockReference")
            (= (setq alert_val_2 (LM:effectivename new_ename_obj_)) "000 - BOX_EF_NAME")
            (/= eee_ename_ dynamic_ename_)
          )
          (progn
            ;get_data_old_EF_NAME_
              (setq old_block_name_ (LM:effectivename (setq eee_ename_obj_ (vlax-ename->vla-object eee_ename_))))
            ;
            ;get_data
              (setq new_ef_name_ (LM:vl-getattributevalue new_ename_obj_ "nameblk"  ))
            ;
          )
          (alert "SOMETHING BAD")
        )
      ;
      ;Rename_process
        (command "rename" "B" old_block_name_ new_ef_name_)
      ;
          


    )
    ; (defun TA:renameblock_ (Old_name New_name)
    ;   ; (setq Old_name "W-2-PP20-AR-4280-01-A_20260115-120954_ASDADADSDESW24")
    ;   ; (setq New_name "W-2-PP20-AR-4180-01-A_20260217_092300_NEWLIGHT")
    ;   (setq doc (vla-get-ActiveDocument (vlax-get-acad-object)))
    ;   (if (and 
    ;         (= (type (vl-catch-all-apply (function (lambda () (vla-Item (vla-get-Blocks doc) Old_name) ) ) ) ) 'VLA-OBJECT)
    ;         (= (type (vl-catch-all-apply (function (lambda () (vla-Item (vla-get-Blocks doc) New_name) ) ) ) ) 'VL-CATCH-ALL-APPLY-ERROR)
    ;       )
    ;     (progn
    ;       (command "rename" "B" Old_name New_name)
    ;     )
    ;     (princ "SOMETHING BAD" )
    ;   )
    ; )
    ; (TA:renameblock_ "A$Cd7765226" "000 - RECEED_DIM")
    (defun c:rename_block_RENBLKV4_RENB4 ()
      (setq text1_ename_ (car (entsel "specify Old Object")))
      (setq text1_obj_EFNAME (LM:effectivename (vlax-ename->vla-object text1_ename_)))
      (setq Er-msg_EFNAME_TARGET nil)
      (setq Er-msg_block-def nil)
      ;checking_process
      (if 
        (and 
          (setq doc (vla-get-ActiveDocument (vlax-get-acad-object)))
          (=
            (type
              (setq Er-msg_EFNAME_TARGET
                (vl-catch-all-apply
                  (function
                    (lambda ()
                      (setq EFNAME_TARGET_ (vla-get-textstring (vlax-ename->vla-object (car (entsel "specify EFNAME_TARGET Object\n Object should be Text or Mtext" ) ) ) ) )
                    )
                  )
                )
              )
            )
          'STR
          )
          (=
            (type
              (setq Er-msg_block-def
                (vl-catch-all-apply
                  (function
                    (lambda ()
                      (setq block-def
                        (vla-Item
                          (vla-get-Blocks doc)
                          Er-msg_EFNAME_TARGET
                        )
                      )
                    )
                  )
                )
              )
            )
          'VL-CATCH-ALL-APPLY-ERROR
          )
        )
        (progn
          (command "rename" "b" text1_obj_EFNAME Er-msg_EFNAME_TARGET )
        )
        (alert "SOMETHING BAD")
      )
      ;
    )
    (defun c:limit_content_name_[limittext_] ()
      ;Note By Code_Developer
      ;This command is designed to work exclusively with a block named 'CONTENT NAME3 LEFT - BUBBLE v6'.
      ;The operation of the command will read the block's attribute values and regenerate By this command can limit number of chhracters per line.
      ;Due to this code is designed to work exclusively with a block named "CONTENT NAME3 LEFT - BUBBLE v6"
      ;Fully command must have sub-functions with names starting with TA: or LM:
      ;
      ;
      ;
      ;fillter_content_name_object_
        (setq content_ename_ nil)
        (while (= content_ename_ nil)
          ;user_input_data
            (setq content_ename_ (car (entsel "specify Object")))
            (setq limit_text_length (cond ( (getint (strcat "\nSpecify limit_text_count   <" (rtos (setq limit_text_length (cond (limit_text_length) (1.0) ) ) ) "> : " ) ) ) (limit_text_length) ) )
          ;
          ;fillter_object_type_
            (if 
              (and
                (if (/= content_ename_ nil) (progn (setq content_obj_ (vlax-ename->vla-object content_ename_)) ))
                (= (vla-get-objectname content_obj_) "AcDbBlockReference")
                (= (vla-get-hasattributes content_obj_) :vlax-true )
                (= (LM:effectivename content_obj_) "CONTENT NAME3 LEFT - BUBBLE v6" )
              )
              (progn ;MAIN_IDEA
                ;getdata_limit_text_
                  (setq content_tag_list_ (LM:removenth 9 (LM:vl-getattributevalues content_obj_)))
                  (setq content_tag_list_length_ (strlen 
                                                  (cdr (nth 0 content_tag_list_))
                                                  (cdr (nth 1 content_tag_list_))
                                                  (cdr (nth 2 content_tag_list_))
                                                  (cdr (nth 3 content_tag_list_))
                                                  (cdr (nth 4 content_tag_list_))
                                                  (cdr (nth 5 content_tag_list_))
                                                  (cdr (nth 6 content_tag_list_))
                                                  (cdr (nth 7 content_tag_list_))
                                                  (cdr (nth 8 content_tag_list_))
                                                  
                                                  "_"
                                                )
                  )
                  (setq content_tag_list_value_ (strcat 
                                                  (cdr (nth 0 content_tag_list_))
                                                  (cdr (nth 1 content_tag_list_))
                                                  (cdr (nth 2 content_tag_list_))
                                                  (cdr (nth 3 content_tag_list_))
                                                  (cdr (nth 4 content_tag_list_))
                                                  (cdr (nth 5 content_tag_list_))
                                                  (cdr (nth 6 content_tag_list_))
                                                  (cdr (nth 7 content_tag_list_))
                                                  (cdr (nth 8 content_tag_list_))
                                                  
                                                  "_"
                                                )
                  )
                  
                  (setq sum_text_ (list content_tag_list_length ))
                  (setq sum_text_name (list content_tag_list_value_))
                  (setq sum_text_name (LM:lst->str sum_text_name ""))
                  (setq sum_text_name (LM:str->lst sum_text_name "_"))
                  (setq sum_text_name (TA:REMOVE_VAL_LIST_ "" sum_text_name ))
                  
                  (setq sum_text_ (TA:REMOVE_VAL_LIST_ nil sum_text_))
                ;
                ;preparing_summary_data_
                  (setq sum_text_i 0)
                  (setq sum_text_len 0)
                  ; (setq new_text_line_0 ())
                  (setq new_text_line_1 ())
                  (setq new_text_line_2 ())
                  (setq new_text_line_3 ())
                  (setq new_text_line_4 ())
                  (setq new_text_line_5 ())
                  (setq new_text_line_6 ())
                  (setq new_text_line_7 ())
                  (setq new_text_line_8 ())
                  (setq new_text_line_9 ())
                  (setq new_text_line_10 ())
                ;
                ;summary_limit_text_to_line
                  (setq limit_text_length limit_text_length)
                  (while (and (< sum_text_i (length sum_text_name)) (< sum_text_len 500))
                    (setq sum_text_ename_name (nth  sum_text_i sum_text_name))
                    (setq sum_text_len (+ (+ sum_text_len (strlen sum_text_ename_name) ) 1))
                    ;main_IDEA_limit_text_process
                      (cond
                        ( ;line_1
                          (<= sum_text_len limit_text_length)
                          (progn
                            (setq new_text_line_1 (cons sum_text_ename_name new_text_line_1 ))
                          )
                          (princ "line_1")
                        )
                        ( ;line_2
                          (and (> sum_text_len (* limit_text_length 1)) (< sum_text_len (* limit_text_length 2)) )
                          (progn
                            (setq new_text_line_2 (cons sum_text_ename_name new_text_line_2 ))
                          )
                          (princ "line_2")
                        )
                        ( ;line_3
                          (and (>= sum_text_len (* limit_text_length 2)) (< sum_text_len (* limit_text_length 3)) )
                          (progn
                            (setq new_text_line_3 (cons sum_text_ename_name new_text_line_3 ))
                          )
                          (princ "line_3")
                        )
                        ( ;line_4
                          (and (>= sum_text_len (* limit_text_length 3)) (< sum_text_len (* limit_text_length 4)) )
                          (progn
                            (setq new_text_line_4 (cons sum_text_ename_name new_text_line_4 ))
                          )
                          (princ "line_4")
                        )
                        ( ;line_5
                          (and (>= sum_text_len (* limit_text_length 4)) (< sum_text_len (* limit_text_length 5)) )
                          (progn
                            (setq new_text_line_5 (cons sum_text_ename_name new_text_line_5 ))
                          )
                          (princ "line_5")
                        )
                        ( ;line_6
                          (and (>= sum_text_len (* limit_text_length 6)) (< sum_text_len (* limit_text_length 7)) )
                          (progn
                            (setq new_text_line_6 (cons sum_text_ename_name new_text_line_6 ))
                          )
                          (princ "line_6")
                        )
                        ( ;line_7
                          (and (>= sum_text_len (* limit_text_length 7)) (< sum_text_len (* limit_text_length 8)) )
                          (progn
                            (setq new_text_line_7 (cons sum_text_ename_name new_text_line_7 ))
                          )
                          (princ "line_7")
                        )
                        ( ;line_8
                          (and (>= sum_text_len (* limit_text_length 8)) (< sum_text_len (* limit_text_length 9)) )
                          (progn
                            (setq new_text_line_8 (cons sum_text_ename_name new_text_line_8 ))
                          )
                          (princ "line_8")
                        )
                        ( ;line_9
                          (and (>= sum_text_len (* limit_text_length 9)) (< sum_text_len (* limit_text_length 10)) )
                          (progn
                            (setq new_text_line_9 (cons sum_text_ename_name new_text_line_9 ))
                          )
                          (princ "line_9")
                        )
                      )
                    ;
                    (setq sum_text_i (+ sum_text_i 1))
                  )
                  (setq limit_text_value_set_ 
                                              (TA:REMOVE_VAL_LIST_ 
                                                ""
                                                (list 
                                                  (setq new_text_line_1_sum (LM:lst->str (reverse new_text_line_1) "_" ) )
                                                  (setq new_text_line_2_sum (LM:lst->str (reverse new_text_line_2) "_" ) )
                                                  (setq new_text_line_3_sum (LM:lst->str (reverse new_text_line_3) "_" ) )
                                                  (setq new_text_line_4_sum (LM:lst->str (reverse new_text_line_4) "_" ) )
                                                  (setq new_text_line_5_sum (LM:lst->str (reverse new_text_line_5) "_" ) )
                                                  (setq new_text_line_6_sum (LM:lst->str (reverse new_text_line_6) "_" ) )
                                                  (setq new_text_line_7_sum (LM:lst->str (reverse new_text_line_7) "_" ) )
                                                  (setq new_text_line_8_sum (LM:lst->str (reverse new_text_line_8) "_" ) )
                                                  (setq new_text_line_9_sum (LM:lst->str (reverse new_text_line_9) "_" ) )
                                                )
                                              )
                  )
                ;
                ;Clear_att_process_
                  (setq except_att_list_ (list "NO.CODE") )
                  (TA:remove_att_value_ content_obj_ except_att_list_)
                ;
                ;preloop_and_while_limit_text_to_line
                    (setq limit_text_i 0)
                    (while (< limit_text_i (length limit_text_value_set_))
                      (setq content_tag_list_att (car (nth limit_text_i content_tag_list_))) ;att_tag
                      (setq limit_text_list_ (nth limit_text_i limit_text_value_set_)) ;att_value
                      
                      (if (/= limit_text_list_ nil)
                        (progn
                          (LM:vl-setattributevalue content_obj_ content_tag_list_att (strcat limit_text_list_ "_") )
                        )
                        (LM:vl-setattributevalue content_obj_ content_tag_list_att "" )
                      )
                  
                      (setq limit_text_i (+ limit_text_i 1))
                    )
                ;
                ;indicate_visibility_BLK_atttribute
                  (setq limit_text_vis_ (TA:REMOVE_VAL_LIST_ "" limit_text_value_set_))
                  (LM:setdynpropvalue content_obj_ "content_line" (rtos(length limit_text_vis_)2 0))
                ;
              
              )
              (setq content_ename_ nil)
            )
              
            
            
            (if
              (or
                (= content_ename_ nil)
                (/= (vla-get-objectname content_obj_) "AcDbBlockReference")
                (if (= (vla-get-objectname content_obj_) "AcDbBlockReference") (progn (/= (vla-get-hasattributes content_obj_) :vlax-true ) ))
              )
              (progn
                (alert "Please selection attribute object")
              )
            )
          ;
        )
      ;
    )
    (defun c:replace_text_attribute_retatt_ ()
      
      (setq replace_old_text_ (getstring (strcat "\nSpecify old_text <" (if replace_old_text_ replace_old_text_ "") ">: ") ) )
      (setq replace_new_text_ (getstring (strcat "\nSpecify new_text <" (if replace_new_text_ replace_new_text_ "") ">: ") ) )
      
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget 
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i ))
          (setq ss_pre_filter_set_xx_obj_ (vlax-ename->vla-object ss_pre_filter_set_xx_ename_))
          
          (setq att_list_ (LM:vl-getattributevalues ss_pre_filter_set_xx_obj_))
          
          ;preloop_and_while
            (setq att_list_i 0)
            (while (< att_list_i (length att_list_))
              (setq att_list_head_ (car (nth  att_list_i att_list_)))
              (setq att_list_val_ (cdr (nth  att_list_i att_list_)))
              
              (LM:vl-setattributevalue ss_pre_filter_set_xx_obj_ att_list_head_ (LM:StringSubst replace_new_text_ replace_old_text_ att_list_val_))
          
              (setq att_list_i (+ att_list_i 1))
            )
          ;
          

          (setq ss_pre_filter_set_xx_i (+ ss_pre_filter_set_xx_i 1))
        )
      ;

      
      
      
      
    )
    
  ;
  ;Joint_FUNC
    (defun c:joint_line_JOL ()
      
      ;Note By Code_Developer
      ;This command is designed to work exclusively with a LWPOLYLINE espectespecially object from offset line
      ;The principle of this code is to read the insertion points (vertices) of the polyline at the head and tail,then create polylines at both insertion points and join them together.
      ;
      (_startundo doc)
      ;joint_pline
        ;selection_set
          (if  ;pre_select_ssget_or_post_select_ssget
            (= 
              (setq ss_pre_filter_set_xx_ (ssget "I" 
                                                (list 
                                                  (cons 0 "lwpolyline") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn 
              (setq ss_pre_filter_set_xx_ (ssget 
                                            (list 
                                              (cons 0 "lwpolyline") ;type of object
                                              ; (cons 8 "000 - GRID")   ;kind of layer
                                              ; (cons 2 "000-GRIDLINE_DYN")       ;kind of nameblock
                                              ; (cons 62 1)           ;kind of color call sign with color code index
                                            )
                                          )
              )
            )
            (sslength ss_pre_filter_set_xx_)
          )
        ;
        ;condition_rule_for_run
          (if (= (sslength ss_pre_filter_set_xx_) 2)
            (progn
              ;preloop_and_while
                (setq ss_pre_filter_set_xx_i 0)
                (setq ss_pre_filter_set_xx_ii 1)
                (while (< ss_pre_filter_set_xx_i 1)
                  ;first_pline_process
                    (setq ss_pre_filter_set_xx_i_ename_ (ssname ss_pre_filter_set_xx_ ss_pre_filter_set_xx_i))
                      (setq ss_pre_filter_set_xx_i_obj_ (vlax-ename->vla-object ss_pre_filter_set_xx_i_ename_))
                        (setq ss_pre_filter_set_xx_i_obj_vertex_len_ (cadr (TA:Get_Pline_vertext_ins_point_ ss_pre_filter_set_xx_i_ename_)))
                        ;reverse insertion point 
                          (if (>
                                (car (car (cadr (TA:Get_Pline_vertext_ins_point_ ss_pre_filter_set_xx_i_ename_))))
                                (car (car (reverse (cadr (TA:Get_Pline_vertext_ins_point_ ss_pre_filter_set_xx_i_ename_)))))
                              )
                            (progn
                              (command "reverse" ss_pre_filter_set_xx_i_ename_ "")
                              (setq ss_pre_filter_set_xx_i_obj_vertex_len_ (cadr (TA:Get_Pline_vertext_ins_point_ ss_pre_filter_set_xx_i_ename_)))
                            )
                          )
                        ;
                          (setq ss_pre_filter_set_xx_i_obj_vertex_len_headline_ (nth 0 ss_pre_filter_set_xx_i_obj_vertex_len_))
                          (setq ss_pre_filter_set_xx_i_obj_vertex_len_botline_ (nth (- (length ss_pre_filter_set_xx_i_obj_vertex_len_) 1) ss_pre_filter_set_xx_i_obj_vertex_len_))
                    ;copy_pline_object
                      ; (vla-copy ss_pre_filter_set_xx_i_obj_)
                    ;
                  ;
                  ;second_pline_process
                    (setq ss_pre_filter_set_xx_ii_ename_ (ssname ss_pre_filter_set_xx_ ss_pre_filter_set_xx_ii))
                      (setq ss_pre_filter_set_xx_ii_obj_ (vlax-ename->vla-object ss_pre_filter_set_xx_ii_ename_))

                        (setq ss_pre_filter_set_xx_ii_obj_vertex_len_ (cadr (TA:Get_Pline_vertext_ins_point_ ss_pre_filter_set_xx_ii_ename_)))
                        ;reverse insertion point 
                          (if (>
                                (car (car (cadr (TA:Get_Pline_vertext_ins_point_ ss_pre_filter_set_xx_ii_ename_))))
                                (car (car (reverse (cadr (TA:Get_Pline_vertext_ins_point_ ss_pre_filter_set_xx_ii_ename_)))))
                              )
                            (progn
                              (command "reverse" ss_pre_filter_set_xx_ii_ename_ "")
                              (setq ss_pre_filter_set_xx_ii_obj_vertex_len_ (cadr (TA:Get_Pline_vertext_ins_point_ ss_pre_filter_set_xx_ii_ename_)))
                            )
                          )
                        ;
                          (setq ss_pre_filter_set_xx_ii_obj_vertex_len_headline_ (nth 0 ss_pre_filter_set_xx_ii_obj_vertex_len_))
                          (setq ss_pre_filter_set_xx_ii_obj_vertex_len_botline_ (nth (- (length ss_pre_filter_set_xx_ii_obj_vertex_len_) 1) ss_pre_filter_set_xx_ii_obj_vertex_len_))
                    ;copy_pline_object
                      ; (vla-copy ss_pre_filter_set_xx_ii_obj_)
                    ;
                  ;
                  ;making_pline_process_
                    (setvar "osmode" 0)
                    (if (= (getvar "worlducs") 0)(progn (setq ss_pre_filter_set_xx_ii_obj_vertex_len_headline_ (trans ss_pre_filter_set_xx_ii_obj_vertex_len_headline_ 0 1))) ss_pre_filter_set_xx_ii_obj_vertex_len_headline_ )
                    (if (= (getvar "worlducs") 0)(progn (setq ss_pre_filter_set_xx_ii_obj_vertex_len_botline_ (trans ss_pre_filter_set_xx_ii_obj_vertex_len_botline_ 0 1))) ss_pre_filter_set_xx_ii_obj_vertex_len_botline_ )
                    (if (= (getvar "worlducs") 0)(progn (setq ss_pre_filter_set_xx_i_obj_vertex_len_headline_ (trans ss_pre_filter_set_xx_i_obj_vertex_len_headline_ 0 1))) ss_pre_filter_set_xx_i_obj_vertex_len_headline_ )
                    (if (= (getvar "worlducs") 0)(progn (setq ss_pre_filter_set_xx_i_obj_vertex_len_botline_ (trans ss_pre_filter_set_xx_i_obj_vertex_len_botline_ 0 1))) ss_pre_filter_set_xx_i_obj_vertex_len_botline_ )
                    (create-pline (list ss_pre_filter_set_xx_i_obj_vertex_len_headline_ ss_pre_filter_set_xx_ii_obj_vertex_len_headline_)) ;head_of_line
                      (setq new_joint_headline_ (entlast))
                    (create-pline (list ss_pre_filter_set_xx_i_obj_vertex_len_botline_ ss_pre_filter_set_xx_ii_obj_vertex_len_botline_)) ;bot_of_line
                      (setq new_joint_botline_ (entlast))
                  ;
                  ;Jointline_process
                    (command "join" new_joint_headline_ new_joint_botline_ ss_pre_filter_set_xx_i_ename_ ss_pre_filter_set_xx_ii_ename_ "")
                  ;
                  (setq ss_pre_filter_set_xx_i (+ ss_pre_filter_set_xx_i 1))
                )
              ;
              (setvar "osmode" 1215)
              (command "draworder"  "L" "" "B") 

            )
          )
        ;
      ;
      (_EndUndo doc)
    )
    
    (defun TA:joint_line_JOL (ss_pre_filter_set_xx_ )
      ;Note By Code_Developer
      ;This command is designed to work exclusively with a LWPOLYLINE espectespecially object from offset line
      ;The principle of this code is to read the insertion points (vertices) of the polyline at the head and tail,then create polylines at both insertion points and join them together.
      ;
      (_startundo doc)
        ;joint_pline
          ;condition_rule_for_run
            (if (and 
                  (/= ss_pre_filter_set_xx_ nil)
                  (= (sslength ss_pre_filter_set_xx_) 2)
                )
              (progn
                ;preloop_and_while
                  (setq ss_pre_filter_set_xx_i 0)
                  (setq ss_pre_filter_set_xx_ii 1)
                  (while (< ss_pre_filter_set_xx_i 1)
                    ;first_pline_process
                      (setq ss_pre_filter_set_xx_i_ename_ (ssname ss_pre_filter_set_xx_ ss_pre_filter_set_xx_i))
                        (setq ss_pre_filter_set_xx_i_obj_ (vlax-ename->vla-object ss_pre_filter_set_xx_i_ename_))
                          (setq ss_pre_filter_set_xx_i_obj_vertex_len_ (cadr (TA:Get_Pline_vertext_ins_point_ ss_pre_filter_set_xx_i_ename_)))

                            (setq ss_pre_filter_set_xx_i_obj_vertex_len_headline_ (nth 0 ss_pre_filter_set_xx_i_obj_vertex_len_))
                            (setq ss_pre_filter_set_xx_i_obj_vertex_len_botline_ (nth (- (length ss_pre_filter_set_xx_i_obj_vertex_len_) 1) ss_pre_filter_set_xx_i_obj_vertex_len_))
                      ;copy_pline_object
                        ; (vla-copy ss_pre_filter_set_xx_i_obj_)
                      ;
                    ;
                    ;second_pline_process
                      (setq ss_pre_filter_set_xx_ii_ename_ (ssname ss_pre_filter_set_xx_ ss_pre_filter_set_xx_ii))
                        (setq ss_pre_filter_set_xx_ii_obj_ (vlax-ename->vla-object ss_pre_filter_set_xx_ii_ename_))

                          (setq ss_pre_filter_set_xx_ii_obj_vertex_len_ (cadr (TA:Get_Pline_vertext_ins_point_ ss_pre_filter_set_xx_ii_ename_)))

                            (setq ss_pre_filter_set_xx_ii_obj_vertex_len_headline_ (nth 0 ss_pre_filter_set_xx_ii_obj_vertex_len_))
                            (setq ss_pre_filter_set_xx_ii_obj_vertex_len_botline_ (nth (- (length ss_pre_filter_set_xx_ii_obj_vertex_len_) 1) ss_pre_filter_set_xx_ii_obj_vertex_len_))
                      ;copy_pline_object
                        ; (vla-copy ss_pre_filter_set_xx_ii_obj_)
                      ;
                    ;
                    ;making_pline_process_
                      (setvar "osmode" 0)
                      (if (= (getvar "worlducs") 0)(progn (setq ss_pre_filter_set_xx_ii_obj_vertex_len_headline_ (trans ss_pre_filter_set_xx_ii_obj_vertex_len_headline_ 0 1))) ss_pre_filter_set_xx_ii_obj_vertex_len_headline_ )
                      (if (= (getvar "worlducs") 0)(progn (setq ss_pre_filter_set_xx_ii_obj_vertex_len_botline_ (trans ss_pre_filter_set_xx_ii_obj_vertex_len_botline_ 0 1))) ss_pre_filter_set_xx_ii_obj_vertex_len_botline_ )
                      (if (= (getvar "worlducs") 0)(progn (setq ss_pre_filter_set_xx_i_obj_vertex_len_headline_ (trans ss_pre_filter_set_xx_i_obj_vertex_len_headline_ 0 1))) ss_pre_filter_set_xx_i_obj_vertex_len_headline_ )
                      (if (= (getvar "worlducs") 0)(progn (setq ss_pre_filter_set_xx_i_obj_vertex_len_botline_ (trans ss_pre_filter_set_xx_i_obj_vertex_len_botline_ 0 1))) ss_pre_filter_set_xx_i_obj_vertex_len_botline_ )
                      (create-pline (list ss_pre_filter_set_xx_i_obj_vertex_len_headline_ ss_pre_filter_set_xx_ii_obj_vertex_len_headline_)) ;head_of_line
                        (setq new_joint_headline_ (entlast))
                      (create-pline (list ss_pre_filter_set_xx_i_obj_vertex_len_botline_ ss_pre_filter_set_xx_ii_obj_vertex_len_botline_)) ;bot_of_line
                        (setq new_joint_botline_ (entlast))
                    ;
                    ;Jointline_process
                      (command "join" new_joint_headline_ new_joint_botline_ ss_pre_filter_set_xx_i_ename_ ss_pre_filter_set_xx_ii_ename_ "")
                    ;
                    (setq ss_pre_filter_set_xx_i (+ ss_pre_filter_set_xx_i 1))
                  )
                ;
                (setvar "osmode" 1215)
                ; (command "draworder"  "L" "" "B") 

              )
            )
          ;
        ;
      (_EndUndo doc)
    )
  ;
  ;Selection_FUNC
    (defun c:call_global_selction_set_cgs ()
      ;Note By Code_Developer
      ;pripciple of codework is designed for call nominal selection 
      ;
      ;
      (command "pselect"  global_selction_set_ "" )
    )
    (defun c:filter_object_and_selection_[sscircle] () ;ssget["Depend_On_User"]
      ;Note By Code_Developer
      ;The principle of codework is to selection object by ssget method via variable name [ss_pre_filter_set_xx_]
      ;Example code 
      ;
      
      (if  ;pre_select_ssget_or_post_select_ssget
        (= 
          (setq ss_pre_filter_set_xx_ (ssget "I" 
                                            (list 
                                              (cons 0 "circle") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "circle") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
      (command "pselect" ss_pre_filter_set_xx_ "")
    )
    (defun c:filter_object_and_selection_[sspline] ()
      (if  ;pre_select_ssget_or_post_select_ssget
        (= 
          (setq ss_pre_filter_set_xx_ (ssget "I" 
                                            (list 
                                              (cons 0 "LWPOLYLINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "LWPOLYLINE") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )

      ;preloop_and_while
        (command "pselect"  ss_pre_filter_set_xx_ "" )
      ;
      
    )
    (defun c:make_selection_set_boudary_line_OVLBOL ()
      (setq sss_ (ssget ))
      (setvar "osmode" 0)
      (setq ssssasas (TA:ss_vla-getboundingbox sss_))
      (if (= (getvar "worlducs") 1) ;รอแก้
        (progn
          (setq sode (list (trans (car ssssasas) 1 0) (trans (cadr ssssasas) 1 0) ) )
        )
        (setq sode (list (trans (car ssssasas) 0 1) (trans (cadr ssssasas) 0 1) ) )
      )
      (command "rectangle" (car sode) (cadr sode) )
      (setvar "osmode" 1215)
      ;new_blk_entlast object
        (setq ss_ename (entlast))
        (setq ss_obj (vlax-ename->vla-object ss_ename))
        (vla-put-color ss_obj 256)
      ;
    )
    (defun c:make_selection_set_boudary_line_OVLBOL ()
      (setq sss_ (ssget ))
      (setvar "osmode" 0)
      (setq ssssasas (TA:ss_vla-getboundingbox sss_))
      (if (= (getvar "worlducs") 1) ;รอแก้
        (progn
          (setq ssssasas (list (trans (car ssssasas) 1 0) (trans (cadr ssssasas) 1 0) ) )
        )
        (setq ssssasas (list (trans (car ssssasas) 0 1) (trans (cadr ssssasas) 0 1) ) )
      )
      (command "rectangle" (car ssssasas) (cadr ssssasas) )
      (setvar "osmode" 1215)
      ;new_blk_entlast object
        (setq ss_ename (entlast))
        (setq ss_obj (vlax-ename->vla-object ss_ename))
        (vla-put-color ss_obj 256)
      ;
    )
    (defun c:make_selection_set_boudary_line_MULBOL ()
      ;selection_set_for_fillter_blk_name
        (if  ;pre_select_ssget_or_post_select_ssget
          (=
            (setq ss_pre_filter_set_xx_ (ssget "i"
                                              (list
                                                (cons 0 "INSERT,line,lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT,line,lwpolyline") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (setq ss_pre_filter_set_xx_obj_getboundingbox (vla-getboundingbox ss_pre_filter_set_xx_obj_ 'min_ 'max_)) 
          (setq ss_pre_filter_set_xx_min_ (vlax-safearray->list min_)) 
          (setq ss_pre_filter_set_xx_max_ (vlax-safearray->list max_)) 
          (command "rectangle" ss_pre_filter_set_xx_min_ ss_pre_filter_set_xx_max_)
          (setq ss_pre_filter_set_xx_i (+ ss_pre_filter_set_xx_i 1))
        )
      ;
        (initget "Yes No")
        (setq ss_ ;Detect the variable's result in case of a function error
          (vl-catch-all-apply 
            (function 
              (lambda () 
                (setq DELETE_OBJ_ (not (eq "No" (getkword "\nKeep Existing object? [Yes/No] <Y>: "))))
              )
            )
          )
        )
        (if (= DELETE_OBJ_ t)
          (progn
            (princ "pass")
          )
          (command "erase" ss_pre_filter_set_xx_  )
        )
    )
    (defun c:copybase_selection_set_boudary_line_CCBOL ()
      (setq sss_ (ssget ))
      (setvar "osmode" 0)
      (setq ssssasas (TA:ss_vla-getboundingbox sss_))
      (command "rectangle" (car ssssasas) (cadr ssssasas) )
      (setq new_ename_ (entlast))
      (setq new_obj_ (vlax-ename->vla-object new_ename_))
      (vla-put-color new_obj_ 0)
      (ssadd new_ename_ sss_)
      (sslength sss_)
      (command "_copybase" (LM:PolyCentroid new_ename_) sss_ "" )
      (setvar "osmode" 1215)
      (command "_pasteblock" )
      
    )
    (defun c:selection_by_handent_hand_ ()
      (setq copytext_val (LM:StringSubst "" "\r\n" (TA:GetClipboardText)))
      (setq copytext_ (LM:StringSubst "" "\r\n" (TA:GetClipboardText)))
      (setq copytext_ ;Get-string by keep previous value
          (if
            (or
              (/= (setq copytext_val (getstring (strcat "\nSpecify Pattern name <" (if copytext_ copytext_ "") ">: ") ) ) "" )
            )
              (progn
                (setq copytext_ copytext_val)
                (setq copytext_keep_val_ copytext_val)
              )
            (setq copytext_val (TA:GetClipboardText))
          )
      )
      (command "pselect"  (setq temozoom_ (handent copytext_val)) "" )
      ; (setq ERR_
      ;   (vl-catch-all-apply
      ;     (function
      ;       (lambda ()
      ;         (if (= (getint "zoom object" ) 1)
      ;           (progn
      ;             (command "zoom" )
      ;             (command "pselect"  (setq temozoom_ (handent copytext_val)) "" )
      ;           )
      ;         )
      ;       )
      ;     )
      ;   )
      ; )
            

    )
    (defun c:lastselect_entity_lse ()
      (command "pselect"  (entlast) "" )
    )
    (defun c:lastselection_lss ()
      (command "pselect"  ss_pre_filter_set_xx_  "" )
    )
    (defun TA:combine_selection_set_ (ss1 ss2 / newSS i ent)
      (setq newSS (ssadd)) ; สร้าง selection set ว่าง
      
      ;; ใส่สมาชิกจาก ss1
      (if ss1
        (progn
          (setq i 0)
          (while (< i (sslength ss1))
            (setq ent (ssname ss1 i))
            (ssadd ent newSS)
            (setq i (1+ i))
          )
        )
      )

      ;; ใส่สมาชิกจาก ss2
      (if ss2
        (progn
          (setq i 0)
          (while (< i (sslength ss2))
            (setq ent (ssname ss2 i))
            (ssadd ent newSS)
            (setq i (1+ i))
          )
        )
      )

      newSS ; return selection set ที่รวมแล้ว
    )
    (defun c:quick_select_yellow_qyel ()
      ;selection_set_for_fillter_blk_name
        (if  ;pre_select_ssget_or_post_select_ssget
          (=
            (setq ss_pre_filter_set_xx_ (ssget "i"
                                              (list
                                                (cons 0 "line") ;type of object
                                                ; (cons 8 "000 - GRID")   ;kind of layer
                                                ; (cons 2 "000-GRID_LINE_DYN")       ;kind of nameblock
                                                (cons 62 2)           ;kind of color call sign with color code index
                                              )
                                        )
            )
            nil
          )
          (progn
            (setq ss_pre_filter_set_xx_ (ssget
                                              (list
                                                (cons 0 "line") ;type of object
                                                ; (cons 8 "000 - GRID")   ;kind of layer
                                                ; (cons 2 "000-GRID_LINE_DYN")       ;kind of nameblock
                                                (cons 62 2)           ;kind of color call sign with color code index
                                              )
                                        )
            )
          )
          (sslength ss_pre_filter_set_xx_)
        )
        (command "qdim"  ss_pre_filter_set_xx_  )
      ;
    )
    (defun c:quick_select_yellow_qwpe ()
      ;selection_set_for_fillter_blk_name
        (if  ;pre_select_ssget_or_post_select_ssget
          (=
            (setq ss_pre_filter_set_xx_ (ssget "i"
                                              (list
                                                (cons 0 "wipeout") ;type of object
                                                ; (cons 8 "000 - GRID")   ;kind of layer
                                                ; (cons 2 "000-GRID_LINE_DYN")       ;kind of nameblock
                                                ; (cons 62 2)           ;kind of color call sign with color code index
                                              )
                                        )
            )
            nil
          )
          (progn
            (setq ss_pre_filter_set_xx_ (ssget
                                              (list
                                                (cons 0 "wipeout") ;type of object
                                                ; (cons 8 "000 - GRID")   ;kind of layer
                                                ; (cons 2 "000-GRID_LINE_DYN")       ;kind of nameblock
                                                ; (cons 62 2)           ;kind of color call sign with color code index
                                              )
                                        )
            )
          )
          (sslength ss_pre_filter_set_xx_)
        )
        
      ;
      (command "pselect"  ss_pre_filter_set_xx_ "" )
    )
    (defun c:select_inside_selinside ()
      ;back of code
        ;choosen list
          (setq selection_object_list_ (list 
                                          "circle"
                                          "insert"
                                          "line,lwpolyline"
                                       )
          )
        ;
      ;
      
      (setq pl_ename_ (car (entsel "specify Object")))
      (setq pl_obj_ (vlax-ename->vla-object pl_ename_))
      (setq pl_entget_ (entget pl_ename_))
      (setq pl_entget_list_vtx_pt_  (mapcar 'cdr (vl-remove-if-not '(lambda (x) (= 10 (car x))) pl_entget_)))
      
      (setq ERR_
        (vl-catch-all-apply
          (function
            (lambda ()
              (setq selection_object_list_value_ (TA:choose_list_ selection_object_list_))
            )
          )
        )
      )
      (if (= (vl-catch-all-error-p err) nil)
        (progn
          (setvar "osmode" 0)
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "CP" pl_entget_list_vtx_pt_
                                                  (list
                                                    (cons 0 "circle") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          (setvar "osmode" 1215)
          (command "pselect" ss_pre_filter_set_xx_  "" )
        )
      )


      
    )
    (defun c:save_selection_savess_ ()
      (setq a "a = slot 1 (empty)"
            b "b = slot 2 (empty)"
            c "c = slot 3 (empty)"
            d "d = slot 4 (empty)"
            e "e = slot 5 (empty)"
            f "f = slot 6 (empty)"
            g "g = slot 7 (empty)"
            h "h = slot 8 (empty)"
            i "i = slot 9 (empty)"
            j "j = slot 10 (empty)"
      )
      (setq ss_list_ (list ssA ssB ssC ssD ssE ssF ssH ssI ssJ))
      ;preloop_and_while
        (setq ss_list_i 0)
        (while (< ss_list_i (length ss_list_))
          (setq ss_list_val_ (nth 0 ss_list_))
          (cond
            (;_case_1
              (and
                  (= ss_list_i 0)
                  (/= ssA nil)
              )
              (progn
                (setq a "a = slot 1 (full)")
                (princ "_case_1")
              )
            )
            (;_case_2
              (and
                  (= ss_list_i 1)
                  (/= ssB nil)
              )
              (progn
                (setq b "b = slot 2 (full)")
                (princ "_case_2")
              )
            )
            (;_case_3
              (and
                  (= ss_list_i 2)
                  (/= ssC nil)
              )
              (progn
                (setq c "c = slot 3 (full)")
                (princ "_case_3")
              )
            )
            (;_case_4
              (and
                  (= ss_list_i 3)
                  (/= ssD nil)
              )
              (progn
                (setq d "d = slot 4 (full)")
                (princ "_case_4")
              )
            )
            (;_case_5
              (and
                  (= ss_list_i 4)
                  (/= ssE nil)
              )
              (progn
                (setq e "e = slot 5 (full)")
                (princ "_case_5")
              )
            )
            (;_case_6
              (and
                  (= ss_list_i 5)
                  (/= ssF nil)
              )
              (progn
                (setq f "f = slot 6 (full)")
                (princ "_case_6")
              )
            )
            (;_case_7
              (and
                  (= ss_list_i 6)
                  (/= ssG nil)
              )
              (progn
                (setq g "g = slot 7 (full)")
                (princ "_case_7")
              )
            )
            (;_case_8
              (and
                  (= ss_list_i 7)
                  (/= ssH nil)
              )
              (progn
                (setq h "h = slot 8 (full)")
                (princ "_case_8")
              )
            )
            (;_case_9
              (and
                  (= ss_list_i 8)
                  (/= ssI nil)
              )
              (progn
                (setq i "i = slot 9 (full)")
                (princ "_case_9")
              )
            )
            (;_case_10
              (and
                  (= ss_list_i 9)
                  (/= ssJ nil)
              )
              (progn
                (setq j "j= slot 10 (full)")
                (princ "_case_10")
              )
            )
          )
      
          (setq ss_list_i (+ ss_list_i 1))
        )
      ;
      (setq visibility_mode_value_ (cond ((getint (strcat a"\n"b"\n"c"\n"d"\n" e"\n" f"\n" g"\n" h"\n" i"\n" j"\n" "<" (rtos (setq visibility_mode_value_ (cond (visibility_mode_value_) (1.0) ) ) ) "> : " ) ) ) (visibility_mode_value_) ) )
      (cond 
        ;; _case_1
        ((= visibility_mode_value_ 1)
         (progn 
           (if (= (setq ssA (ssget "i" )) nil) 
             (setq ssA (ssget ))
           )
           (sslength ssA)
           (princ "_case_1")
         )
        )

        ;; _case_2
        ((= visibility_mode_value_ 2)
         (progn 
           (if (= (setq ssB (ssget "i" )) nil) 
             (setq ssB (ssget ))
           )
           (sslength ssB)
           (princ "_case_2")
         )
        )

        ;; _case_3
        ((= visibility_mode_value_ 3)
         (progn 
           (if (= (setq ssC (ssget "i" )) nil) 
             (setq ssC (ssget ))
           )
           (sslength ssC)
           (princ "_case_3")
         )
        )

        ;; _case_4
        ((= visibility_mode_value_ 4)
         (progn 
           (if (= (setq ssD (ssget "i" )) nil) 
             (setq ssD (ssget ))
           )
           (sslength ssD)
           (princ "_case_4")
         )
        )

        ;; _case_5
        ((= visibility_mode_value_ 5)
         (progn 
           (if (= (setq ssE (ssget "i" )) nil) 
             (setq ssE (ssget ))
           )
           (sslength ssE)
           (princ "_case_5")
         )
        )

        ;; _case_6
        ((= visibility_mode_value_ 6)
         (progn 
           (if (= (setq ssF (ssget "i" )) nil) 
             (setq ssF (ssget ))
           )
           (sslength ssF)
           (princ "_case_6")
         )
        )

        ;; _case_7
        ((= visibility_mode_value_ 7)
         (progn 
           (if (= (setq ssG (ssget "i" )) nil) 
             (setq ssG (ssget ))
           )
           (sslength ssG)
           (princ "_case_7")
         )
        )

        ;; _case_8
        ((= visibility_mode_value_ 8)
         (progn 
           (if (= (setq ssH (ssget "i" )) nil) 
             (setq ssH (ssget ))
           )
           (sslength ssH)
           (princ "_case_8")
         )
        )

        ;; _case_9
        ((= visibility_mode_value_ 9)
         (progn 
           (if (= (setq ssI (ssget "i" )) nil) 
             (setq ssI (ssget ))
           )
           (sslength ssI)
           (princ "_case_9")
         )
        )

        ;; _case_10
        ((= visibility_mode_value_ 10)
         (progn 
           (if (= (setq ssJ (ssget "i" )) nil) 
             (setq ssJ (ssget ))
           )
           (sslength ssJ)
           (princ "_case_10")
         )
        )
      )
    ) 
    (defun c:load_selection_loadss_ ()
      ;selection_set_for_fillter_blk_name
        (if  ;pre_select_ssget_or_post_select_ssget
          (=
            (setq old_set_ (ssget "i"
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (princ "no pre object in old selection set")
          )
        )
      ;
      (setq a "a = slot 1"
            b "b = slot 2"
            c "c = slot 3"
            d "d = slot 4"
            e "e = slot 5"
            f "f = slot 6"
            g "g = slot 7"
            h "h = slot 8"
            i "i = slot 9"
            j "j = slot 10"
      )
      (setq ss_list_ (list ssA ssB ssC ssD ssE ssF ssH ssI ssJ))
      ;preloop_and_while
        (setq ss_list_i 0)
        (while (< ss_list_i (length ss_list_))
          (setq ss_list_val_ (nth 0 ss_list_))
          (cond
            (;_case_1
              (and
                  (= ss_list_i 0)
                  (/= ssA nil)
              )
              (progn
                (setq a "a = slot 1 (full)")
                (princ "_case_1")
              )
            )
            (;_case_2
              (and
                  (= ss_list_i 1)
                  (/= ssB nil)
              )
              (progn
                (setq b "b = slot 2 (full)")
                (princ "_case_2")
              )
            )
            (;_case_3
              (and
                  (= ss_list_i 2)
                  (/= ssC nil)
              )
              (progn
                (setq c "c = slot 3 (full)")
                (princ "_case_3")
              )
            )
            (;_case_4
              (and
                  (= ss_list_i 3)
                  (/= ssD nil)
              )
              (progn
                (setq d "d = slot 4 (full)")
                (princ "_case_4")
              )
            )
            (;_case_5
              (and
                  (= ss_list_i 4)
                  (/= ssE nil)
              )
              (progn
                (setq e "e = slot 5 (full)")
                (princ "_case_5")
              )
            )
            (;_case_6
              (and
                  (= ss_list_i 5)
                  (/= ssF nil)
              )
              (progn
                (setq f "f = slot 6 (full)")
                (princ "_case_6")
              )
            )
            (;_case_7
              (and
                  (= ss_list_i 6)
                  (/= ssG nil)
              )
              (progn
                (setq g "g = slot 7 (full)")
                (princ "_case_7")
              )
            )
            (;_case_8
              (and
                  (= ss_list_i 7)
                  (/= ssH nil)
              )
              (progn
                (setq h "h = slot 8 (full)")
                (princ "_case_8")
              )
            )
            (;_case_9
              (and
                  (= ss_list_i 8)
                  (/= ssI nil)
              )
              (progn
                (setq i "i = slot 9 (full)")
                (princ "_case_9")
              )
            )
            (;_case_10
              (and
                  (= ss_list_i 9)
                  (/= ssJ nil)
              )
              (progn
                (setq j "j= slot 10 (full)")
                (princ "_case_10")
              )
            )
          )
      
          (setq ss_list_i (+ ss_list_i 1))
        )
      ;
      (setq visibility_mode_value_ (cond ((getint (strcat a"\n"b"\n"c"\n"d"\n" e"\n" f"\n" g"\n" h"\n" i"\n" j"\n" "<" (rtos (setq visibility_mode_value_ (cond (visibility_mode_value_) (1.0) ) ) ) "> : " ) ) ) (visibility_mode_value_) ) )
      (setq new_set_ (ssadd))

      (cond 
        ;; _case_1
        ((= visibility_mode_value_ 1)
        (progn 
          (command "pselect"  ssA "" )
          (setq new_set_ ssA )
          (princ "_case_1")
        )
        )

        ;; _case_2
        ((= visibility_mode_value_ 2)
        (progn 
          (command "pselect"  ssB "" )
          (setq new_set_ ssB )
          (princ "_case_2")
        )
        )

        ;; _case_3
        ((= visibility_mode_value_ 3)
        (progn 
          (command "pselect"  ssC "" )
          (setq new_set_ ssC )
          (princ "_case_3")
        )
        )

        ;; _case_4
        ((= visibility_mode_value_ 4)
        (progn 
          (command "pselect"  ssD "" )
          (setq new_set_ ssD )
          (princ "_case_4")
        )
        )

        ;; _case_5
        ((= visibility_mode_value_ 5)
        (progn 
          (command "pselect"  ssE "" )
          (setq new_set_ ssE )
          (princ "_case_5")
        )
        )

        ;; _case_6
        ((= visibility_mode_value_ 6)
        (progn 
          (command "pselect"  ssF "" )
          (setq new_set_ ssF )
          (princ "_case_6")
        )
        )

        ;; _case_7
        ((= visibility_mode_value_ 7)
        (progn 
          (command "pselect"  ssG "" )
          (setq new_set_ ssG )
          (princ "_case_7")
        )
        )

        ;; _case_8
        ((= visibility_mode_value_ 8)
        (progn 
          (command "pselect"  ssH "" )
          (setq new_set_ ssH )
          (princ "_case_8")
        )
        )

        ;; _case_9
        ((= visibility_mode_value_ 9)
        (progn 
          (command "pselect"  ssI "" )
          (setq new_set_ ssI )
          (princ "_case_9")
        )
        )

        ;; _case_10
        ((= visibility_mode_value_ 10)
        (progn 
          (command "pselect"  ssJ "" )
          (setq new_set_ ssj )
          (princ "_case_10")
        )
        )
      )


      (if (/= old_set_ nil)
        (progn
          (setq sss (TA:combine_selection_set_ new_set_ old_set_))
          (command "pselect"   sss "" )
        )
        (command "pselect"  new_set_ "" )
      )
    ) 
    (defun c:add_selection_addss_
      (
        /
        slot_symbol_list_
        slot_number_
        target_symbol_
        old_ss_
        add_ss_
        combine_ss_
        slot_i_
        message_
      )

      ;; เก็บวัตถุที่เลือกไว้ก่อนเรียกคำสั่ง
      (setq add_ss_ (ssget "_I"))
      (setq slot_symbol_list_ '(ssA ssB ssC ssD ssE ssF ssG ssH ssI ssJ))

      ;; TA:last_ss_slot_ เป็นตัวแปร Global สำหรับจำ Slot ล่าสุด
      (if
        (not
          (and
            (eq (type TA:last_ss_slot_) 'INT)
            (<= 1 TA:last_ss_slot_ 10)
          )
        )
        (setq TA:last_ss_slot_ 1)
      )

      ;; แสดงสถานะ Slot
      (setq slot_i_ 0)
      (setq message_ "")

      (while (< slot_i_ (length slot_symbol_list_))
        (setq target_symbol_ (nth slot_i_ slot_symbol_list_))

        (setq message_
          (strcat
            message_
            "\n"
            (itoa (1+ slot_i_))
            " = Slot "
            (itoa (1+ slot_i_))
            " "
            (if
              (and
                (boundp target_symbol_)
                (eq (type (eval target_symbol_)) 'PICKSET)
                (> (sslength (eval target_symbol_)) 0)
              )
              "(full)"
              "(empty)"
            )
          )
        )

        (setq slot_i_ (1+ slot_i_))
      )

      (prompt message_)

      ;; กด Enter เพื่อใช้ Slot ล่าสุด
      (initget 6)
      (setq slot_number_ (cond ((getint (strcat "\nSpecify Slot [1-10] <" (itoa TA:last_ss_slot_) ">: "))) (TA:last_ss_slot_)))

      (if
        (<= slot_number_ 10)
        (progn
          (setq TA:last_ss_slot_ slot_number_)
          (setq target_symbol_ (nth (1- slot_number_) slot_symbol_list_))

          (setq old_ss_
            (if
              (and
                (boundp target_symbol_)
                (eq (type (eval target_symbol_)) 'PICKSET)
              )
              (eval target_symbol_)
              nil
            )
          )

          (if (not add_ss_)
            (progn
              (prompt "\nSelect objects to add to Slot: ")
              (setq add_ss_ (ssget))
            )
          )

          (if add_ss_
            (progn
              (setq combine_ss_ (ssadd))

              ;; คัดลอกวัตถุเดิม
              (if old_ss_
                (progn
                  (setq slot_i_ 0)

                  (while (< slot_i_ (sslength old_ss_))
                    (ssadd (ssname old_ss_ slot_i_) combine_ss_)
                    (setq slot_i_ (1+ slot_i_))
                  )
                )
              )

              ;; เพิ่มวัตถุที่เลือก
              (setq slot_i_ 0)

              (while (< slot_i_ (sslength add_ss_))
                (ssadd (ssname add_ss_ slot_i_) combine_ss_)
                (setq slot_i_ (1+ slot_i_))
              )

              (set target_symbol_ combine_ss_)
              (sssetfirst nil combine_ss_)

              (prompt
                (strcat
                  "\nSlot "
                  (itoa slot_number_)
                  " now contains "
                  (itoa (sslength combine_ss_))
                  " object(s)."
                )
              )
            )

            (prompt "\nNo objects selected. Slot was not changed.")
          )
        )

        (prompt "\nSlot must be between 1 and 10.")
      )

      (princ)
    )


    (defun c:DELSS
      (
        /
        slot_symbol_list_
        slot_number_
        target_symbol_
        old_ss_
        remove_ss_
        result_ss_
        slot_i_
        ename_
        removed_
      )

      ;; เก็บวัตถุที่เลือกไว้ก่อนเรียกคำสั่ง
      (setq remove_ss_ (ssget "_I"))
      (setq slot_symbol_list_ '(ssA ssB ssC ssD ssE ssF ssG ssH ssI ssJ))

      ;; ใช้ค่า Slot ล่าสุดร่วมกับ ADDSS
      (if
        (not
          (and
            (eq (type TA:last_ss_slot_) 'INT)
            (<= 1 TA:last_ss_slot_ 10)
          )
        )
        (setq TA:last_ss_slot_ 1)
      )

      ;; กด Enter เพื่อใช้ Slot ล่าสุด
      (initget 6)
      (setq slot_number_ (cond ((getint (strcat "\nSpecify Slot [1-10] <" (itoa TA:last_ss_slot_) ">: "))) (TA:last_ss_slot_)))

      (if
        (<= slot_number_ 10)
        (progn
          (setq TA:last_ss_slot_ slot_number_)
          (setq target_symbol_ (nth (1- slot_number_) slot_symbol_list_))

          (setq old_ss_
            (if
              (and
                (boundp target_symbol_)
                (eq (type (eval target_symbol_)) 'PICKSET)
              )
              (eval target_symbol_)
              nil
            )
          )

          (if
            (or
              (not old_ss_)
              (= (sslength old_ss_) 0)
            )
            (prompt (strcat "\nSlot " (itoa slot_number_) " is empty."))

            (progn
              (if (not remove_ss_)
                (progn
                  (prompt "\nSelect objects to remove from Slot: ")
                  (setq remove_ss_ (ssget))
                )
              )

              (if remove_ss_
                (progn
                  ;; คัดลอกชุดเดิมก่อนลบ เพื่อไม่กระทบ Slot อื่น
                  (setq result_ss_ (ssadd))
                  (setq slot_i_ 0)

                  (while (< slot_i_ (sslength old_ss_))
                    (ssadd (ssname old_ss_ slot_i_) result_ss_)
                    (setq slot_i_ (1+ slot_i_))
                  )

                  (setq slot_i_ 0)
                  (setq removed_ 0)

                  (while (< slot_i_ (sslength remove_ss_))
                    (setq ename_ (ssname remove_ss_ slot_i_))

                    (if (ssmemb ename_ result_ss_)
                      (progn
                        (ssdel ename_ result_ss_)
                        (setq removed_ (1+ removed_))
                      )
                    )

                    (setq slot_i_ (1+ slot_i_))
                  )

                  (if (= (sslength result_ss_) 0)
                    (setq result_ss_ nil)
                  )

                  (set target_symbol_ result_ss_)
                  (sssetfirst nil result_ss_)

                  (prompt
                    (strcat
                      "\nRemoved "
                      (itoa removed_)
                      " object(s) from Slot "
                      (itoa slot_number_)
                      "."
                    )
                  )
                )

                (prompt "\nNo objects selected. Slot was not changed.")
              )
            )
          )
        )

        (prompt "\nSlot must be between 1 and 10.")
      )

      (princ)
    )
  ;
  ;DESELECTION_FUNC
    (defun c:desel ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq ss-new-new (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (if (/= (LM:effectivename ss_pre_filter_set_xx_obj_) "010 - ASPG_FLASING")
            (progn
              (setq ss-new-new (ssadd ss_pre_filter_set_xx_ename_ ss-new-new))
            )
          )
          (setq ss_pre_filter_set_xx_i (+ ss_pre_filter_set_xx_i 1))
        )
      ;
      (command "pselect"  ss-new-new "" )
    )
  ; 
  ;test_command
    (defun TA:dump_obj_ (dump_ename_ )
      ; (setq dump_ename_ (car (entsel "specify Object")))
      (setq dump_obj_ (vlax-ename->vla-object dump_ename_))
      (vlax-dump-object (vlax-ename->vla-object dump_ename_))
    )
    (defun C:Dumpit ( / ent) 
      (while (setq ent (entsel)) 
        (vlax-Dump-Object 
          (vlax-Ename->Vla-Object (car ent)) 
        ) 
      ) 
      (princ) 
    )
    (defun c:t1_ins_vla-getboundingbox ()
      (setq ss (vlax-ename->vla-object (car (entsel))) )
      (vla-getboundingbox ss 'ins_min 'ins_max)
                  (setq ins_min (vlax-safearray->list ins_min))
                  (setq ins_max (vlax-safearray->list ins_max))

      (command "point" ins_min)
      (command "point" ins_max)
    )
    (defun c:t2_find_objname ()
      (setq obj_name_ (vla-get-objectname (vlax-ename->vla-object (car (entsel)))))
    )
  ;
  ;ALuminium Tube FUNC
    (defun c:insert_ALTUBE_insAL ()
      ;Note By Code_Developer
      ;This command is designed to work exclusively with a block named '001 - DYNAMIC REC&SSQ SHAPE SOLID_midpoint'.
      ;principle of codework is design to work woth line object only by referce start-end point of the line is basepoint for first insertion Block object
      ;After insertion block complete, main code will keep Ename data by "enlast" method and use Lee Mac dynamic block for strech object 
      ;Fully command must have sub-functions with names starting with TA: or LM:
      ;
      ;
      ;user_input_dynammic_
        (setq user_input_width_ (cond ( (getint (strcat "\nspecify fllet_rec_<" (rtos (setq user_input_width_ (cond (user_input_width_) (1.0) ) ) ) "> : " ) ) ) (user_input_width_) ) )
      ;
      ;selection_set_for_fillter_blk_name
        (if  ;pre_select_ssget_or_post_select_ssget
          (=
            (setq ss_pre_filter_set_xx_ (ssget "i"
                                              (list
                                                (cons 0 "line") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget 
                                              (list
                                                (cons 0 "line") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;while_select_block_on_condition_
          (setq blk_ename_ nil)
          (while (= blk_ename_ nil)
            (setq blk_ename_ (car (entsel "specify blk_ename Object")))
            (if
              (and ;conditional_rule_for_select_object
                (/= blk_ename_ nil)
                (setq blk_ename_obj_ (vlax-ename->vla-object blk_ename_))
                (= (vla-get-objectname blk_ename_obj_ ) "AcDbBlockReference")
                (= (vla-get-isdynamicblock blk_ename_obj_ ) :vlax-true)
                
              )
              (progn
                (setq blk_ename_efname_ (LM:effectivename blk_ename_obj_ ) )
              )
              (alert "Object invalid Please try again")
            )
          )
      ;
      ;preloop_and_while
        (setq ss_pre_filter_set_xx_i 0)
        (while (< ss_pre_filter_set_xx_i (sslength ss_pre_filter_set_xx_))
          ;get_line_data
            (setq ss_pre_filter_set_xx_ename_ (ssname ss_pre_filter_set_xx_ ss_pre_filter_set_xx_i))
            (setq ss_pre_filter_set_xx_hon_obj_ (vlax-ename->vla-object ss_pre_filter_set_xx_ename_))
            (setq ss_pre_filter_set_xx_hon_obj_start_end_pt_ (list
                                            (setq ss_pre_filter_set_xx_hon_obj_startpt_ (vlax-safearray->list
                                                                      (vlax-variant-value ( vla-get-startpoint ss_pre_filter_set_xx_hon_obj_ ))
                                                                    )
                                            )
                                            (setq ss_pre_filter_set_xx_hon_obj_endpt_ (vlax-safearray->list
                                                                      (vlax-variant-value ( vla-get-endpoint ss_pre_filter_set_xx_hon_obj_ ))
                                                                  )
                                            )
                                          )
            )
            (setq ss_pre_filter_set_xx_hon_obj_length (atoi (rtos (vla-get-length ss_pre_filter_set_xx_hon_obj_) 2 0)))
          
          ;
          ;insertion_new_object
            (command "insert" blk_ename_efname_ ss_pre_filter_set_xx_hon_obj_startpt_ 1 0)
            (LM:setdynpropvalue (vlax-ename->vla-object (entlast)) "H" ss_pre_filter_set_xx_hon_obj_length )
            (LM:setdynpropvalue (vlax-ename->vla-object (entlast)) "W" user_input_width_ )

          ;
          (setq ss_pre_filter_set_xx_i (+ ss_pre_filter_set_xx_i 1))
        )
      ;
    )

  ;
  ;Excel_sub_func
    ;get-object-Excel
    (defun TA:New_Excel_File_NEX_ (new_vla-obj_app )
      (if (= new_vla-obj_app nil)
        (progn
          (setq new_vla-obj_app (vlax-get-or-create-object "Excel.Application"))
          
        )
      )
      (if (/= new_vla-obj_app nil)
        (progn
          (setq new_vla-obj_app (vlax-get-or-create-object "Excel.Application"))
          ; (setq new_vla-obj_app (vlax-create-object "Excel.Application"))
          (setq new_Workbooks_ (vlax-get-property new_vla-obj_app 'Workbooks))
          (setq new_workbook_ (vlax-invoke-method new_Workbooks_ 'Add))
          (setq Vla_workbook_list_ (TA:Excel_Assembly_ALL-obj_list_ new_Workbooks_ ))
          (vlax-put-property new_vla-obj_app 'Visible :vlax-true)
          (setq Vla_workbook_list_ Vla_workbook_list_)
        )
      )
      ;princ main object
        (setq new_Workbooks_ new_Workbooks_)
      ;
    )
    (defun TA:Excel_Assembly_ALL-obj_list_ (books_obj_)
      ;Note By Code_Developer
      ;pripicle of code for get total _worksheet sequnce name vla-obj _sheet by sorting via sequnce  
      ;
      ;books_obj_ = #<VLA-OBJECT Sheets >
      ;preloop_and_while
        (if 
          (or
            (wcmatch (strcase (vl-prin1-to-string books_obj_)) "*<VLA-OBJECT WORKBOOKS*")
            ; (wcmatch (strcase (vl-prin1-to-string books_obj_)) "*SHEETS*")
          )
          (progn
            (setq _workbook_Vla-obj_list_ ())
            (setq _worksheet_vla-obj_name_list_ ())
            
            (setq books_obj_length (vlax-get-property books_obj_ 'count )) ;total file open in 1 app
            (setq books_obj_i 1)
            (while (<= books_obj_i books_obj_length)
              (setq _workbook_obj_ (vlax-get-property books_obj_ 'item books_obj_i))
                (setq _sheets_obj_ (vlax-get-property _workbook_obj_ 'sheets))
                  ;preloop_and_while
                    (setq _sheets_obj_length (vlax-get-property _sheets_obj_ 'count))
                    (setq _sheets_obj_i 1 )
                    (setq _worksheet_vla-obj_name_list_ ())
                      (while (<= _sheets_obj_i _sheets_obj_length)
                        (setq _worksheet_obj_ (vlax-get-property _sheets_obj_ 'item _sheets_obj_i))
                          (setq _worksheet_obj_name (vlax-get-property _worksheet_obj_ 'name))
                          (setq _worksheet_vla-obj_name_list_sum (list _sheets_obj_i _worksheet_obj_name _worksheet_obj_))
                        (setq _worksheet_vla-obj_name_list_ (cons _worksheet_vla-obj_name_list_sum _worksheet_vla-obj_name_list_))
                        (setq _sheets_obj_i (+ _sheets_obj_i 1))
                        ; (setq _worksheet_vla-obj_name_list_ (reverse _worksheet_vla-obj_name_list_))
                        (setq _worksheet_vla-obj_name_list_ (vl-sort _worksheet_vla-obj_name_list_  ;bigest open indent list
                                                        (function 
                                                          (lambda (a b) 
                                                            (< (nth 0 a) (nth 0 b))
                                                          )
                                                        )
                                                ) ;bigest close indent list
                        )
                      )
                    ;
              (setq _workbook_obj_name (vlax-get-property _workbook_obj_ 'name))
              (setq _worksheet_Vla-obj_list_sum_ (list books_obj_i _workbook_obj_name _workbook_obj_ _worksheet_vla-obj_name_list_))
              
              (setq _workbook_Vla-obj_list_ (cons _worksheet_Vla-obj_list_sum_ _workbook_Vla-obj_list_))
              (setq books_obj_i (+ books_obj_i 1))
            )
            ; (setq _workbook_Vla-obj_list_ (reverse _workbook_Vla-obj_list_ ))
            (setq _workbook_Vla-obj_list_ (vl-sort _workbook_Vla-obj_list_  ;bigest open indent list
                                            (function 
                                              (lambda (a b) 
                                                (< (nth 0 a) (nth 0 b))
                                              )
                                            )
                                    ) ;bigest close indent list
            )
            (append (list books_obj_) _workbook_Vla-obj_list_)
          )
        )
      ;preloop
    )
    (defun TA:Excel_Assembly_worksheet_obj_list_ (sheets_obj_)
      ;Note By Code_Developer
      ;pripicle of code for get total _worksheet sequnce name vla-obj _sheet by sorting via sequnce  
      ;
      ;sheets_obj_ = #<VLA-OBJECT Sheets >
      ;preloop_and_while
        (if 
          (or
            (wcmatch (strcase (vl-prin1-to-string sheets_obj_)) "*WORKBOOKS*")
            (wcmatch (strcase (vl-prin1-to-string sheets_obj_)) "*SHEETS*")
          )
          (progn
            (setq _worksheet_Vla-obj_list_ ())
            (setq sheets_obj_length (vlax-get-property sheets_obj_ 'count ))
            (setq sheets_obj_i 1)
            (while (<= sheets_obj_i sheets_obj_length)
              (setq _worksheet_obj_ (vlax-get-property sheets_obj_ 'item sheets_obj_i))
                (setq _worksheet_obj_name (vlax-get-property _worksheet_obj_ 'name))
                (setq _worksheet_Vla-obj_sum_ (list sheets_obj_i _worksheet_obj_name _worksheet_obj_ ))
              (setq _worksheet_Vla-obj_list_ (cons _worksheet_Vla-obj_sum_ _worksheet_Vla-obj_list_))
              (setq sheets_obj_i (+ sheets_obj_i 1))
            )
            (setq _worksheet_Vla-obj_list_ (reverse _worksheet_Vla-obj_list_ ))
          )
        )
      ;preloop
    )
    (defun Excel:VLA-OBJECT-Workbook->VLA-OBJECT-Sheets  (VLA-OBJECT_Workbook)
      (if 
        (wcmatch 
          (strcase (vl-princ-to-string VLA-OBJECT_Workbook))
          (strcase "*<VLA-OBJECT _Workbook*")
        )
        (progn
          (setq VLA-OBJECT-Sheets (vlax-get-property VLA-OBJECT_Workbook 'sheets))
        )
        (princ "argument invalid")
      )
    )
    (defun Excel:VLA-OBJECT-Sheets->VLA-OBJECT-Worksheet  (VLA-OBJECT-Sheets i)
      (if 
        (and
          (wcmatch 
            (strcase (vl-princ-to-string VLA-OBJECT-Sheets))
            (strcase "*<VLA-OBJECT SHEETS*")
          )
          (numberp i )
          (<= i (vlax-get-property VLA-OBJECT-Sheets 'count))
        )
        (progn
          (vlax-get-property VLA-OBJECT-Sheets 'item i)
        )
        (princ "argument invalid")
      )
    )
    (defun TA:EXCEL_put_all_rowheight (VLA-OBJECT-Worksheet rowheight_value_ )
      (vlax-put-property (vlax-get VLA-OBJECT-Worksheet 'Cells) 'rowheight rowheight_value_)
    )
    (defun TA:EXCEL_put_all_columnwidth (VLA-OBJECT-Worksheet columnwidth_value_ )
      (vlax-put-property (vlax-get VLA-OBJECT-Worksheet 'Cells) 'columnwidth columnwidth_value_)
    )
    (defun TA:EXCEL_put_columnhide (VLA-OBJECT-Worksheet column_number columnhide_value_ )
      (setq vla-object-cols_ (vlax-get-property VLA-OBJECT-Worksheet 'Columns))
        (setq vla-object-col_(vlax-get-property (vlax-variant-value (vlax-get-property vla-object-cols_ 'Item column_number)) 'EntireColumn))
          (vlax-put-property vla-object-col_ 'Hidden  columnhide_value_)
    )
    (defun TA:EXCEL_put_rowhide (VLA-OBJECT-Worksheet row_number rowhide_value_ )
      (setq vla-object-rows_ (vlax-get-property VLA-OBJECT-Worksheet 'rows))
        (setq vla-object-row_(vlax-get-property (vlax-variant-value (vlax-get-property vla-object-rows_ 'Item row_number)) 'Entirerow))
          (vlax-put-property vla-object-row_ 'Hidden rowhide_value_)
    )
    (defun TA:EXCEL_put_columnwidth (VLA-OBJECT-Worksheet column_number columnwidth_value_ )
      (setq vla-object-cols_ (vlax-get-property VLA-OBJECT-Worksheet 'Columns))
        (setq vla-object-col_(vlax-get-property (vlax-variant-value (vlax-get-property vla-object-cols_ 'Item column_number)) 'EntireColumn))
          (vlax-put-property vla-object-col_ 'ColumnWidth columnwidth_value_)
    )
    (defun TA:EXCEL_put_rowheight (VLA-OBJECT-Worksheet row_number rowheight_value_ )
      (setq vla-object-rows_ (vlax-get-property VLA-OBJECT-Worksheet 'rows))
        (setq vla-object-row_(vlax-get-property (vlax-variant-value (vlax-get-property vla-object-rows_ 'Item row_number)) 'Entirerow))
          (vlax-put-property vla-object-row_ 'rowheight rowheight_value_)
    )
    (defun TA:EXCEL_put_columnwidth_viatext  (Rangecell_row_ Rangecell_column_ Rangecell_target_row_ text_width_val)
      ;Note By Code_Developer
      ;pripicle of code for put columnwidth from string len or number len in rangecell in Excel App by While-loop method 1st-row to target-row (target-row specify by argument)
      ;
      ;Exce_sub_FUNC_list_
        ;TA:EXCEL_put_columnwidth 
      ;
      ;argument
        ;_worksheet_obj_        = <VLA-OBJECT _Worksheet >   
        ;Rangecell_row_         = "1st-Row cell in Excel App"
        ;Rangecell_target_row_  = "lowset-Row cell in Excel App"
        ;Rangecell_column_      = "Column cell in Excel App"
        ;text_width_val         = text_len per width_
      ;
      ;example_argument_
        ; (setq Rangecell_row_ 1)
        ; (setq Rangecell_column_ 2)
        
        ; (setq Rangecell_target_row_ 2) 
      
      ;preloop_and_while
        (setq rangecell_colwidth_list_ ())
        (while
          (< Rangecell_row_ (+ Rangecell_target_row_ 1))
          (setq rangecell_value_ (TA:Excel_get_data_R1C1 _worksheet_obj_ Rangecell_row_ Rangecell_column_ ))
          (if (numberp rangecell_value_)
            (progn 
              (setq col_width_ (* (strlen (rtos rangecell_value_ 2 8)) text_width_val ) )
            )
            (setq col_width_ (* (if (/= rangecell_value_ nil) (progn (strlen rangecell_value_)) 0 ) text_width_val) )
          )
          (setq rangecell_colwidth_list_ (cons col_width_ rangecell_colwidth_list_ ))
          
          
          (setq Rangecell_row_ (+ Rangecell_row_ 1))
        )
      ;
      (TA:EXCEL_put_columnwidth _worksheet_obj_ Rangecell_column_ (setq rangecell_col-max-width_ (car (vl-sort rangecell_colwidth_list_ '>))))
    )
    (defun TA:Excel_Clearcontents (VLA-OBJECT-Worksheet  )
      (setq VLA-OBJECT-Range (vlax-get-property VLA-OBJECT-Worksheet 'Cells  ) )
      (vlax-invoke-method VLA-OBJECT-Range 'ClearContents)
    )
    (defun TA:Excel_get_data_Rangecell (_worksheet_obj_ Rangecell_name_)
      ;Note By Code_Developer
      ;pripicle of code for get data from rangecell in Excel App by specify <VLA-OBJECT _Worksheet
      ;
      ;argument
        ;_worksheet_obj_ = <VLA-OBJECT _Worksheet >
        ;Rangecell_name_ = "Rangecell name in Excel App"
      ;
      ;Example 
        ;(vlax-get (vlax-get-property _worksheet_obj_ 'Range "AA1") "value2")  ;get_value_from_range_cell
      ;
      (vlax-get (vlax-get-property _worksheet_obj_ 'Range Rangecell_name_) "value2")
    )
    (defun TA:Excel_put_data_Rangecell (_worksheet_obj_ Rangecell_name_ Rangecell_value_)
      ;Note By Code_Developer
      ;pripicle of code for get data from rangecell in Excel App by specify <VLA-OBJECT _Worksheet
      ;
      ;argument
        ;_worksheet_obj_  = <VLA-OBJECT _Worksheet >
        ;Rangecell_name_  = "Rangecell name in Excel App"
        ;Rangecell_value_ = "Rangecell Value in Excel App"
      ;
      ;Example 
        ;(vlax-put (vlax-get-property _worksheet_obj_ 'Range "AA1") 'Value "XXX") ;put_value_from_range_cell
      ;
      (vlax-put (vlax-get-property _worksheet_obj_ 'Range Rangecell_name_ ) 'Value Rangecell_value_)
    )
    (defun TA:Excel_get_data_R1C1 (_worksheet_obj_  Rangecell_row_ Rangecell_column_)
      ;Note By Code_Developer
      ;pripicle of code for get data from rangecell in Excel App by specify <VLA-OBJECT _Worksheet
      ;
      ;argument
        ;_worksheet_obj_  = <VLA-OBJECT _Worksheet >
        ;Rangecell_row_  = "Row cell in Excel App"
        ;Rangecell_column_  = "Column cell in Excel App"
        ;Rangecell_value_ = "get Rangecell Value in Excel App"
      ;
      ;Example 
        ; (vlax-get (vlax-variant-value (vlax-get-property (vlax-get _worksheet_obj_ 'Cells) 'Item 1 27)) 'Value) ;get_value_from_range_cell
      ;
      (if 
        (and 
          (= (wcmatch (vlax-get (vlax-variant-value (vlax-get-property (vlax-get _worksheet_obj_ 'Cells) 'Item Rangecell_row_ Rangecell_column_)) 'NumberFormat ) "*d-mm-yy*") T)
        )
        (progn
          (vlax-get (vlax-variant-value (vlax-get-property (vlax-get _worksheet_obj_ 'Cells) 'Item Rangecell_row_ Rangecell_column_)) 'text)
        )
        (vlax-get (vlax-variant-value (vlax-get-property (vlax-get _worksheet_obj_ 'Cells) 'Item Rangecell_row_ Rangecell_column_)) 'Value) ;get_value_from_range_cell
      )
      
    )
    (defun TA:Excel_input_data_R1C1 (_worksheet_obj_ Rangecell_row_ Rangecell_column_ Rangecell_value_ )
      ;Note By Code_Developer
      ;pripicle of code for get data from rangecell in Excel App by specify <VLA-OBJECT _Worksheet
      ;
      ;argument
        ;_worksheet_obj_  = <VLA-OBJECT _Worksheet >
        ;Rangecell_row_  = "Row cell in Excel App"
        ;Rangecell_column_  = "Column cell in Excel App"
        ;Rangecell_value_ = "put Rangecell Value in Excel App"
        ;
      ;
      ;Example 
        ; (vlax-put (vlax-variant-value (vlax-get-property (vlax-get _worksheet_obj_ 'Cells) 'Item 1 27)) 'Value "TESTTESTTESTTEST") ;put_value_from_range_cell
        ;(vlax-dump-object (vlax-get _worksheet_obj_ 'Cells))
        ;(vlax-put-property (vlax-get _worksheet_obj_ 'Cells) 'rowheight 22)
      ;
      (vlax-put (vlax-variant-value (vlax-get-property (vlax-get _worksheet_obj_ 'Cells) 'Item Rangecell_row_ Rangecell_column_)) 'Value Rangecell_value_) ;p
    )
    (defun TA:Excel_get_font-size_R1C1 (_worksheet_obj_ Rangecell_row_ Rangecell_column_)
      ;Note By Code_Developer
      ;pripicle of code for get font-size from rangecell in Excel App by specify <VLA-OBJECT _Worksheet
      ;argument
        ;_worksheet_obj_  = <VLA-OBJECT _Worksheet >
        ;Rangecell_row_  = "Row cell in Excel App"
        ;Rangecell_column_  = "Column cell in Excel App"
      ;
      ;example_for_testing_
        ; (setq Rangecell_row_ 1)
        ; (setq Rangecell_column_ 1)
      ;
      ;main_idea
        (vlax-get
          (vlax-get 
            (vlax-variant-value 
              (vlax-get-property (vlax-get _worksheet_obj_ 'Cells) 'Item Rangecell_row_ Rangecell_column_ )
            )
            'font
          )
          'size
        )
      ;
    ) 
    (defun TA:Excel_put_font-size_R1C1 (_worksheet_obj_ Rangecell_row_ Rangecell_column_ font-size_value)
      ;Note By Code_Developer
      ;pripicle of code for put font-size from rangecell in Excel App by specify <VLA-OBJECT _Worksheet
      ;argument
        ;_worksheet_obj_  = <VLA-OBJECT _Worksheet >
        ;Rangecell_row_  = "Row cell in Excel App"
        ;Rangecell_column_  = "Column cell in Excel App"
        ;font-size_value = integer for incase or decase size 
      ;
      ;example_for_testing_
        ; (setq Rangecell_row_ 1)
        ; (setq Rangecell_column_ 1)
        ; (vlax-dump-object (vlax-get (vlax-variant-value (vlax-get-property (vlax-get _worksheet_obj_ 'Cells) 'Item Rangecell_row_ Rangecell_column_ ) ) 'font ))
      ;
      ;main_idea
        (vlax-put
          (vlax-get 
            (vlax-variant-value 
              (vlax-get-property (vlax-get _worksheet_obj_ 'Cells) 'Item Rangecell_row_ Rangecell_column_ )
            )
            'font
          )
          'size
          font-size_value
        )
      ;
    ) 
    (defun TA:Excel_get_font-VerticalAlignment_R1C1 (_worksheet_obj_ Rangecell_row_ Rangecell_column_)
      ;Note By Code_Developer
      ;pripicle of code for get font-size from rangecell in Excel App by specify <VLA-OBJECT _Worksheet
      ;argument
        ;_worksheet_obj_  = <VLA-OBJECT _Worksheet >
        ;Rangecell_row_  = "Row cell in Excel App"
        ;Rangecell_column_  = "Column cell in Excel App"
      ;
      ;example_for_testing_
        ; (setq Rangecell_row_ 1)
        ; (setq Rangecell_column_ 1)
      ;
      ;main_idea
        (cond
          (;Top Align
            (= 
              (vlax-get 
                (vlax-variant-value 
                  (vlax-get-property (vlax-get _worksheet_obj_ 'Cells) 'Item Rangecell_row_ Rangecell_column_ )
                )
                'VerticalAlignment
              )
              -4160
            )
            (progn
              (setq VerticalAlignment "Top Align")
            )
          )
          (;MIddle Align
            (= 
              (vlax-get 
                (vlax-variant-value 
                  (vlax-get-property (vlax-get _worksheet_obj_ 'Cells) 'Item Rangecell_row_ Rangecell_column_ )
                )
                'VerticalAlignment
              )
              -4108
            )
            (progn
              (setq VerticalAlignment "Middle Align")
            )
          )
          (;Bottom Align
            (= 
              (vlax-get 
                (vlax-variant-value 
                  (vlax-get-property (vlax-get _worksheet_obj_ 'Cells) 'Item Rangecell_row_ Rangecell_column_ )
                )
                'VerticalAlignment
              )
              -4107
            )
            (progn
              (setq VerticalAlignment "Bottom Align")
            )
          )
        )
      ;
    )
    (defun TA:Excel_put_font-VerticalAlignment_R1C1 (_worksheet_obj_ Rangecell_row_ Rangecell_column_ Alignment_value_)
      ;Note By Code_Developer
      ;pripicle of code for get font-size from rangecell in Excel App by specify <VLA-OBJECT _Worksheet
      ;argument
        ;_worksheet_obj_  = <VLA-OBJECT _Worksheet >
        ;Rangecell_row_  = "Row cell in Excel App"
        ;Rangecell_column_  = "Column cell in Excel App"
      ;
      ;example_for_testing_
        ; (setq Rangecell_row_ 1)
        ; (setq Rangecell_column_ 1)
        ; (setq Alignment_value_ "top")
      ;
      ;main_idea
        (if
          (or
            (= (strcase Alignment_value_) "TOP")
            (= (strcase Alignment_value_) "CENTER")
            (= (strcase Alignment_value_) "BOTTOM")
          )
          (progn
            (cond
              (;Top Align
                (and 
                  (= (type  Alignment_value_) 'str)
                  (= (strcase Alignment_value_) "TOP")
                )
                (progn
                  (vlax-put 
                    (vlax-variant-value (vlax-get-property (vlax-get _worksheet_obj_ 'Cells) 'Item Rangecell_row_ Rangecell_column_ ) )
                    'VerticalAlignment
                    -4160
                  )
                )
              )
              (;Middle Align
                (and 
                  (= (type  Alignment_value_) 'str)
                  (= (strcase Alignment_value_) "CENTER")
                )
                (progn
                  (vlax-put 
                    (vlax-variant-value (vlax-get-property (vlax-get _worksheet_obj_ 'Cells) 'Item Rangecell_row_ Rangecell_column_ ) )
                    'VerticalAlignment
                    -4108
                  )
                )
              )
              (;Bottom Align
                (and 
                  (= (type  Alignment_value_) 'str)
                  (= (strcase Alignment_value_) "BOTTOM")
                )
                (progn
                  (vlax-put 
                    (vlax-variant-value (vlax-get-property (vlax-get _worksheet_obj_ 'Cells) 'Item Rangecell_row_ Rangecell_column_ ) )
                    'VerticalAlignment
                    -4107
                  )
                )
              )
            )
          )
          (princ "object value invalid")
        )
      ;
    )
    (defun TA:Excel_get_font-HonlizontalAlignment_R1C1 (_worksheet_obj_ Rangecell_row_ Rangecell_column_ )
      ;Note By Code_Developer
      ;pripicle of code for get font-size from rangecell in Excel App by specify <VLA-OBJECT _Worksheet
      ;argument
        ;_worksheet_obj_  = <VLA-OBJECT _Worksheet >
        ;Rangecell_row_  = "Row cell in Excel App"
        ;Rangecell_column_  = "Column cell in Excel App"
      ;
      ;example_for_testing_
        ; (setq Rangecell_row_ 1)
        ; (setq Rangecell_column_ 1)
        ; (setq Alignment_value_ "top")
      ;
      ;main_idea
        (cond
          (;Left Align
            (and 
              (=
                (vlax-get 
                  (vlax-variant-value 
                    (vlax-get-property (vlax-get _worksheet_obj_ 'Cells) 'Item Rangecell_row_ Rangecell_column_ )
                  )
                  'HorizontalAlignment               
                )
                -4131
              )
            )
            (progn
              (setq Alignment_value_ "Align Left")
            )
          )
          (;Middle Align
            (and 
              (=
                (vlax-get 
                  (vlax-variant-value 
                    (vlax-get-property (vlax-get _worksheet_obj_ 'Cells) 'Item Rangecell_row_ Rangecell_column_ )
                  )
                  'HorizontalAlignment               
                )
                -4108
              )
            )
            (progn
              (setq Alignment_value_ "Align Center")
            )
          )
          (;Bottom Align
            (and 
              (=
                (vlax-get 
                  (vlax-variant-value 
                    (vlax-get-property (vlax-get _worksheet_obj_ 'Cells) 'Item Rangecell_row_ Rangecell_column_ )
                  )
                  'HorizontalAlignment               
                )
                -4152
              )
            )
            (progn
              (setq Alignment_value_ "Align Right")
            )
          )
        )
      ;
    )
    (defun TA:Excel_put_font-HonlizontalAlignment_R1C1 (_worksheet_obj_ Rangecell_row_ Rangecell_column_ Alignment_value_)
      ;Note By Code_Developer
      ;pripicle of code for get font-size from rangecell in Excel App by specify <VLA-OBJECT _Worksheet
      ;argument
        ;_worksheet_obj_  = <VLA-OBJECT _Worksheet >
        ;Rangecell_row_  = "Row cell in Excel App"
        ;Rangecell_column_  = "Column cell in Excel App"
      ;
      ;example_for_testing_
        ; (setq Rangecell_row_ 1)
        ; (setq Rangecell_column_ 1)
        ; (setq Alignment_value_ "top")
      ;
      ;main_idea
        (if
          (or
            (= (strcase Alignment_value_) "LEFT")
            (= (strcase Alignment_value_) "CENTER")
            (= (strcase Alignment_value_) "RIGHT")
          )
          (progn
            (cond
              (;Left Align
                (and 
                  (= (type  Alignment_value_) 'str)
                  (= (strcase Alignment_value_) "LEFT")
                )
                (progn
                  (vlax-put
                    (vlax-variant-value (vlax-get-property (vlax-get _worksheet_obj_ 'Cells) 'Item Rangecell_row_ Rangecell_column_ ) )
                    'HorizontalAlignment 
                    -4131
                  )
                )
              )
              (;Middle Align
                (and 
                  (= (type  Alignment_value_) 'str)
                  (= (strcase Alignment_value_) "CENTER")
                )
                (progn
                  (vlax-put 
                    (vlax-variant-value (vlax-get-property (vlax-get _worksheet_obj_ 'Cells) 'Item Rangecell_row_ Rangecell_column_ ) )
                    'HorizontalAlignment
                    -4108
                  )
                )
              )
              (;Bottom Align
                (and 
                  (= (type  Alignment_value_) 'str)
                  (= (strcase Alignment_value_) "RIGHT")
                )
                (progn
                  (vlax-put 
                    (vlax-variant-value (vlax-get-property (vlax-get _worksheet_obj_ 'Cells) 'Item Rangecell_row_ Rangecell_column_ ) )
                    'HorizontalAlignment
                    -4152
                  )
                )
              )
            )
          )
          (princ "object value invalid")
        )
      ;
    )    
    (defun TA_EXCEL_RangecellName_to_R1C1 (RangeCellName_list_)
      ;preloop_and_while
        (setq RangeCellName_list_i 0)
        (setq r1c1_list_ ())
        (while (< RangeCellName_list_i (length RangeCellName_list_))
          (setq RangeCellName_list_col_ (TA:remove-numbers (nth  RangeCellName_list_i RangeCellName_list_)))
          (setq RangeCellName_list_row_ (TA:remove-alphabet (nth  RangeCellName_list_i RangeCellName_list_)))
          
          
          (setq R1C1_data_ 
                  (list 
                    (setq RangeCellName_list_col_ (TA_EXCEL_RangeCOL_to_C1 RangeCellName_list_col_ ) )
                    (atoi RangeCellName_list_row_)
                  )
          )
          (setq r1c1_list_ (cons R1C1_data_ r1c1_list_ ))

        
          
          (setq RangeCellName_list_i (+ RangeCellName_list_i 1))
        )
        (setq r1c1_list_ (reverse r1c1_list_ ))
      ;
    )
    (defun TA_EXCEL_RangeCOL_to_C1 (col)
      (setq len (strlen col)) ; หาความยาวของตัวอักษร
      (setq result 0)
      (setq i 0)
      
      ;; loop ผ่านตัวอักษรแต่ละตัวในคอลัมน์
      (repeat len
        (setq char (strcase (substr col (1+ i) 1))) ; เอาตัวอักษรทีละตัว
        (setq result (+ result (* (- (ascii char) 64) (expt 26 (- len (1+ i)))))) ; คำนวณตามฐาน 26
        (setq i (1+ i)) ; เพิ่มตัวนับ
      )
      result
    )
    (defun TA_EXCEL_method_password ()
      (setq _Workbook_obj_ (vlax-invoke-method 
                              (vlax-get-property vla-obj_app 'WorkBooks)
                              'Open
                              filePath ; 1. Filename
                              0 ; 2. UpdateLinks
                              :vlax-false ; 3. ReadOnly
                              nil ; 4. Format
                              "bb" ; 5. for input Password 
                            )
      )
    )
    (defun TA_EXCEL_Merge_cell (_worksheet_obj_ lst_cell_1 lst_cell_2 )
      ;Note By Code_Developer
      ;The principle of codework is desgined for merge cell object in Excel APP
      ;
      ;Example Argument
        ; (setq lst_cell_1 (list 1 5))
        ; (setq lst_cell_2 (list 1 8))
      ;
        (setq cell_1 (vlax-variant-value (vlax-get-property (vlax-get _worksheet_obj_ 'Cells) 'Item (car lst_cell_1) (cadr lst_cell_1))))
        (setq cell_2 (vlax-variant-value (vlax-get-property (vlax-get _worksheet_obj_ 'Cells) 'Item (car lst_cell_2) (cadr lst_cell_2))))
        (setq cell_range_obj_ (vlax-get-property _worksheet_obj_ 'Range cell_1 cell_2))
        (vlax-put-property cell_range_obj_ 'MergeCells  :vlax-true)
      ;

    )
    (defun TA_EXCEL_UnMerge_cell (_worksheet_obj_ lst_cell_1 lst_cell_2 )
      ;Note By Code_Developer
      ;The principle of codework is desgined for merge cell object in Excel APP
      ;
      ;Example Argument
        ; (setq lst_cell_1 (list 1 5))
        ; (setq lst_cell_2 (list 1 8))
      ;
        (setq cell_1 (vlax-variant-value (vlax-get-property (vlax-get _worksheet_obj_ 'Cells) 'Item (car lst_cell_1) (cadr lst_cell_1))))
        (setq cell_2 (vlax-variant-value (vlax-get-property (vlax-get _worksheet_obj_ 'Cells) 'Item (car lst_cell_2) (cadr lst_cell_2))))
        (setq cell_range_obj_ (vlax-get-property _worksheet_obj_ 'Range cell_1 cell_2))
        (vlax-put-property cell_range_obj_ 'MergeCells  :vlax-false)
      ;

    )
    (defun TA_EXCEL_get_rangeccell_color (_worksheet_obj_ lst_cell_1 lst_cell_2  )
      ;Note By Code_Developer
      ;The principle of codework is desgined for merge cell object in Excel APP
      ;
      ;Example Argument
        (setq lst_cell_1 (list 1 1))
        (setq lst_cell_2 (list 1 1))
        ; (setq color_rgb_list (list 50 50 50))
      ;
    
        (setq cell_1 (vlax-variant-value (vlax-get-property (vlax-get _worksheet_obj_ 'Cells) 'Item (car lst_cell_1) (cadr lst_cell_1))))
        (setq cell_2 (vlax-variant-value (vlax-get-property (vlax-get _worksheet_obj_ 'Cells) 'Item (car lst_cell_2) (cadr lst_cell_2))))
        (setq cell_range_obj_ (vlax-get-property _worksheet_obj_ 'Range cell_1 cell_2))
        (vlax-get-property
          (vlax-get-property cell_range_obj_ 'Interior  )
          'color
          
          
        )
        (vlax-dump-object (vlax-get-property cell_range_obj_ 'Interior  ))

      ;

    )
    (defun TA_EXCEL_input_rangeccell_color (_worksheet_obj_ lst_cell_1 lst_cell_2 color_rgb_list )
      ;Note By Code_Developer
      ;The principle of codework is desgined for merge cell object in Excel APP
      ;
      ;Example Argument
        ; (setq lst_cell_1 (list 1 5))
        ; (setq lst_cell_2 (list 1 8))
        ; (setq color_rgb_list (list 50 50 50))
      ;
    
        (setq cell_1 (vlax-variant-value (vlax-get-property (vlax-get _worksheet_obj_ 'Cells) 'Item (car lst_cell_1) (cadr lst_cell_1))))
        (setq cell_2 (vlax-variant-value (vlax-get-property (vlax-get _worksheet_obj_ 'Cells) 'Item (car lst_cell_2) (cadr lst_cell_2))))
        (setq cell_range_obj_ (vlax-get-property _worksheet_obj_ 'Range cell_1 cell_2))
        (vlax-put-property
          (vlax-get-property cell_range_obj_ 'Interior  )
          'color
          
          (car 
            (list 
              (+ (car color_rgb_list) 
                (* 256 (cadr color_rgb_list))
                (* 256 (* 256 (caddr color_rgb_list)))
              )
            )
          )
        )

      ;

    )
    (defun TA_EXCEL_input_rangeccell_colorindex (_worksheet_obj_ lst_cell_1 lst_cell_2 colorindex_code )
      ;Note By Code_Developer
      ;The principle of codework is desgined for merge cell object in Excel APP
      ;
      ;Example Argument
        ; (setq lst_cell_1 (list 1 5))
        ; (setq lst_cell_2 (list 1 8))
        ; (setq color_rgb_list (list 50 50 50))
      ;
    
        (setq cell_1 (vlax-variant-value (vlax-get-property (vlax-get _worksheet_obj_ 'Cells) 'Item (car lst_cell_1) (cadr lst_cell_1))))
        (setq cell_2 (vlax-variant-value (vlax-get-property (vlax-get _worksheet_obj_ 'Cells) 'Item (car lst_cell_2) (cadr lst_cell_2))))
        (setq cell_range_obj_ (vlax-get-property _worksheet_obj_ 'Range cell_1 cell_2))
        (vlax-put-property
          (vlax-get-property cell_range_obj_ 'Interior  )
          'color
          
          colorindex_code
        )

      ;

    )
    (defun TA:Excel_Open-Excel_ (Using_file_mode_ clear_file_mode )
      ;Excel_file_process_ 
        ;Note By Code_Developer
          ;Principle of codework is designed for open Excel file or lasted current excel window 
          ;and keep vla-object workbook in varibale
          ;in normally this sub funcntion was developed from commmand sub code
          ;
        ;
        ;Example incase userinput via command while code running
          ; (setq Using_file_mode_ (cond ( (getint (strcat "\nOpen new Excel File = 1\nUse Exiting Excel file = 2\n<" (rtos (setq Using_file_mode_ (cond (Using_file_mode_) (1.0) ) ) ) "> : " ) ) ) (Using_file_mode_) ) )
        ;
        ;Example Argument
        ;   (setq Using_file_mode_ 1) ;integer number for indicate condition  ;open new Excel fiel
        ;   (setq Using_file_mode_ 2) ;integer number for indicate condition  ;Use curent Excel file 
        ;   (setq clear_file_mode 1) ;integer number for indicate condition   ;clear content incase currnet Excel file 
        ; ;
        ;Subfunction 
          ; (TA:Excel_Clearcontents Excel_lasted_worksheet_obj_)
        ;
        (cond
          (;Open new Excel File
            (and
              (= Using_file_mode_ 1)
            )
            (progn 
              (setq get_ExcelApp_object_ (vlax-get-or-create-object "Excel.Application"))
              (setq Workbooks_obj_ (vlax-get-property get_ExcelApp_object_ 'workbooks) )
              (setq Workbooks_obj_ (TA:New_Excel_File_NEX_ get_ExcelApp_object_))
              (setq Excel_File+sheet_data_list_ (TA:Excel_Assembly_ALL-obj_list_ Workbooks_obj_))
              (format-all-workbook-list Excel_File+sheet_data_list_)
              (setq Excel_lasted_file_ (nth (- (length Excel_File+sheet_data_list_) 1) Excel_File+sheet_data_list_))
              (format-all-worksheet-list Excel_lasted_file_)
              (setq Excel_lasted_sheet_obj_ (vlax-get-property (nth 2 Excel_lasted_file_ ) 'sheets))
              (setq Excel_lasted_worksheet_obj_ (vlax-get-property Excel_lasted_sheet_obj_ 'item 1))
              (vlax-put-property Excel_lasted_worksheet_obj_ 'name  "Summary block object")
            )
          )
          (;Exiting Excel file
            (and
              (= Using_file_mode_ 2)
              (/= (setq get_ExcelApp_object_ (vlax-get-object "Excel.Application")) nil)
              (/= (setq Workbooks_obj_ (vlax-get-property get_ExcelApp_object_ 'workbooks) ) nil)
              (/= (setq workbook_obj_ (vlax-get-property get_ExcelApp_object_ 'ActiveWorkbook)) nil)
            )
            (progn
              (setq Workbooks_obj_ (vlax-get-property get_ExcelApp_object_ 'workbooks) )
              (setq workbook_obj_ (vlax-get-property get_ExcelApp_object_ 'ActiveWorkbook))
              (setq Excel_lasted_sheet_obj_ (vlax-get-property workbook_obj_ 'sheets))
              (setq Excel_lasted_worksheet_obj_ (vlax-get-property Excel_lasted_sheet_obj_ 'item 1))
              (vlax-put-property Excel_lasted_worksheet_obj_ 'name  "Summary block object")
              ;incase userpinput
                ; (if ( = (setq clear_file_mode (cond ( (getint (strcat "\nClear Contents Excel File = 1\nKeep Existing Contents Excel file = 2\n<" (rtos (setq clear_file_mode (cond (clear_file_mode) (1.0) ) ) ) "> : " ) ) ) (clear_file_mode) ) ) 1)
                ;   (progn
                ;     (TA:Excel_Clearcontents Excel_lasted_worksheet_obj_ )
                ;   )
                ; )
              ;
              (if ( = clear_file_mode 1)
                (progn
                  (TA:Excel_Clearcontents Excel_lasted_worksheet_obj_ )
                )
              )                
            )    
          )
        )
        ; (vlax-dump-object get_ExcelApp_object_ )
        ; (vlax-dump-object (vlax-get (vlax-get get_ExcelApp_object_ 'selection  ) 'address ) )
        ; (vlax-dump-object (vlax-get get_ExcelApp_object_ 'ActiveCell  ) )
        ; (vlax-dump-object get_ExcelApp_object_ )
        ; (vlax-get get_ExcelApp_object_ 'selection  )
        (setq Excel_lasted_worksheet_obj_ Excel_lasted_worksheet_obj_)
      ;
    )
    (defun TA:EXCEL_autofit_column_ (_worksheet_obj_ coloumn_cell)
      (vlax-invoke-method
        (vlax-variant-value 
          (vlax-get-property 
            (vlax-get-property 
              _worksheet_obj_ 
              "columns"
            )
            "item"
            coloumn_cell
          )
        )
        'autofit
      )
    )
    (defun TA:EXCEL_autofit_rangecell_ (_worksheet_obj_ range_cell_1_obj_ range_cell_2_obj_ )
      ;Note By Code_Developer
      ;principle of codework is baseon VBA language 
        ;Worksheets("Sheet1").Range("A1:E1").Columns.AutoFit
      ;
      (setq range_cell_1_obj_ (vlax-variant-value (vlax-get-property (vlax-get _worksheet_obj_ 'Cells) 'Item (car range_cell_1) (cadr range_cell_1))))
      (setq range_cell_2_obj_ (vlax-variant-value (vlax-get-property (vlax-get _worksheet_obj_ 'Cells) 'Item (car range_cell_2) (cadr range_cell_2))))
      (vlax-invoke-method 
        (vlax-get-property 
          (setq vla-range_obj_ 
            (vlax-get-property 
              _worksheet_obj_
              'Range
              range_cell_1_obj_
              range_cell_2_obj_
            )
          )
          'columns
        )
        'autofit
      )
    )
    (defun TA:Excel_foreach_input_list_dataset_R1C1 (_worksheet_obj_ row_start_ col_start_ main_list_  )
      ;Note By Code_Developer
        ;principle of coodework is designed for input data list to Excel appication via list/gruop data,
        ;Can specify R1C1 via argument (row_start_ col_start_)

        ;Precautions when using this program 
          ;The argument main_list_ must contain data in the form of a main list that groups multiple sublists.
          ;Each sublist holds detailed data intended for display purposes.
          ;Example
            ; (setq mainlist ;main list_
            ;                (list 
            ;                  (list 54 68 6 6 32 68 3 65 6 35 65 3 35 61 64 95 3) ;sub list_
            ;                  (list 54 68 6 6 32 68 3 65 6 35 65 3 35 61 64 95 3) ;sub list_
            ;                  (list 54 68 6 6 32 68 3 65 6 35 65 3 35 61 64 95 3) ;sub list_
            ;                  (list 54 68 6 6 32 68 3 65 6 35 65 3 35 61 64 95 3) ;sub list_
            ;                )
            ; )
            ;Precautions when using this program 
              ;The argument main_list_ must contain data in the form of a main list that groups multiple sublists.
              ;Each sublist holds detailed data intended for display purposes.
              ;Example 1
                ; mainlist_
                ; └─ sublist
                ;    └─ sublist of sublist (maximun Below lv.3 )
                ; └─ sublist
                ;    └─ sublist of sublist (maximun Below lv.3 )

                ; (setq mainlist ;main list_
                ;                (list 
                ;                  (list 54 68 6 6 32 68 3 65 6 35 65 3 35 61 64 95 3) ;sub list_
                ;                  (list 54 68 6 6 32 68 3 65 6 35 65 (list "A" "B" "C" "D") 3 35 61 64 95 3) ;sub list_
                ;                  (list 54 68 6 6 32 68 3 65 6 35 65 3 35 61 64 95 3) ;sub list_
                ;                  (list 54 68 6 6 (list "A" "B" "C" "D") 32 68 3 65 6 35 65 3 35 61 64 95 3) ;sub list_
                ;                )
                ; )
              ;
            ;
          ;
        ;
      ;
      ;
      ; ;Example_argument_
      ;   (setq row_start_ 1)
      ;   (setq col_start_ 1)
      ; ;
        (foreach sub_group_ main_list_
          (setq col_ col_start_)
          (if 
            (= (listp sub_group_) T)
            (progn
              (foreach sub_list_ sub_group_  ; ← ลูปชั้นที่ 2
                (if (listp sub_list_)
                  (foreach sub_value_ sub_list_  ; ← ลูปชั้นที่ 3
                    (progn
                      (vlax-put
                        (vlax-variant-value
                          (vlax-get-property
                            (vlax-get _worksheet_obj_ 'Cells)
                            'Item
                            row_start_
                            col_
                          )
                        )
                        'Value
                        sub_value_
                      )
                      (setq col_ (+ col_ 1))
                    )
                  )
                  ;; ถ้า sub_list_ ไม่ใช่ list → แปลว่าเป็นค่าธรรมดา (อาจอยู่แค่ 2 ชั้น)
                  (progn
                    (vlax-put
                      (vlax-variant-value
                        (vlax-get-property
                          (vlax-get _worksheet_obj_ 'Cells)
                          'Item
                          row_start_
                          col_
                        )
                      )
                      'Value
                      sub_list_
                    )
                    (setq col_ (+ col_ 1))
                  )
                )
              )
            )
          )

          (setq row_start_ (+ row_start_ 1))
        )
    )
    (defun TA:EXCEL_all-cut-copy_row_ (_worksheet_obj_ row_cell method-argument-type)
      ;Note By Code_Developer
        ;input argument-type = 'copy
        ;input argument-type = 'cut
      ;
      (vlax-invoke-method
        (vlax-variant-value 
          (vlax-get-property 
            (vlax-get-property 
              _worksheet_obj_ 
              "rows"
            )
            "item"
             row_cell
          )
        )
        method-argument-type
      )
    )
    



    (defun c:Open_Excel_File_OPEX_ ()
      (if (= vla-obj_app nil)
        (progn
          (setq vla-obj_app (vlax-get-or-create-object "Excel.Application"))
          
        )
      )
      (setq filePath (getfiled "Select an Excel file"  "C:/TA/TEMP EST FILES/" "" 8)) ;open Ex-file
      (if 
        (and
          (if
            (/= filePath nil)
            (progn
              (or 
                (wcmatch (strcase filePath) "*XLSX")
                (wcmatch (strcase filePath) "*XLSM")
              )
            )
            nil          
          )
        )
        (progn
              ; (setq vla-obj_app (vlax-get-or-create-object "Excel.Application"))
                (setq _Workbook_obj_ (vlax-invoke-method (vlax-get-property vla-obj_app 'WorkBooks) 'Open filePath)) ;VLA-OBJECT _Workbook
                  (setq sheets_obj_ (vlax-get-property _Workbook_obj_ 'Sheets)) ;VLA-OBJECT Sheets
                    (setq sheets_obj_length (vlax-get-property sheets_obj_ 'count )) ;total_worksheet_in_file_
                  (setq _worksheet_obj_ (vlax-get-property sheets_obj_ 'item 1)) ;VLA-OBJECT _Worksheet
                  (setq _worksheet_obj_name (vlax-get-property _worksheet_obj_ 'name))
            (vlax-put-property vla-obj_app 'Visible :vlax-true)
        )
        (alert "invalid file please try agaian")
      )
    )

  ;
  ;Shell_FUNC
    ;Copy to clipboard FUNC
      (defun TA:copytext->clipboard (clipboard_text)
        ;sub FUNC สำหรับในคัดลอก text ให้อยู่ clipboard สำหรับ ctrl+v ในอนาคต
        ;มีฟังชั่นแบบนี้ด้วยหรอ ถามจริง
        (vlax-invoke
          (vlax-get
            (vlax-get (setq htmlfile (vlax-create-object "htmlfile")) 'ParentWindow)
            'ClipBoardData
          )
          'SetData
          "Text"
          clipboard_text ;input อะไรลงไป
        )
      )
      (defun TA:GetClipboardText ( / htmlfile clipObj result)
        (setq htmlfile (vlax-create-object "htmlfile"))
        (setq clipObj  (vlax-get (vlax-get htmlfile 'ParentWindow) 'ClipBoardData))
        (setq result   (vlax-invoke clipObj 'GetData "Text"))
        (vlax-release-object htmlfile)
        result
      )
    ;
    ;create_shortcut_FUNC
      (defun TA:create_shortcut_file (targetPath shortcutPath shortcutName )
        ;Note By Code_Developer
        ;As following argument name targetPath shortcutName shortcutPath_ must be Englist letter only 
        ;
        ; ;user_input for example process
          ; ; (setq targetPath    "C:\\xvba_modules-bb\\test.txt") ;argument example
          ; (setq targetPath  "C:\\TA\\TA_WORK\\000-AREA_PP29-AR-1305-A.pdf") ;argument example
          ; ; (setq shortcutPath    "C:\\xvba_modules-bb\\")       ;argument example
          ; (setq shortcutName "x1111test")                    ;argument example
          (setq shortcutPath_  (strcat shortcutPath shortcutName ".lnk"))
        ; ;
        ;get vla-object shell appication
          (setq shell (vlax-create-object "WScript.Shell"))
          (setq shortcut (vlax-invoke-method shell 'CreateShortcut shortcutPath_))
        ;
        ;put properties shortcut object
          (vlax-put-property shortcut 'TargetPath targetPath)
          (vlax-put-property shortcut 'WindowStyle 1)
          (vlax-put-property shortcut 'Description "My Shortcut Description")
        ;
        ;create shotcut to shortcutPath
          (vlax-invoke-method shortcut 'Save)
        ;clean object
          (vlax-release-object shortcut)
          (vlax-release-object shell)
        ;
        (princ "\nShortcut created successfully.")
        (princ)
      )
    ;
  ;
  ;FINDER_FUNC_
    (defun TA:blockname_finder_ (ss_pre_filter_set_xx_ finding_mode_value_ text_list_ )
      ;user_input
        (setq finding_screw_mode_                    "1 = *wildcard*") 
        (setq font_search_                           "2 = *Character") 
        (setq back_search_                           "3 = Character*") 
        ; (setq finding_mode_value_ (cond ((getint (strcat finding_screw_mode_ "\n" font_search_ "\n" back_search_ "\n" "<" (rtos (setq finding_mode_value_ (cond (finding_mode_value_) (1.0) ) ) ) "> : " ) ) ) (finding_mode_value_) ) )
      ;
      ;selection_set_for_fillter_blk_name
        ; (if  ;pre_select_ssget_or_post_select_ssget
        ;   (=
        ;     (setq ss_pre_filter_set_xx_ (ssget "x"
        ;                                       (list
        ;                                         (cons 0 "INSERT") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;     nil
        ;   )
        ;   (progn
        ;     (setq ss_pre_filter_set_xx_ (ssget
        ;                                       (list
        ;                                         (cons 0 "INSERT") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;   )
        ;   (sslength ss_pre_filter_set_xx_)
        ; )
      ;
      (if (/= ss_pre_filter_set_xx_ nil)
        (progn
          ;preloop_and_while
            (setq ss_pre_filter_set_xx_i 0)
            (setq selection_target_ (ssadd))
            (while (< ss_pre_filter_set_xx_i (sslength ss_pre_filter_set_xx_))
              (setq ss_pre_filter_set_xx_ename_ (ssname ss_pre_filter_set_xx_ ss_pre_filter_set_xx_i))
              (setq ss_pre_filter_set_xx_obj_ (vlax-ename->vla-object ss_pre_filter_set_xx_ename_))
                ;preloop_and_while
                  (if (= (vl-princ-to-string (type text_list_)) "LIST")
                      (progn
                          (setq text_list_i 0)
                          (while (< text_list_i (length text_list_))
                            (setq text_list_ename_ (nth  text_list_i text_list_))
                              (cond
                                (;if 
                                  (and
                                    (= finding_mode_value_ 1)
                                    (= (wcmatch (strcase (LM:effectivename ss_pre_filter_set_xx_obj_ )) (strcase (strcat "*" text_list_ename_  "*"))) T) ;form_1
                                    ; (= (wcmatch (LM:vl-getattributevalue ss_pre_filter_set_xx_filter_obj_ "NOOO") (strcat "*" "6264" "*") ) T ) ;form_2
                                  )
                                  (progn
                                    (setq selection_target_ (ssadd  ss_pre_filter_set_xx_ename_ selection_target_))
                                  )
                                )
                                (;if 
                                  (and
                                    (= finding_mode_value_ 2)
                                    (= (wcmatch (strcase (LM:effectivename ss_pre_filter_set_xx_obj_ )) (strcase (strcat "*" text_list_ename_  ))) T) ;form_1
                                    ; (= (wcmatch (LM:vl-getattributevalue ss_pre_filter_set_xx_filter_obj_ "NOOO") (strcat "*" "6264" "*") ) T ) ;form_2
                                  )
                                  (progn
                                    (setq selection_target_ (ssadd ss_pre_filter_set_xx_ename_ selection_target_))
                                  )
                                )
                                (;if 
                                  (and
                                    (= finding_mode_value_ 3)
                                    (= (wcmatch (strcase (LM:effectivename ss_pre_filter_set_xx_obj_ )) (strcase (strcat  text_list_ename_  "*"))) T) ;form_1
                                    ; (= (wcmatch (LM:vl-getattributevalue ss_pre_filter_set_xx_filter_obj_ "NOOO") (strcat "*" "6264" "*") ) T ) ;form_2
                                  )
                                  (progn
                                    (setq selection_target_ (ssadd  ss_pre_filter_set_xx_ename_ selection_target_))
                                  )
                                )
                              )      
                            (setq text_list_i (+ text_list_i 1))
                          )
                        ;
                      )
                      (princ "argument is not array list")
                  )
                ;      
              (setq ss_pre_filter_set_xx_i (+ ss_pre_filter_set_xx_i 1))
            )
          ;
          ;selection_object_process
            ; (length selection_target_)
            ; (command "pselect"  selection_target_ "" )
            (setq selection_target_ selection_target_)
            
          ;
        )
      )
      (setq selection_target_ selection_target_)
    )
    (defun c:SFBx2_stackblk-to-list_ (  )
      ;selection_set_for_fillter_blk_name
        (if  ;pre_select_ssget_or_post_select_ssget
          (=
            (setq ssblk_list_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ssblk_list_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ssblk_list_)
        )
      ;
      ;preloop_and_while ;get_effectivename_from_selection_set
        (setq ssblk_list_i 0)
        (setq effectivename_list_ (list "ALL BLOCK"))
        (if ssblk_list_
          (progn
            (while (< ssblk_list_i (sslength ssblk_list_))
              (setq ssblk_list_ename_ (ssname ssblk_list_ ssblk_list_i))
              (setq ssblk_list_obj_ (vlax-ename->vla-object ssblk_list_ename_))
              (setq ssblk_list_effectivename_ (LM:effectivename ssblk_list_obj_))
              (setq effectivename_list_ (cons ssblk_list_effectivename_ effectivename_list_))

              (setq ssblk_list_i (+ ssblk_list_i 1))
            )
            ; (setq effectivename_list_ (LM:CountItems (reverse effectivename_list_) nil))
          )
        )
      ;
    )
    (defun c:SFBx1_FINDING_SPECFILY_NAME_BLOCK (  )
      (if effectivename_list_
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          (setq result_ nil)
          (setq effectivename_list_1 (foreach item_ effectivename_list_ 
                                      (if (not (member item_ result_)) 
                                        (setq result_ (append result_ (list item_)))
                                      )
                                    )
          )
          (setq sdas (TA:choose_list_v4 effectivename_list_1 "Select Block Name to find" sdas ) )
          (if (= sdas "ALL BLOCK")
            (progn
              (setq result_filter_ (TA:EF_Filter_ss_set_V2_ ss_pre_filter_set_xx_ effectivename_list_1  ) )
              
            )
            (setq result_filter_ (TA:EF_Filter_ss_set_V2_ ss_pre_filter_set_xx_ (list sdas )))
          )
          
        )
      )
      (command "pselect"  result_filter_ "" )
    )
    (defun c:find_area_ ()
      ;selection_set_for_fillter_blk_name
        (if  ;pre_select_ssget_or_post_select_ssget
          (=
            (setq ss_pre_filter_set_xx_ (ssget "i"
                                              (list
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget 
                                              (list
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq area_i 0)
        (while (< ss_pre_filter_set_xx_i (sslength ss_pre_filter_set_xx_))
          (setq ss_pre_filter_set_xx_ename_ (ssname ss_pre_filter_set_xx_ ss_pre_filter_set_xx_i))
          (setq ss_pre_filter_set_xx_hon_obj_ (vlax-ename->vla-object ss_pre_filter_set_xx_ename_))
          (setq ss_pre_filter_set_xx_hon_obj_area_ (vla-get-area ss_pre_filter_set_xx_hon_obj_ ))
          (setq area_i (+ area_i ss_pre_filter_set_xx_hon_obj_area_))
          (setq ss_pre_filter_set_xx_i (+ ss_pre_filter_set_xx_i 1))
        )
      ;  
      ;convert sq.mm to sq.m
        (setq ss_pre_filter_set_xx_hon_obj_area_sqm (/ area_i 1000000))
      ;
      (alert (strcat (rtos ss_pre_filter_set_xx_hon_obj_area_sqm 2 2 ) " " "sq.m"))
    )
    (defun c:find_total_length_fiTL ()
 
      ;selection_set_for_fillter_blk_name
        ; (if  ;pre_select_ssget_or_post_select_ssget
        ;   (=
        ;     (setq ss_pre_filter_set_xx_ (ssget "i"
        ;                                       (list
        ;                                         (cons 0 "lwpolyline") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;     nil
        ;   )
        ;   (progn
        ;     (setq ss_pre_filter_set_xx_ (ssget
        ;                                       (list
        ;                                         (cons 0 "lwpolyline") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;   )
        ;   (sslength ss_pre_filter_set_xx_)
        ; )
      ;

      (setq ss_pre_filter_set_xx_ (ssget "c" ss1 ss2(list (cons 0 "lwpolyline"))))
      (setq mainfinder_ename_ (car (entsel "specify Object")))
      (setq mainfinder_obj_ (vlax-ename->vla-object mainfinder_ename_))
      (setq mainfinder_obj_length (vla-get-length mainfinder_obj_))
      ;preloop_and_while
        (setq ss_pre_filter_set_xx_i 0)
        (setq sstarget_ (ssadd))
        (setq sstarget_ (ssadd mainfinder_ename_ sstarget_))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (setq ss_pre_filter_set_xx_obj_TL (vla-get-length ss_pre_filter_set_xx_obj_))
          (if (= ss_pre_filter_set_xx_obj_TL mainfinder_obj_length )
            (progn
              (setq sstarget_ (ssadd ss_pre_filter_set_xx_ename_ sstarget_ ))
              (vla-move ss_pre_filter_set_xx_obj_  (vlax-3d-point ss1) (vlax-3d-point  ss11 (cadr ss1 ) 0) )
            )
          )
          (setq ss_pre_filter_set_xx_i (+ ss_pre_filter_set_xx_i 1))
        )
      ;
      (setq ss11 (+ ss11 10))
      
    )
    (defun c:foo ()
      (setq ss1 (getpoint))
      (setq ss2 (getpoint))
      (setq ss11 (+ (car ss1) 10) )
      (setq ss11 (+ ss11 20) )
    )
    (defun c:fihand ()
      (setq handent_
        (list 
          (list "4EB8F0")
          (list "4EB308")
          (list "4EB31A")
          (list "4EB32C")
          (list "4EB33E")
          (list "4EB350")
          (list "4EB3E0")
          (list "4EB3F2")
          (list "4EB404")
          (list "4EB416")
          (list "4EB428")
          (list "4EB4A6")
          (list "4EB4B8")
          (list "4EB4CA")
          (list "4EB4DC")
          (list "4EB4EE")
          (list "4EB56C")
          (list "4EB57E")
          (list "4EB590")
          (list "4EB5A2")
          (list "4EB5B4")
          (list "4EB632")
          (list "4EB644")
          (list "4EB656")
          (list "4EB668")
          (list "4EB67A")
          (list "4EB8DE")
          (list "4F5ED7")
          (list "4F5EF3")
          (list "4F5EC9" "4EB2F6")
          (list "4EB6E6" "4EB362")
          (list "4EB6F8" "4EB3CE")
          (list "4EB70A" "4EB43A")
          (list "4EB71C" "4EB494")
          (list "4EB72E" "4EB500")
          (list "4EB740" "4EB55A")
          (list "4EB752" "4EB5C6")
          (list "4EB764" "4EB620")
          (list "4EB776" "4EB68C")
          (list "4EB860")
          (list "4EB79A" "4F5F2B")
          (list "4F5EAD" "4EB788" "4EB7AC" "4F5F01")
          (list "4F5F0F" "4F5F1D")
          (list "4F5EE5")
          (list "4EB374")
          (list "4EB386")
          (list "4EB398")
          (list "4EB44C")
          (list "4EB45E")
          (list "4EB470")
          (list "4EB512")
          (list "4EB524")
          (list "4EB536")
          (list "4EB5D8")
          (list "4EB5EA")
          (list "4EB5FC")
          (list "4EB69E")
          (list "4EB6B0")
          (list "4EB6C2")
          (list "4EB872")
          (list "4EB3AA")
          (list "4EB482")
          (list "4EB548")
          (list "4EB60E")
          (list "4EB6D4")
          (list "4F5EBB")
          (list "4F5E9F")
        )
      )

      ;preloop_and_while
        (setq handent_i 0)
        (setq handent_selection_ (ssadd))
        (while (< handent_i (length handent_))
          (setq GTP (getpoint "SSSSSSSSSSS"))
          (setq handent_list_ (nth  handent_i handent_))
          (if (= (listp handent_list_) T )
            (progn
              ;preloop_and_while
                (setq handent_list_i 0)
                (while (< handent_list_i (length handent_list_))
                  (setq handent_list_ename_ (nth  handent_list_i handent_list_))
                  (setq handent_list_obj_ (vlax-ename->vla-object (handent handent_list_ename_)))
                  (vla-move handent_list_obj_ (vlax-3d-point (vlax-safearray->list (vlax-variant-value (vla-get-insertionpoint handent_list_obj_)))) (vlax-3d-point GTP))
                  ; (setq handent_selection_ (ssadd (handent handent_list_ename_ ) handent_selection_  ))
                  (setq handent_list_i (+ handent_list_i 1))
                )
              ;
            )
            ; (setq handent_selection_ (ssadd (handent handent_list_ ) handent_selection_  ))
          )
          (setq handent_i (+ handent_i 1))
        )
      ;
      
      
    )
    (defun c:find_distance_y_fidy ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq ss_pre_filter_set_xx_dist ())
        (while (< ss_pre_filter_set_xx_i 2)
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_dist (cons (setq ss_pre_filter_set_xx_obj_ins_ (vlax-safearray->list (vlax-variant-value (vla-get-insertionpoint ss_pre_filter_set_xx_obj_)))) ss_pre_filter_set_xx_dist ))
          (setq ss_pre_filter_set_xx_i (+ ss_pre_filter_set_xx_i 1))
        )
      ;

      (alert (strcat "distance " (rtos (distance (nth 0 ss_pre_filter_set_xx_dist) (nth 1 ss_pre_filter_set_xx_dist)) 2 2) "mm."))
    )
    (defun TA:if_found_layer_ (layer_val_)
      (if (=  (type (setq iferror_ ;Detect the variable's result in case of a function error
                    (vl-catch-all-apply 
                      (function 
                        (lambda () 
                          (setq iferror_val_ (vla-Item (vla-get-layers (setq doc (vla-get-ActiveDocument (vlax-get-acad-object)))) layer_val_))
                        )
                      )
                    )
                  )
              
              ) 
            'VLA-OBJECT
          )
      (progn
        T
      )
      nil
      )
    )
    (defun c:finding_attribute_findattval ()
      (if (and 
            ; (/= att-pre_filter_set_xx_ nil)
            ; (= (TA:getkword "new input selection-set ?"  "Yes" "No"  att-pre_filter_set_xx_ "false") nil) ;พัง
            (= 1 1)
          )
        (progn
          ;selection_set_for_fillter_blk_name
            (if  ;pre_select_ssget_or_post_select_ssget
              (=
                (setq att-pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq att-pre_filter_set_xx_ (ssget
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength att-pre_filter_set_xx_)
            )
          ;
        )
      )

      (setq att-finder_mode (TA:choose_list_v3 
                              (setq attlist_ (list "match_value" "*wildcard_value*" "numbering" "multi-name"))
                              "select block"
                              (if (or 
                                    (= att-finder_modeexval nil)
                                    (= att-finder_mode nil)
                                  ) 
                                (progn 
                                  (setq att-finder_modeexval 1)
                                )
                                (setq att-finder_modeexval (+ 
                                                             (vl-position att-finder_mode 
                                                                          attlist_
                                                             )
                                                             1
                                                           )
                                )
                              )
                            )
      )
      (setq att-value_list_ (list "user input" "PP17" "S2214V" "SA-09101" "PP18" "SA-05611" "PP19" "NS-1S-E0114" "SD-9211" "standard_varies_shape") )
      (setq att-value_multi-list_ (list 
                                    (list "")
                                    (list "Detail 1" "Detail 2" "Detail 3" "Detail 4" "Detail 5" "Detail 6"  )
                                    (list "Detail 7" "Detail 8" "Detail 9" "Detail 10" "Detail 11" "Detail 12" )
                                    (list "Detail 13" "Detail 14" "Detail 15" "Detail 16" "Detail 17" "Detail 18"  )
                                    (list "Detail 19" "Detail 20")
                                    (list "A-1" "A-2" "B-1" "B-2" "D-1") ;6
                                    (list "B-3" "C-1" ) ;7
                                    (list "TYPE 26" "TYPE 2" "TYPE 28" ) ;7
                                  )
      )
      (cond
        ( (= att-finder_mode "match_value")
          (progn 
            (setq att-match_value_ (TA:choose_list_v3
                               att-value_list_
                               "Specify Macth Case Attribute Value"
                               (if (and
                                        (= att-match_value_exval nil)
                                        (= att-match_value_ nil)
                                   )
                                 (progn
                                   (setq att-match_value_exval 1)
                                 )
                                 (setq att-match_value_exval
                                       (+ (vl-position
                                            att-match_value_
                                            att-value_list_
                                          )
                                          1
                                       )
                                 )
                               )
                     )
            )
            (setq att-value_list_val att-match_value_)
          )
        )
        ( (= att-finder_mode "*wildcard_value*")
          (progn
            (if (and 
                  (= 
                    (vl-catch-all-error-p 
                      (vl-catch-all-apply 
                        (function 
                          (lambda () 
                            (setq wildcard_value 
                                  (TA:choose_list_v3 
                                    att-value_list_
                                    "select block"
                                    (if (or (= wildcard_value_exval nil) (= wildcard_value nil) )
                                      (progn 
                                        (setq wildcard_value_exval 1)
                                      )
                                      (setq wildcard_value_exval (+ (vl-position wildcard_value att-value_list_ ) 1 ) )
                                    )
                                  )
                            )
                          )
                        )
                      )
                    )
                    nil
                  )
                  (/= wildcard_value "user input")
                )
              (progn
                wildcard_value
              )
              (setq wildcard_value_str-val_ ;Get-string by keep previous value
                  (if
                    (or
                      (/= (setq wildcard_value_str-val_val (getstring (strcat "\nSpecify Pattern name <" (if wildcard_value_str-val_ wildcard_value_str-val_ "") ">: ") ) ) "" )
                    )
                      (progn
                        (setq wildcard_value_str-val_ wildcard_value_str-val_val)
                        (setq wildcard_value_str-val_keep_val_ wildcard_value_str-val_val)
                      )
                    (setq wildcard_value_str-val_val wildcard_value_str-val_keep_val_)
                  )
              )
            )
            (setq att-value_list_val wildcard_value_str-val_)
          )
        )
        ( (= att-finder_mode "numbering")
          (progn
            (setq filter_min_range_ (cond ( (getreal (strcat "\nspecify get filter_min_range_ \n<" (rtos (setq filter_min_range_ (cond (filter_min_range_) (1.0) ) ) ) "> : " ) ) ) (filter_min_range_) ) )
            (setq filter_max_range_ (cond ( (getreal (strcat "\nspecify get filter_max_range_ \n<" (rtos (setq filter_max_range_ (cond (filter_max_range_) (1.0) ) ) ) "> : " ) ) ) (filter_max_range_) ) )
          )
        )
        ( (= att-finder_mode "multi-name")
          (progn
            (setq att-value_multi-list_val_ (cond ( (getint (strcat "\nspecify list set for matching \n<" (rtos (setq att-value_multi-list_val_ (cond (att-value_multi-list_val_) (1.0) ) ) ) "> : " ) ) ) (att-value_multi-list_val_) ) )
              
          )
        )
        
      )
      
      ;preloop_and_while
        (setq att-pre_filter_set_xx_i 0)
        (setq att-pre_filter_set_xx_new-ss_ (ssadd))
        (while (and 
                 (= (type att-pre_filter_set_xx_) 'PICKSET)
                 (< att-pre_filter_set_xx_i (sslength att-pre_filter_set_xx_))
               )
          (setq att-pre_filter_set_xx_ename_ (ssname att-pre_filter_set_xx_ att-pre_filter_set_xx_i)) 
          (setq att-pre_filter_set_xx_obj_ (vlax-ename->vla-object  att-pre_filter_set_xx_ename_))
          (if (and 
                (= (vla-get-hasattributes att-pre_filter_set_xx_obj_) :vlax-true)
                (/= (setq att-pre_filter_set_xx_obj_val-list_ (LM:vl-getattributevalue-val-TA-Modifies att-pre_filter_set_xx_obj_)) nil)
                (or 
                  (= att-finder_mode "match_value")
                  (= att-finder_mode "*wildcard_value*")
                )
              )
            (progn
              (if (/= (setq att-pre_filter_set_xx_obj_match-val_ (TA:wcmatch_list  (list att-value_list_val) att-pre_filter_set_xx_obj_val-list_ nil)) nil)
                (progn
                  (setq att-pre_filter_set_xx_new-ss_ (ssadd att-pre_filter_set_xx_ename_ att-pre_filter_set_xx_new-ss_ ))
                )
              )
              
            )
          )
          (if (and 
                (= (vla-get-hasattributes att-pre_filter_set_xx_obj_) :vlax-true)
                (/= (setq att-pre_filter_set_xx_obj_val-list_ (LM:vl-getattributevalue-val-TA-Modifies att-pre_filter_set_xx_obj_)) nil)
                (or 
                  (= att-finder_mode "numbering")
                )
              )
            (progn
              (setq tester_save (list "asd245"  "2dsg398598ifasa" "Sdasf" "900 mm.") )
              
              (vl-list->string tester_save )
            )
          )
          (if (and 
                (= (vla-get-hasattributes att-pre_filter_set_xx_obj_) :vlax-true)
                (/= (setq att-pre_filter_set_xx_obj_val-list_ (LM:vl-getattributevalue-val-TA-Modifies att-pre_filter_set_xx_obj_)) nil)
                (and 
                  (= att-finder_mode "multi-name")
                )
              )
            (progn
              (if (/= (setq att-pre_filter_set_xx_obj_match-val_ (TA:wcmatch_list  (nth (fix att-value_multi-list_val_) att-value_multi-list_) att-pre_filter_set_xx_obj_val-list_ nil)) nil)
                (progn
                  (setq att-pre_filter_set_xx_new-ss_ (ssadd att-pre_filter_set_xx_ename_ att-pre_filter_set_xx_new-ss_ ))
                )
              )
            )
          )
          (setq att-pre_filter_set_xx_i (+ att-pre_filter_set_xx_i 1))
        )
      ;
      (command "pselect"  att-pre_filter_set_xx_new-ss_ "" )
    )
    (defun c:FINDTXT (/ key ss)
      (setq key (getstring T "\nSpecify text to find: "))

      (setq ss
        (ssget "X"
          (list
            '(0 . "TEXT,MTEXT")
            (cons 1 (strcat "*" "Type " key  "*"))
          )
        )
      )
      (setq global_selction_set_ ss)
      (if ss
        (progn
          (princ (strcat "\nFound : " (itoa (sslength ss)) " object(s)"))
          (sssetfirst nil ss)
          (command "zoom" "O" global_selction_set_ "")
        )
        (princ "\nNot found.")
        
      )

      (princ)
    )
    (defun c:izoom ()
      (setq ss_i_zoom_ename_ (ssname  (ssget "i" ) 0))
        (setq ss_i_zoom_obj_ (vla-getboundingbox (vlax-ename->vla-object ss_i_zoom_ename_) 'min_ 'max_)) 
        (setq rec_min_ (vlax-safearray->list min_)) 
        (setq rec_max_ (vlax-safearray->list max_))   
      (vla-zoomcenter 
        (vlax-get-acad-object)
        (vlax-3d-point rec_max_ )
          400
      )
    )
    (defun c:current_zoom_curzoom ()
      (if (= cur-zoom_stopper_val nil)
        (progn
          (setq cur-zoom_stopper_val 25)
        )
      )
      (if (> (sslength (setq curzoom_ssget_ (ssget "i"))) 1)
        (progn
          ;preloop_and_while
            (setq curzoom_ssget_i 0)
            
            (setq cur-zoom_stopper_ nil)
            (while (and
                      (= (vl-catch-all-error-p cur-zoom_stopper_) nil)
                      (< curzoom_ssget_i (sslength curzoom_ssget_))
                   )
              (if (= curzoom_ssget_i 0)
                (progn
                  (sssetfirst nil nil) 
                )
              )
              (setq curzoom_ssget_ename_ (ssname curzoom_ssget_ curzoom_ssget_i))
              (setq curzoom_ssget_obj_ (vlax-ename->vla-object  curzoom_ssget_ename_))
              (setq curzoom_ssget_obj_bol_ (vla-getboundingbox curzoom_ssget_obj_ 'min_ 'max_)) 
              (setq rec_min_ (vlax-safearray->list min_)) 
              (setq rec_max_ (vlax-safearray->list max_))   
              (setq rec_all_ (nth 4 (TA:assembly_coordinate_coner (list rec_min_ rec_max_))))
              (vla-zoomcenter 
                (vlax-get-acad-object)
                (vlax-3d-point (list 
                                 (+ (car rec_all_) 0) 
                                 (+ (cadr rec_all_) 0) 
                                 (+ (if (caddr rec_all_) (progn (caddr rec_all_) ) 0 ) 0) 
                               ) )
                cur-zoom_stopper_val
              )
              (if (= curzoom_ssget_i (- ( sslength curzoom_ssget_) 1))
                (progn
                  (setq curzoom_ssget_i 0)
                )
              )
              (setq cur-zoom_stopper_
                (vl-catch-all-apply
                  (function
                    (lambda ()
                      (setq cur-zoom_stopper_val (cond ( (getint (strcat "\nspecify get zoom depth value \n<" (rtos (setq cur-zoom_stopper_val (cond (cur-zoom_stopper_val) (1.0) ) ) ) "> : " ) ) ) (cur-zoom_stopper_val) ) )
                    )
                  )
                )
              )
              (setq curzoom_ssget_i (+ curzoom_ssget_i 1))
            )
          ;
        )
      )
    )
    
  ;
  ;TITLE DRAWING FUNC
    (defun c:sort_heading_number_sorH ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq sorted_list_ercheck_ nil)
      (if (= (vl-prin1-to-string (TA:corrd_sorting_group (TA:standard_list_croodinate+ename (TA:EF_Filter_ss_set_ ss_pre_filter_set_xx_ "000 - HEADING NAME REV02-2" )) 1 )) "(nil)")
        (progn
          (setq sorted_list_ (TA:standard_list_croodinate+ename (TA:EF_Filter_ss_set_ ss_pre_filter_set_xx_ "000 - HEADING NAME REV02-2" )))
          (setq sorted_list_ercheck_ T)
        )
        (setq sorted_list_ (TA:corrd_sorting_group (TA:standard_list_croodinate+ename (TA:EF_Filter_ss_set_ ss_pre_filter_set_xx_ "000 - HEADING NAME REV02-2" )) 1 ))
      )
      
      ;ErrorDetect_
        (if ;Detect the variable's result in case of a function error
          (= 
            (wcmatch
              (vl-princ-to-string
                (setq variable_error_checking
                  (vl-catch-all-apply 
                    (function 
                      (lambda () 
                        (setq sorted_list_num_ (cond ( (getint (strcat "\nspecify get heading_number \n<" (rtos (setq sorted_list_num (cond (sorted_list_num) (1.0) ) ) ) "> : " ) ) ) (sorted_list_num) ) )
                      )
                    )
                  )
                )
              )
              "*nil*,*error*"
            )
            nil
          )
          (progn
            (setq sorted_list_num sorted_list_num_)
          )
        )
      ;
      ;preloop_and_while sorting overall heaing title
        (setq sorted_list_i 0)
        (while (< sorted_list_i (length sorted_list_))
          (setq sorted_list_main_ (nth  sorted_list_i sorted_list_))
          ;preloop_and_while sub heading in sorting list 
            (setq sorted_list_main_i 0)
            (while (< sorted_list_main_i (length sorted_list_main_))
              (if (= sorted_list_ercheck_ T)
                (progn
                  (setq sorted_list_main_ename_ (nth  sorted_list_main_i (cdr sorted_list_main_)))
                  (setq sorted_list_main_i (+ (length sorted_list_main_)  1))
                )
                (setq sorted_list_main_ename_ (cadr (nth  sorted_list_main_i sorted_list_main_)))
              )
              
              (setq sorted_list_main_ename_obj_ (vlax-ename->vla-object sorted_list_main_ename_))
              (LM:vl-setattributevalue sorted_list_main_ename_obj_ "LO" sorted_list_num)
              (LM:vl-setattributevalue sorted_list_main_ename_obj_ "DETAIL_NO." sorted_list_num)
              
              (setq sorted_list_num (+ sorted_list_num 1))
              (setq sorted_list_main_i (+ sorted_list_main_i 1))
            )
          ;
          (setq sorted_list_i (+ sorted_list_i 1))
        )
      ;
    )
    (defun c:sort_box_number_sorB ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq sorted_list_ercheck_ nil)
      (if (= (vl-prin1-to-string (TA:corrd_sorting_group (TA:standard_list_croodinate+ename (TA:EF_Filter_ss_set_ ss_pre_filter_set_xx_ "PANEL_SET.NO." )) 250 )) "(nil)")
        (progn
          (setq sorted_list_ (TA:standard_list_croodinate+ename (TA:EF_Filter_ss_set_ ss_pre_filter_set_xx_ "PANEL_SET.NO." )))
          (setq sorted_list_ercheck_ T)
        )
        (setq sorted_list_ (TA:corrd_sorting_group (TA:standard_list_croodinate+ename (TA:EF_Filter_ss_set_ ss_pre_filter_set_xx_ "PANEL_SET.NO." )) 1 ))
      )


      ;ErrorDetect_
        (if ;Detect the variable's result in case of a function error
          (= 
            (wcmatch
              (vl-princ-to-string
                (setq variable_error_checking
                  (vl-catch-all-apply 
                    (function 
                      (lambda () 
                        (setq sorted_list_num_ (cond ( (getint (strcat "\nspecify get heading_number \n<" (rtos (setq sorted_list_num (cond (sorted_list_num) (1.0) ) ) ) "> : " ) ) ) (sorted_list_num) ) )
                      )
                    )
                  )
                )
              )
              "*nil*,*error*"
            )
            nil
          )
          (progn
            (setq sorted_list_num sorted_list_num_)
          )
        )
      ;
      ;preloop_and_while sorting overall heaing title
        (setq sorted_list_i 0)
        (while (< sorted_list_i (length sorted_list_))
          (setq sorted_list_main_ (nth  sorted_list_i sorted_list_))
          ;preloop_and_while sub heading in sorting list 
            (setq sorted_list_main_i 0)
            (while (< sorted_list_main_i (length sorted_list_main_))
              (if (= sorted_list_ercheck_ T)
                (progn
                  (setq sorted_list_main_ename_ (nth  sorted_list_main_i (cdr sorted_list_main_)))
                  (setq sorted_list_main_i (+ (length sorted_list_main_)  1))
                )
                (setq sorted_list_main_ename_ (cadr (nth  sorted_list_main_i sorted_list_main_)))
              )
              
              (setq sorted_list_main_ename_obj_ (vlax-ename->vla-object sorted_list_main_ename_))
              (LM:vl-setattributevalue sorted_list_main_ename_obj_ "PANEL_SET.NO." sorted_list_num)
              (LM:vl-setattributevalue sorted_list_main_ename_obj_ "PANEL_SET.NO." sorted_list_num)
              
              (setq sorted_list_num (+ sorted_list_num 1))
              (setq sorted_list_main_i (+ sorted_list_main_i 1))
            )
          ;
          (setq sorted_list_i (+ sorted_list_i 1))
        )
      ;
    )
    (defun c:sort_box_number_sorFu ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ss_pre_filter_set_xx_ (TA:EF_Filter_ss_set_ ss_pre_filter_set_xx_ "001 - DYNAMIC REC&SSQ SHAPE SOLID_startpoint"))
      ;preloop_and_while
        (setq ss_pre_filter_set_xx_i 0)
        (setq sorted_list_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (setq sorted_list_ (cons (list ss_pre_filter_set_xx_ename_ (setq ss_pre_filter_set_xx_obj_ins_ (vlax-safearray->list (vlax-variant-value (vla-get-insertionpoint ss_pre_filter_set_xx_obj_))))) sorted_list_))
          (setq ss_pre_filter_set_xx_i (+ ss_pre_filter_set_xx_i 1))
        )
      ;
      ;TA:stanndard_lambda_sorting
        (setq sorted_list_sorted_ (vl-sort sorted_list_  ;bigest open indent list
                                                  (function 
                                                    (lambda (a b) 
                                                      (< (car (nth 1 a)) (car (nth 1 b)))
                                                    )
                                                  )
                              ) ;bigest close indent list
        )
      ;
      (setq sorted_list_num_ (cond ( (getint (strcat "\nspecify get heading_number \n<" (rtos (setq sorted_list_num (cond (sorted_list_num) (1.0) ) ) ) "> : " ) ) ) (sorted_list_num) ) )
      ;preloop_and_while sorting overall heaing title
        (setq sorted_list_i 0)
        (while (< sorted_list_i (length sorted_list_))
          (setq sorted_list_main_ (car (nth  sorted_list_i sorted_list_)))
          ;preloop_and_while sub heading in sorting list 
            (setq sorted_list_main_obj_ (vlax-ename->vla-object sorted_list_main_ename_))
              
              
              (LM:vl-setattributevalue sorted_list_main_obj_ "FULL_SIZE_NO." sorted_list_num)
              
              
              
              (setq sorted_list_num_ (+ sorted_list_num_ 1))
              (setq sorted_list_i (+ sorted_list_i 1))
            )
          ;

        
      ;
    )
    (defun c:sort_heading_number_sorH ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq sorted_list_ercheck_ nil)
      (if (= (vl-prin1-to-string (TA:corrd_sorting_group (TA:standard_list_croodinate+ename (TA:EF_Filter_ss_set_ ss_pre_filter_set_xx_ "PANEL_SET.NO." )) 1 )) "(nil)")
        (progn
          (setq sorted_list_ (TA:standard_list_croodinate+ename (TA:EF_Filter_ss_set_ ss_pre_filter_set_xx_ "PANEL_SET.NO." )))
          (setq sorted_list_ercheck_ T)
        )
        (setq sorted_list_ (TA:corrd_sorting_group (TA:standard_list_croodinate+ename (TA:EF_Filter_ss_set_ ss_pre_filter_set_xx_ "000 - HEADING NAME REV02-2" )) 1 ))
      )
      
      ;ErrorDetect_
        (if ;Detect the variable's result in case of a function error
          (= 
            (wcmatch
              (vl-princ-to-string
                (setq variable_error_checking
                  (vl-catch-all-apply 
                    (function 
                      (lambda () 
                        (setq sorted_list_num_ (cond ( (getint (strcat "\nspecify get heading_number \n<" (rtos (setq sorted_list_num (cond (sorted_list_num) (1.0) ) ) ) "> : " ) ) ) (sorted_list_num) ) )
                      )
                    )
                  )
                )
              )
              "*nil*,*error*"
            )
            nil
          )
          (progn
            (setq sorted_list_num sorted_list_num_)
          )
        )
      ;
      ;preloop_and_while sorting overall heaing title
        (setq sorted_list_i 0)
        (while (< sorted_list_i (length sorted_list_))
          (setq sorted_list_main_ (nth  sorted_list_i sorted_list_))
          ;preloop_and_while sub heading in sorting list 
            (setq sorted_list_main_i 0)
            (while (< sorted_list_main_i (length sorted_list_main_))
              (if (= sorted_list_ercheck_ T)
                (progn
                  (setq sorted_list_main_ename_ (nth  sorted_list_main_i (cdr sorted_list_main_)))
                  (setq sorted_list_main_i (+ (length sorted_list_main_)  1))
                )
                (setq sorted_list_main_ename_ (cadr (nth  sorted_list_main_i sorted_list_main_)))
              )
              
              (setq sorted_list_main_ename_obj_ (vlax-ename->vla-object sorted_list_main_ename_))
              (LM:vl-setattributevalue sorted_list_main_ename_obj_ "LO" sorted_list_num)
              (LM:vl-setattributevalue sorted_list_main_ename_obj_ "DETAIL_NO." sorted_list_num)
              
              (setq sorted_list_num (+ sorted_list_num 1))
              (setq sorted_list_main_i (+ sorted_list_main_i 1))
            )
          ;
          (setq sorted_list_i (+ sorted_list_i 1))
        )
      ;
    )
    (defun c:typical_sorting ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq  ss_pre_filter_set_xx_ (TA:EF_Filter_ss_set_V2_ ss_pre_filter_set_xx_ (list "300HK ORDER FROM CHINA REV.2-LOT 2_20260529-185614FLxx")))
      (setq ss_pre_filter_set_xx_ (TA:standard_list_croodinate_sorting ss_pre_filter_set_xx_ "X"))
      ;user-input process
        ; (setq prefix_txt (getstring "specify prefix text"))
        (setq prefix_txt "PJ25-031-P")
        (setq start_number (cond ( (getint (strcat "\nspecify get move to point\n<" (rtos (setq start_number (cond (start_number) (0) ) ) ) "> : " ) ) ) (start_number) ) )
      ;
      ;preloop_and_while TA:prefix_value
        (setq ss_pre_filter_set_xx_i 0)
        (while (< ss_pre_filter_set_xx_i (length ss_pre_filter_set_xx_))
          (setq ss_pre_filter_set_xx_ename_ (car (nth  ss_pre_filter_set_xx_i ss_pre_filter_set_xx_)))
          (setq ss_pre_filter_set_xx_obj_ (vlax-ename->vla-object  ss_pre_filter_set_xx_ename_))
          (LM:vl-setattributevalue ss_pre_filter_set_xx_obj_ "DWG_NO" (strcat prefix_txt (TA:prefix_value_000 start_number)))
          (LM:vl-setattributevalue ss_pre_filter_set_xx_obj_ "SHEET_NO" (strcat (rtos start_number 2 0) "/" (rtos (length ss_pre_filter_set_xx_) 2 0) ))
          (LM:vl-setattributevalue ss_pre_filter_set_xx_obj_ "TOTAL_NO" (length ss_pre_filter_set_xx_))
          (setq start_number (+ start_number 1))
          (setq ss_pre_filter_set_xx_i (+ ss_pre_filter_set_xx_i 1))
        )
      ;
    )
    (defun c:masterattso ()
      (setq prefix-name "1-VS01-AR-")
      (setq midfix "2564-")
      (setq starting_increment-number (cond ( (getint (strcat "\nspecify get move to point\n<" (rtos (setq starting_increment-number (cond (starting_increment-number) (0) ) ) ) "> : " ) ) ) (starting_increment-number) ) )
      
      
      (setq att-tag-name "DRAWING_NO_val")
      
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:EF_Filter_ss_set_V2_ ss_pre_filter_set_xx_ (list "Title Block_Under Ground_C1 v3" )))
        (setq ss_pre_filter_set_xx_ (TA:standard_list_croodinate_sorting ss_pre_filter_set_xx_ "X"))
      ;
      ;preloop_and_while
        (setq ss_pre_filter_set_xx_i 0)
        (while (< ss_pre_filter_set_xx_i (length ss_pre_filter_set_xx_))
          (setq ss_pre_filter_set_xx_ename_ (car (nth  ss_pre_filter_set_xx_i ss_pre_filter_set_xx_)))
          (setq ss_pre_filter_set_xx_obj_ (vlax-ename->vla-object  ss_pre_filter_set_xx_ename_))
          (setq ss_pre_filter_set_xx_obj_att (LM:vl-setattributevalue ss_pre_filter_set_xx_obj_ att-tag-name (strcat prefix-name  midfix (TA:prefix_value_00 starting_increment-number) )))
          (setq starting_increment-number (+ starting_increment-number 1))
          (setq ss_pre_filter_set_xx_i (+ ss_pre_filter_set_xx_i 1))
        )
      ;
    )
  ;
  ;UNDO FUNC
    (defun _StartUndo ( doc ) (_EndUndo doc)
      (if (= doc nil)
        (progn
          (setq doc (vla-get-ActiveDocument (vlax-get-Acad-Object)))
        )
      )
      (vla-StartUndoMark doc)
    )
  
    (defun _EndUndo ( doc )
      (if (= doc nil)
        (progn
          (setq doc (vla-get-ActiveDocument (vlax-get-Acad-Object)))
        )
      )
      (if (= 8 (logand 8 (getvar 'UNDOCTL)))
        (vla-EndUndoMark doc)
      )
    )
    
  ;
  ;check-detecty FUNC
    (defun c:Check_overlap_object_COBJ_ (/ *error*
                                    TA:COBJ-effectivename
                                    TA:COBJ-ename+insertionpoint
                                    ss_pre_filter_set_xx_
                                    ss_pre_filter_set_xx_i
                                    ss_pre_filter_set_xx_count_
                                    ss_pre_filter_set_xx_ename_
                                    ss_pre_filter_set_xx_obj_
                                    tolerance_dist_
                                    EFNAME_
                                    EFNAME_obj_
                                    EFNAME_MAIN_
                                    cancel_
                                    sum_list
                                    sum_list_
                                    sum_list_i
                                    sum_list_count_
                                    sum_list_obj_ins_
                                    check_list_
                                    check_list_scan_
                                    check_duplicate_
                                    check_final_
                                    newssset_
                                    percent
                                 )
      ;Note By Code_Developer
      ;This command is designed to work exclusively with a Block Object
      ;The principle of the code is to find blocks with the same effective name
      ;Duplicate checking uses insertion-point distance, not geometry intersection
      ;Select extra blocks and keep one representative for each checked location
      ;Fully command must have sub-functions with names starting with TA: or LM:
      ;
      ;

      ;sub_function_ effective block name
        (defun TA:COBJ-effectivename (obj)
          (if (vlax-property-available-p obj 'EffectiveName)
            (vla-get-effectivename obj)
            (vla-get-name obj)
          )
        )
      ;
      ;sub_function_ entity name and WCS insertion point
        (defun TA:COBJ-ename+insertionpoint (obj)
          (list
            (vlax-vla-object->ename obj)
            (vlax-safearray->list (vlax-variant-value (vla-get-insertionpoint obj)))
          )
        )
      ;
      ;error_handler_
        (defun *error* (msg)
          (if
            (and msg (not (wcmatch (strcase msg) "*CANCEL*,*QUIT*,*BREAK*")))
            (princ (strcat "\nError: " msg))
          )
          (princ)
        )
        (vl-load-com)
      ;
      ;selection_set_for_fillter_blk_name
        (if ;pre_select_ssget_or_post_select_ssget
          (not
            (setq ss_pre_filter_set_xx_ (ssget "_I"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (setq ss_pre_filter_set_xx_ (ssget
                                            (list
                                              (cons 0 "INSERT") ;type of object
                                            )
                                      )
          )
        )
      ;
      (if ss_pre_filter_set_xx_
        (progn
          ;user_input_
            (if
              (not
                (and
                  (numberp *TA:COBJ-tolerance-dist_*)
                  (> *TA:COBJ-tolerance-dist_* 0.0)
                )
              )
              (setq *TA:COBJ-tolerance-dist_* 0.001)
            )
            (initget 6) ;reject zero and negative distances; allow Enter
            (setq tolerance_dist_
              (cond
                ((getdist (strcat "\nSpecify tolerance_dist_ <"
                                  (rtos *TA:COBJ-tolerance-dist_* 2 6)
                                  "> : "
                          )
                 )
                )
                (*TA:COBJ-tolerance-dist_*)
              )
            )
            (setq *TA:COBJ-tolerance-dist_* tolerance_dist_)
            ;while_select_block_on_condition_
              (setq EFNAME_MAIN_ nil)
              (setq cancel_ nil)
              (while (and (null EFNAME_MAIN_) (not cancel_))
                (setq EFNAME_ (car (entsel "\nSpecify EFNAME Object <cancel>: ")))
                (cond
                  ((null EFNAME_)
                    (setq cancel_ T)
                  )
                  ((= (vla-get-objectname
                        (setq EFNAME_obj_ (vlax-ename->vla-object EFNAME_))
                      )
                      "AcDbBlockReference"
                   )
                    (setq EFNAME_MAIN_ (TA:COBJ-effectivename EFNAME_obj_))
                  )
                  (T
                    (alert "Object invalid Please try again")
                  )
                )
              )
            ;
          ;
          (if (not cancel_)
            (progn
              ;preloop_and_while ;get_data_process_for_fillter_blk_name
                (setq ss_pre_filter_set_xx_i 0)
                (setq ss_pre_filter_set_xx_count_ (sslength ss_pre_filter_set_xx_))
                (setq sum_list_ ())
                (while (< ss_pre_filter_set_xx_i ss_pre_filter_set_xx_count_)
                  (setq ss_pre_filter_set_xx_ename_ (ssname ss_pre_filter_set_xx_ (float ss_pre_filter_set_xx_i)))
                  (setq ss_pre_filter_set_xx_obj_ (vlax-ename->vla-object ss_pre_filter_set_xx_ename_))
                  (if (= (strcase EFNAME_MAIN_) (strcase (TA:COBJ-effectivename ss_pre_filter_set_xx_obj_)))
                    (progn
                      (setq sum_list (TA:COBJ-ename+insertionpoint ss_pre_filter_set_xx_obj_))
                      (setq sum_list_ (cons sum_list sum_list_))
                    )
                  )
                  (setq ss_pre_filter_set_xx_i (+ ss_pre_filter_set_xx_i 1))
                  ;screen process
                    (setq percent (fix (* (/ (float ss_pre_filter_set_xx_i) ss_pre_filter_set_xx_count_) 100)))
                    (princ (strcat "tranfering for_fillter_blk_name " (rtos ss_pre_filter_set_xx_i 2 0) "/" (rtos ss_pre_filter_set_xx_count_ 2 0) " (" (rtos percent 2 0) "%" ")" "\n"))
                    (textscr)
                  ;
                )
                (setq sum_list_ (reverse sum_list_)) ;preserve selection-set order
              ;
              ;preloop_and_while for_filter overlapped object
                (setq sum_list_i 0)
                (setq sum_list_count_ (length sum_list_))
                (setq check_list_ ()) ;representatives that will be kept
                (setq newssset_ (ssadd)) ;extra blocks that will be selected
                (foreach sum_list_obj_ins_ sum_list_
                  (setq check_duplicate_ nil)
                  (setq check_list_scan_ check_list_)
                  (while (and check_list_scan_ (not check_duplicate_))
                    (if
                      (< (distance (cadr sum_list_obj_ins_)
                                   (cadr (car check_list_scan_))
                         )
                         tolerance_dist_
                      )
                      (setq check_duplicate_ T)
                    )
                    (setq check_list_scan_ (cdr check_list_scan_))
                  )
                  (if check_duplicate_
                    (setq newssset_ (ssadd (car sum_list_obj_ins_) newssset_))
                    (setq check_list_ (cons sum_list_obj_ins_ check_list_))
                  )
                  (setq sum_list_i (+ sum_list_i 1))
                  ;screen process
                    (setq percent (fix (* (/ (float sum_list_i) sum_list_count_) 100)))
                    (princ (strcat "tranfering overlapped object " (rtos sum_list_i 2 0) "/" (rtos sum_list_count_ 2 0) " (" (rtos percent 2 0) "%" ")" "\n"))
                    (textscr)
                  ;
                )
              ;
              ;selection_process_ selection set for extra overlapp object
                (setq check_final_ newssset_)
                (if (> (sslength check_final_) 0)
                  (sssetfirst nil check_final_)
                  (sssetfirst nil nil)
                )
                (princ (strcat "\nBlock name: " EFNAME_MAIN_
                               " | Checked: " (itoa sum_list_count_)
                               " | Kept: " (itoa (length check_list_))
                               " | Duplicates selected: " (itoa (sslength check_final_))
                       )
                )
              ;
            )
            (princ "\nCommand cancelled.")
          )
        )
        (princ "\nNo block selected.")
      )
      (princ)
    ) 
    (defun c:Check_intersection_ckinsblk ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (if (not 
                (and
                  (or 
                    (= (- (fix (car ss_pre_filter_set_xx_obj_ins_)) (car ss_pre_filter_set_xx_obj_ins_) ) 0)
                    (= (abs (- (fix (car ss_pre_filter_set_xx_obj_ins_)) (car ss_pre_filter_set_xx_obj_ins_) )) 0.5)
                  )
                  (or 
                    (= (- (fix (cadr ss_pre_filter_set_xx_obj_ins_)) (cadr ss_pre_filter_set_xx_obj_ins_) ) 0)
                    (= (abs (- (fix (cadr ss_pre_filter_set_xx_obj_ins_)) (cadr ss_pre_filter_set_xx_obj_ins_) )) 0.5)
                  )
                  (or 
                    (= (- (fix (caddr ss_pre_filter_set_xx_obj_ins_)) (caddr ss_pre_filter_set_xx_obj_ins_) ) 0)
                    (= (abs (- (fix (caddr ss_pre_filter_set_xx_obj_ins_)) (caddr ss_pre_filter_set_xx_obj_ins_) )) 0.5)
                  )
                )
              )
            (progn
              (setq new_ss_pre_filter_set_xx_ (ssadd ss_pre_filter_set_xx_ename_ new_ss_pre_filter_set_xx_  ))
            )
          )
          (setq ss_pre_filter_set_xx_i (+ ss_pre_filter_set_xx_i 1))
        )
      ;
      (command "pselect"  new_ss_pre_filter_set_xx_ "" )
    )
    (defun c:Check_intersection_ckxinsblk ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (if (not 
                (and
                  (or 
                    (= (- (fix (car ss_pre_filter_set_xx_obj_ins_)) (car ss_pre_filter_set_xx_obj_ins_) ) 0)
                    (= (abs (- (fix (car ss_pre_filter_set_xx_obj_ins_)) (car ss_pre_filter_set_xx_obj_ins_) )) 0.5)
                  )
                  (or 
                    (= (- (fix (caddr ss_pre_filter_set_xx_obj_ins_)) (caddr ss_pre_filter_set_xx_obj_ins_) ) 0)
                    (= (abs (- (fix (caddr ss_pre_filter_set_xx_obj_ins_)) (caddr ss_pre_filter_set_xx_obj_ins_) )) 0.5)
                  )
                )
              )
            (progn
              (setq new_ss_pre_filter_set_xx_ (ssadd ss_pre_filter_set_xx_ename_ new_ss_pre_filter_set_xx_  ))
            )
          )
          (setq ss_pre_filter_set_xx_i (+ ss_pre_filter_set_xx_i 1))
        )
      ;
      (command "pselect"  new_ss_pre_filter_set_xx_ "" )
    )
    (defun c:Check_intersection_ckyinsblk ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (if (not 
                (and
                  (or 
                    (= (- (fix (cadr ss_pre_filter_set_xx_obj_ins_)) (cadr ss_pre_filter_set_xx_obj_ins_) ) 0)
                    (= (abs (- (fix (cadr ss_pre_filter_set_xx_obj_ins_)) (cadr ss_pre_filter_set_xx_obj_ins_) )) 0.5)
                  )
                  (or 
                    (= (- (fix (caddr ss_pre_filter_set_xx_obj_ins_)) (caddr ss_pre_filter_set_xx_obj_ins_) ) 0)
                    (= (abs (- (fix (caddr ss_pre_filter_set_xx_obj_ins_)) (caddr ss_pre_filter_set_xx_obj_ins_) )) 0.5)
                  )
                )
              )
            (progn
              (setq new_ss_pre_filter_set_xx_ (ssadd ss_pre_filter_set_xx_ename_ new_ss_pre_filter_set_xx_  ))
            )
          )
          (setq ss_pre_filter_set_xx_i (+ ss_pre_filter_set_xx_i 1))
        )
      ;
      (command "pselect"  new_ss_pre_filter_set_xx_ "" )
    )
    (defun c:insallsdec ()
      ;selection_set_for_fillter_blk_name
        (if  ;pre_select_ssget_or_post_select_ssget
          (=
            (setq ss_pre_filter_set_xx_ (ssget "i"
                                              (list
                                                (cons 0 "attdef,MTEXT,TEXT,INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "attdef,MTEXT,TEXT,INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_name (vla-get-objectname  ss_pre_filter_set_xx_obj_))
          (setq ss_pre_filter_set_xx_obj_ins_ (vlax-safearray->list (vlax-variant-value (vla-get-insertionpoint ss_pre_filter_set_xx_obj_))))
          
          (cond
            (;_case_1
               (and
                  (/= ss_pre_filter_set_xx_obj_name "AcDbAttributeDefinition")
                  (= (getvar "worlducs") 1)
               )
               (progn
                  (vla-put-insertionpoint 
                    ss_pre_filter_set_xx_obj_
                    (vlax-3d-point 
                      (TA:round-05 (car ss_pre_filter_set_xx_obj_ins_))
                      (TA:round-05 (cadr ss_pre_filter_set_xx_obj_ins_))
                      (TA:round-05 (caddr ss_pre_filter_set_xx_obj_ins_))
                    )
                  )
                  (princ "_case_1")
               )
            )
            (;_case_2
               (and
                  (= ss_pre_filter_set_xx_obj_name "AcDbAttributeDefinition")
                  (= (getvar "worlducs") 1)
               )
               (progn
                  (setq ss_pre_filter_set_xx_obj_insalmentpt_ (vlax-safearray->list (vlax-variant-value (vla-get-textalignmentpoint ss_pre_filter_set_xx_obj_))))
                  (vla-put-textalignmentpoint 
                    ss_pre_filter_set_xx_obj_
                    (vlax-3d-point 
                      (TA:round-05 (car ss_pre_filter_set_xx_obj_insalmentpt_))
                      (TA:round-05 (cadr ss_pre_filter_set_xx_obj_insalmentpt_))
                      (TA:round-05 (caddr ss_pre_filter_set_xx_obj_insalmentpt_))
                    )
                  )
                  (princ "_case_2")
               )
            )
            (;_case_3
              (and
                (/= ss_pre_filter_set_xx_obj_name "AcDbAttributeDefinition")
                (= (getvar "worlducs") 0)
              )
              (progn
                  (setq new_ss_pre_filter_set_xx_obj_ins_xyz (list 
                                                               (TA:round-10 (car (trans ss_pre_filter_set_xx_obj_ins_ 0 1)))
                                                               (TA:round-10 (cadr (trans ss_pre_filter_set_xx_obj_ins_ 0 1)))
                                                               (TA:round-10 (caddr (trans ss_pre_filter_set_xx_obj_ins_ 0 1)))
                                                             )
                  )
                  (setq new_ss_pre_filter_set_xx_obj_ins_ (trans new_ss_pre_filter_set_xx_obj_ins_xyz 1 0))
                  (vla-put-insertionpoint 
                    ss_pre_filter_set_xx_obj_
                    (vlax-3d-point 
                      (car new_ss_pre_filter_set_xx_obj_ins_)
                      (cadr new_ss_pre_filter_set_xx_obj_ins_)
                      0 ;(caddr new_ss_pre_filter_set_xx_obj_ins_)
                    )
                  )
                  (princ "_case_3")
               )
            )

          )
          
          
          (setq ss_pre_filter_set_xx_i (+ ss_pre_filter_set_xx_i 1))
        )
      ;
      (command "pselect"  new_ss_pre_filter_set_xx_ "" )
    )
    (defun c:insxdec ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (vla-put-insertionpoint 
            ss_pre_filter_set_xx_obj_
            (vlax-3d-point 
              (TA:round-05 (car ss_pre_filter_set_xx_obj_ins_))
              (cadr ss_pre_filter_set_xx_obj_ins_)
              (TA:round-05 (caddr ss_pre_filter_set_xx_obj_ins_))
            )
          )
          
          (setq ss_pre_filter_set_xx_i (+ ss_pre_filter_set_xx_i 1))
        )
      ;
      (command "pselect"  new_ss_pre_filter_set_xx_ "" )
    )
    (defun c:insx1500 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (round-1500 (car (trans ss_pre_filter_set_xx_obj_ins_ 0 1) ) )
                                    (cadr (trans ss_pre_filter_set_xx_obj_ins_ 0 1))
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (round-1500  (car ss_pre_filter_set_xx_obj_ins_))
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  new_ss_pre_filter_set_xx_ "" )
    )
    (defun c:insx00 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (vla-put-insertionpoint 
            ss_pre_filter_set_xx_obj_
            (if (= (getvar "worlducs") 0)
              (progn
                  (setq 1st_trans (list 
                                    (LM:round (car (trans ss_pre_filter_set_xx_obj_ins_ 0 1) ) )
                                    (cadr (trans ss_pre_filter_set_xx_obj_ins_ 0 1))
                                    (LM:round (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (LM:round  (car ss_pre_filter_set_xx_obj_ins_))
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insy00 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (car (trans ss_pre_filter_set_xx_obj_ins_ 0 1) )
                                    (LM:round (cadr (trans ss_pre_filter_set_xx_obj_ins_ 0 1)))
                                    (LM:round (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (car ss_pre_filter_set_xx_obj_ins_)
                (LM:round(cadr ss_pre_filter_set_xx_obj_ins_))
                (LM:round (caddr ss_pre_filter_set_xx_obj_ins_))
              )
            )
            
          )
          
          (setq ss_pre_filter_set_xx_i (+ ss_pre_filter_set_xx_i 1))
        )
      ;
      (command "pselect"  ss_pre_filter_set_xx_ "" )
    )
    
    (defun c:insx300 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (round-300 (car (trans ss_pre_filter_set_xx_obj_ins_ 0 1) ) )
                                    (round-300 (cadr (trans ss_pre_filter_set_xx_obj_ins_ 0 1) ) )
                                    (caddr (trans ss_pre_filter_set_xx_obj_ins_ 0 1) )
                                  )
                  )
                  (vlax-3d-point 
                    (car (trans 1st_trans 1 0))
                    (cadr (trans 1st_trans 1 0))
                    0
                  )
                
              )
              (vlax-3d-point 
                (round-300  (car ss_pre_filter_set_xx_obj_ins_))
                (round-300 (cadr ss_pre_filter_set_xx_obj_ins_))
                (caddr ss_pre_filter_set_xx_obj_ins_)
              )
            )
            
          )
          
          (setq ss_pre_filter_set_xx_i (+ ss_pre_filter_set_xx_i 1))
        )
      ;
      (command "pselect"  new_ss_pre_filter_set_xx_ "" )
    )
    (defun c:insx150 ()
      
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) 150 )
                                    (cadr (trans ss_pre_filter_set_xx_obj_ins_ 0 1) )
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (TA:round-number (car ss_pre_filter_set_xx_obj_ins_) 150 )
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insx400 ()
      
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) 400 )
                                    (TA:round-number (cadr (trans ss_pre_filter_set_xx_obj_ins_ 0 1) ) 400 )
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (TA:round-number (car ss_pre_filter_set_xx_obj_ins_) 400 )
                (TA:round-number (cadr ss_pre_filter_set_xx_obj_ins_) 400 )
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insxxx ()

      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq x_increment_ (cond ( (getint (strcat "\nspecify get move to point\n<" (rtos (setq x_increment_ (cond (x_increment_) (0) ) ) ) "> : " ) ) ) (x_increment_) ) )
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) x_increment_ )
                                    (cadr (trans ss_pre_filter_set_xx_obj_ins_ 0 1) )
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (TA:round-number (car ss_pre_filter_set_xx_obj_ins_) 400 )
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insX0400 ()
      ;selection_set_for_fillter_blk_name
        (if  ;pre_select_ssget_or_post_select_ssget
          (=
            (setq ss_pre_filter_set_xx_ (ssget "i"
                                              (list
                                                (cons 0 "INSERT") ;type of object
                                                (cons 8 "008 - LIGHT_DN_MAIN*")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                (cons 8 "008 - LIGHT_DN_MAIN*")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    
                                    (TA:round-number (car (trans ss_pre_filter_set_xx_obj_ins_ 0 1) ) 400 )
                                    0; (TA:round-number  (cadr (trans ss_pre_filter_set_xx_obj_ins_ 0 1) ) 0)
                                    0
                                  )
                  )
                  (vlax-3d-point 
                    (car (trans 1st_trans 1 0))
                    (cadr (trans 1st_trans 1 0))
                    0
                  )
                
              )
              (vlax-3d-point 
                (TA:round-05 (car ss_pre_filter_set_xx_obj_ins_)  )
                (TA:round-number (cadr ss_pre_filter_set_xx_obj_ins_) 400 )
                0
              )
            )
            
          )
          
          (setq ss_pre_filter_set_xx_i (+ ss_pre_filter_set_xx_i 1))
        )
      ;
      (command "pselect"  ss_pre_filter_set_xx_ "" )
    )
    (defun c:insDL400 ()
      ;selection_set_for_fillter_blk_name
        (if  ;pre_select_ssget_or_post_select_ssget
          (=
            (setq ss_pre_filter_set_xx_ (ssget "i"
                                              (list
                                                (cons 0 "INSERT") ;type of object
                                                (cons 8 "008 - LIGHT_DN_MAIN*")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                (cons 8 "008 - LIGHT_DN_MAIN*")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    
                                    (TA:round-number (car (trans ss_pre_filter_set_xx_obj_ins_ 0 1) ) 400 )
                                    (if (< (cadr (trans ss_pre_filter_set_xx_obj_ins_ 0 1) ) 0)
                                      (progn
                                        -325
                                      )
                                      325
                                    )
                                    0
                                  )
                  )
                  (vlax-3d-point 
                    (car (trans 1st_trans 1 0))
                    (cadr (trans 1st_trans 1 0))
                    0
                  )
                
              )
              (vlax-3d-point 
                (TA:round-05 (car ss_pre_filter_set_xx_obj_ins_)  )
                (TA:round-number (cadr ss_pre_filter_set_xx_obj_ins_) 400 )
                0
              )
            )
            
          )
          
          (setq ss_pre_filter_set_xx_i (+ ss_pre_filter_set_xx_i 1))
        )
      ;
      (command "pselect"  ss_pre_filter_set_xx_ "" )
    )
    
    (defun c:insx1750 ()
      ;selection_set_for_fillter_blk_name
        (if  ;pre_select_ssget_or_post_select_ssget
          (=
            (setq ss_pre_filter_set_xx_ (ssget "i"
                                              (list
                                                (cons 0 "INSERT") ;type of object
                                                (cons 8 "008 - LIGHT_FLUORESCENT*,008 - AIR_MASK*,FRAMING_CC-01*")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                (cons 8 "008 - LIGHT_FLUORESCENT*,008 - AIR_MASK*,FRAMING_CC-01*")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (round-1750 (car (trans ss_pre_filter_set_xx_obj_ins_ 0 1) ) )
                                    (cadr (trans ss_pre_filter_set_xx_obj_ins_ 0 1))
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (round-1750  (car ss_pre_filter_set_xx_obj_ins_))
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insx1200 ()
      ;selection_set_for_fillter_blk_name
        (if  ;pre_select_ssget_or_post_select_ssget
          (=
            (setq ss_pre_filter_set_xx_ (ssget "i"
                                              (list
                                                (cons 0 "INSERT") ;type of object
                                                ; (cons 8 "008 - LIGHT_FLUORESCENT*,008 - AIR_MASK*,FRAMING_CC-01*")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "008 - LIGHT_FLUORESCENT*,008 - AIR_MASK*,FRAMING_CC-01*")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) 1200)
                                    (cadr (trans ss_pre_filter_set_xx_obj_ins_ 0 1))
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (round-1750  (car ss_pre_filter_set_xx_obj_ins_))
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insx ()
      ;selection_set_for_fillter_blk_name
        (if  ;pre_select_ssget_or_post_select_ssget
          (=
            (setq ss_pre_filter_set_xx_ (ssget "i"
                                              (list
                                                (cons 0 "INSERT") ;type of object
                                                (cons 8 "008 - LIGHT_FLUORESCENT*,008 - AIR_MASK*")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                (cons 8 "008 - LIGHT_FLUORESCENT*,008 - AIR_MASK*")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) 3000)
                                    (cadr (trans ss_pre_filter_set_xx_obj_ins_ 0 1))
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (round-1750  (car ss_pre_filter_set_xx_obj_ins_))
                (cadr ss_pre_filter_set_xx_obj_ins_)
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insy1750 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (car (trans ss_pre_filter_set_xx_obj_ins_ 0 1) )
                                    (round-1750 (cadr (trans ss_pre_filter_set_xx_obj_ins_ 0 1)) )
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (car ss_pre_filter_set_xx_obj_ins_)
                (round-1750 (cadr ss_pre_filter_set_xx_obj_ins_))
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insx1875 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) 1875 )
                                    (TA:round-number (cadr (trans ss_pre_filter_set_xx_obj_ins_ 0 1) ) 1875 )
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (TA:round-number (car ss_pre_filter_set_xx_obj_ins_) 1875 )
                (TA:round-number (cadr ss_pre_filter_set_xx_obj_ins_) 1875 )
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insy10 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          ) 
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (vla-put-insertionpoint 
            ss_pre_filter_set_xx_obj_
            (if (= (getvar "worlducs") 0)
              (progn
                  (setq 1st_trans (list 
                                    (TA:round-number (car (trans ss_pre_filter_set_xx_obj_ins_ 0 1) ) 1 )
                                    (TA:round-number (cadr (trans ss_pre_filter_set_xx_obj_ins_ 0 1) ) 10 )
                                    (TA:round-05 (caddr (trans ss_pre_filter_set_xx_obj_ins_ 0 1) ) )
                                  )
                  )
                  (vlax-3d-point 
                    (car (trans 1st_trans 1 0))
                    (cadr (trans 1st_trans 1 0))
                    0
                  )
                
              )
              (vlax-3d-point 
                (TA:round-number (car ss_pre_filter_set_xx_obj_ins_) 1 )
                (TA:round-number (cadr ss_pre_filter_set_xx_obj_ins_) 10 )
                (TA:round-05 (caddr ss_pre_filter_set_xx_obj_ins_))
              )
            )
            
          )
          
          (setq ss_pre_filter_set_xx_i (+ ss_pre_filter_set_xx_i 1))
        )
      ;
      (command "pselect"  ss_pre_filter_set_xx_ "" )
    )
    (defun c:insydec ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (vla-put-insertionpoint 
            ss_pre_filter_set_xx_obj_
            (vlax-3d-point 
              (car ss_pre_filter_set_xx_obj_ins_)
              (TA:round-05 (cadr ss_pre_filter_set_xx_obj_ins_))
              (TA:round-05 (caddr ss_pre_filter_set_xx_obj_ins_))
            )
          )
          (setq ss_pre_filter_set_xx_i (+ ss_pre_filter_set_xx_i 1))
        )
      ;
      (command "pselect"  new_ss_pre_filter_set_xx_ "" )
    )
  ;
  ;Common_commmand 
    (defun c:stamp_layer_to_model ()
      ;user_inpput for specify point
        (setq mk_point (getpoint "specify point"))
        (setq mk_point_y_ 0)
        (setq rotation_val (angtof "45" ))
        (setq layers_list_ (acad_strlsort (TA:get_name_layer_in_drawing)))
        (setq layers_list_i 0)
        (while (< layers_list_i (length layers_list_))
          (setq layers_list_name (nth layers_list_i layers_list_))
          
          (setq mk_point_xyz (vlax-3d-point 
                              (list 
                                (setq mk_point_x (car mk_point))
                                (setq mk_point_y (+ (cadr mk_point) mk_point_y_))
                                (setq mk_point_z (caddr mk_point))
                              )
                            )
          )
          
          (create-text-vla mk_point_xyz layers_list_name 5 rotation_val)
          (vla-put-layer (vlax-ename->vla-object (entlast)) layers_list_name  )
          (vla-put-color (vlax-ename->vla-object (entlast)) 256)
          (setq mk_point_y_ (+ mk_point_y_ -20))
          (setq layers_list_i (+ layers_list_i 1))
          
        )

    )
    (defun c:round_up_down_insertion_point_REINS ()
      ;selection_set
        (if  ;pre_select_ssget_or_post_select_ssget
          (= 
            (setq ss_pre_filter_set_xx (ssget "I" 
                                              (list 
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx (ssget 
                                          (list 
                                            (cons 0 "INSERT") ;type of object
                                            ; (cons 8 "000 - GRID")   ;kind of layer
                                            ; (cons 2 "000-GRIDLINE_DYN")       ;kind of nameblock
                                            ; (cons 62 1)           ;kind of color call sign with color code index
                                          )
                                        )
            )
          )
          (sslength ss_pre_filter_set_xx)
        )
      ;
      ;get_efname_
        (setq blk_name_ (LM:effectivename (vlax-ename->vla-object (car (entsel)))))
      ;
      ;ssget_filtter
        (setq ss_prop_filter_ (TA:Prop_Filter_ss_set_ ss_pre_filter_set_xx "effectivename" blk_name_))
      ;
      ;preloop_and_while_rework_inspoint
        (setq ss_prop_filter_i 0)
        (while  (< ss_prop_filter_i (sslength ss_prop_filter_))
          (setq ss_prop_filter_ename_ (ssname ss_prop_filter_ ss_prop_filter_i))
          (setq ss_prop_filter_obj_ (vlax-ename->vla-object ss_prop_filter_ename_))
          (setq ss_prop_filter_obj_ins_ (TA:ename+vla-get-insertionpoint ss_prop_filter_obj_))
          
          ;re_location_inspt_
            ;get_data
              (setq new_input_ins_ (list
                                        (setq ss_prop_filter_obj_ins_x (LM:round (car (nth 1 ss_prop_filter_obj_ins_))))
                                        (setq ss_prop_filter_obj_ins_y (LM:round (cadr (nth 1 ss_prop_filter_obj_ins_))))
                                        (setq ss_prop_filter_obj_ins_z (LM:round (caddr (nth 1 ss_prop_filter_obj_ins_))))                             
                                      )
              )
            ;
            (vla-put-insertionpoint ss_prop_filter_obj_ (vlax-3d-point new_input_ins_))
          ;
          (setq ss_prop_filter_i (+ ss_prop_filter_i 1))
        )
      ;
    )
    (defun c:make_boudary_line_MKBOL ()
      ;get_osmode_process
        (setq getold_osmode_ (getvar "osmode"))
        (setq zero_osmode_ (setvar "osmode" 0))
      ;
      ;user_input
        (setq ref_pline_or_block_ (car (entsel "specify PLINE OR BLOCK OBJECT" )))
      ;
      ;MAIN_IDEA_COMMAND_
        (setq lower_upper_inspoint_ (TA:Find_boundary_line_ ref_pline_or_block_))
        (command "rectangle" (car lower_upper_inspoint_) (cadr lower_upper_inspoint_))
      ;  
      ;Change_Color_process
        (setq new_obj_ (vlax-ename->vla-object (entlast)))
        (setq new_obj_input_color_ (vla-put-color new_obj_ 250))
      ;
      ;return_osmode_process_
        (setq return_osmode_ (setvar "osmode" getold_osmode_))
      ;
    )
    (defun c:STAMP_START_POINT_STP_ ()
      
      ;Stamp_ dynamic block "000SYM-START_POINT_" /w RECTANGLE_BLOCK
      (setvar "osmode" 0)
      (setq main_rec_ename_ (car (entsel "specify Object")))
      (setq rec_point_ (TA:find_center main_rec_ename_ ))
      (command "insert" "000SYM-START_POINT_" rec_point_ 0.1 0 )
      (setvar "osmode" 1215)
    )
    (defun c:relocation_rectangle_vertex_REVX ()
        (setq rec_ename_ (car (entsel "specify Object")))
        (setq rec_obj_ (vlax-ename->vla-object rec_ename_))
      
        ; (if (and
        ;       (= (vla-get-objectname rec_obj_) "AcDbPolyline")
        ;     )
        ;   (progn
        ;     (thenexpr)
        ;   )
        ; )
        (setq rec_obj_getboundingbox (vla-getboundingbox rec_obj_ 'min_ 'max_)) 
        (setq rec_min_ (vlax-safearray->list min_)) 
        (setq rec_max_ (vlax-safearray->list max_)) 
        
      (command "rectangle" rec_min_ rec_max_ )
      (vla-delete   rec_obj_ )
      
      
    )
    (defun c:make_thickness_sheet_THS ()
      (_startundo doc)
      ;user_input_
        (setq 2dblank_ename_ (car (entsel "specify Object")))
        
        (setq user_input_thickness_ (cond ( (getreal (strcat "\nspecify_height blank size<" (rtos (setq user_input_thickness_ (cond (user_input_thickness_) (1.0) ) ) ) "> : " ) ) ) (user_input_thickness_) ) )
        (setq user_input_offset_ (cond ( (getreal (strcat "\n\n1 = Max 0 = Min [1/0] <" (rtos (setq user_input_offset_ (cond (user_input_offset_) (1.0) ) ) ) "> : " ) ) ) (user_input_offset_) ) )
        (cond
          (;user_input_offset_case_1
            (and
                (= user_input_offset_ 1)
            )
            (progn
              (setq user_input_offset_val "max")
              (princ "user_input_offset_case_1")
            )
          )
          (;user_input_offset_case_2
            (and
                (= user_input_offset_ 0)
            )
            (progn
              (setq user_input_offset_val "min")
              (princ "user_input_offset_case_2")
            )
          )
        )
      ;
      ;new_ssget_process_
        (setq new_ssget_ ())
        (setq new_ssget_ (ssadd))
        (setq new_ssget_ (ssadd  2dblank_ename_ new_ssget_))
        (sslength new_ssget_)
      ;
      ;get_data_
        (setq r2dblank_obj_ (vlax-ename->vla-object 2dblank_ename_))
        (setq 2dblank_objname_  (vla-get-objectname r2dblank_obj_))
      
        (setq vertex_list_  (TA:Get_Pline_vertext_ins_point_ 2dblank_ename_))
        (setq 2dblank_len_val_ (TA:get_vertex_len_ 2dblank_ename_))
      ;
      ;offset_process

        (TA:Offset_Pline_multi_vertex_ 2dblank_ename_ user_input_thickness_ user_input_offset_val)
        (setq new_line_ (entlast))
        (setq new_line_vertex_list_  (TA:Get_Pline_vertext_ins_point_ new_line_))
        (setq new_ssget_ (ssadd  new_line_ new_ssget_))
        (sslength new_ssget_)
      ;
      ;create_start_line_process
        (setq startline_
              (list
                  ; (nth 0 (cadr vertex_list_ ))
                  ; (nth 0 (cadr new_line_vertex_list_ ))
                  (if (= (getvar "worlducs") 0)(progn (trans (nth 0 (cadr vertex_list_ )) 0 1)) (nth 0 (cadr vertex_list_ )) )
                  (if (= (getvar "worlducs") 0)(progn (trans (nth 0 (cadr new_line_vertex_list_ )) 0 1)) (nth 0 (cadr new_line_vertex_list_ )) )
              )
        )
        (if (= (getvar "worlducs") 0)(progn (trans ss_pre_filter_set_xx_obj_ins_ 0 1)) ss_pre_filter_set_xx_obj_ins_ )
        (create-pline startline_ )
        (setq new_line_ (entlast))
        (setq new_ssget_ (ssadd  new_line_ new_ssget_))
        (sslength new_ssget_)
      
        (setq vertex_list_i (- (length (cadr vertex_list_ ) ) 1))
        (setq endline_
              (list
                  ; (nth vertex_list_i (cadr vertex_list_ ))                  
                  ; (nth vertex_list_i (cadr new_line_vertex_list_ ))
                  (if (= (getvar "worlducs") 0)(progn (trans (nth vertex_list_i (cadr vertex_list_ )) 0 1)) (nth vertex_list_i (cadr vertex_list_ )) )
                  (if (= (getvar "worlducs") 0)(progn (trans (nth vertex_list_i (cadr new_line_vertex_list_ )) 0 1)) (nth vertex_list_i (cadr new_line_vertex_list_ )) )
              )
        )

        (create-pline endline_ )
        (setq new_line_ (entlast))
        (setq new_ssget_ (ssadd  new_line_ new_ssget_))
        (sslength new_ssget_)
      ;
      ;joint_all_selection_set_process
        (command "pedit"  "m" new_ssget_ "" "j" "" "" )
      ;
      (_endUndo doc)
    )
    (defun c:rotate_counter_clockwise_rccw ()
      ;Note By Code_Developer
      ;The principle of Codework is designed for block objects, where the commands
      ;will rotale block object only
      ;
      ;sub-FUNC
        (defun TA:ModifyRotation (Ex_rotation New_rotation)
          ;Note By Code_Developer
          ;The principle of this code is designed to modify the angle value, allowing for both increments and decrements based on a reference number.
          ;The reference number used must be a value representing degrees, ranging from 1 to 360.
          ;The number added or subtracted from the angle is calculated based on the number of degrees rotated, considering 1 full rotation as 360 degrees.
          ;
          (cond 
            ( ;normal_rotation_case_1
              (and 
                (>= New_rotation 0)
                (<= New_rotation 360)
              )
              (progn
                (princ "rotation_case_1\n")
                (setq new_rotaion_val_ (+ Ex_rotation New_rotation))
                (if (<= new_rotaion_val_ 360)
                  (progn
                    (setq new_rotaion_val_ (+ Ex_rotation New_rotation))
                  )
                  (setq new_rotaion_val_ (- (+ Ex_rotation New_rotation) 360))
                )
                
                
              )
            )
            (;multi_time_rotation_case_2
              (and 
                (> New_rotation 360)
              )
              (progn 
                (princ "rotation_case_2\n")
                (setq round_time_ (atoi (rtos (/ New_rotation 360) 2 0)))
                (setq round_time_val (* round_time_ 360))
                (setq new_rotaion_val_ (- New_rotation round_time_val))
                (if (> (+ Ex_rotation new_rotaion_val_ ) 360)
                (progn
                  (setq new_rotaion_val_ans_ (-  (+ Ex_rotation new_rotaion_val_ ) 360 ))
                )
                  (setq new_rotaion_val_ans_ (+ Ex_rotation new_rotaion_val_ ))
                )
                
              )
            )
            (;rotation_case_3
              (and 
                (<= New_rotation 0) 
              )
              (progn 
                (princ "rotation_case_3\n")
                (setq round_time_ (atoi (rtos (/ New_rotation 360) 2 0)))
                (setq round_time_val (* round_time_ 360))
                (setq new_rotaion_val_ (- New_rotation round_time_val))
                (setq Ex_rotation_val_ (+ Ex_rotation new_rotaion_val_))
                (if (< Ex_rotation_val_ 0)
                  (progn
                    (setq new_rotaion_val_ans_ (+ 360 Ex_rotation_val_))
                  )
                  (setq new_rotaion_val_ans_ Ex_rotation_val_ )
                )
                
              )
            )
            
          )
        )
      ;Exaample use
      ;no Example just use it !!!
      ;
      ;user_input_
        (initget "Yes No")
        (setq ss_ ;Detect the variable's result in case of a function error
          (vl-catch-all-apply 
            (function 
              (lambda () 
                (setq DELETE_OBJ_ (not (eq "No" (getkword "\nKeep Existing point with object? [Yes/No] <Y>: "))))
              )
            )
          )
        )
        (if (or (= ss_ nil) (= (vl-prin1-to-string ss_) "#<%catch-all-apply-error%>")  )
          (progn
            ;selection_set_for_fillter_blk_name
              (if  ;pre_select_ssget_or_post_select_ssget
                (=
                  (setq ss_pre_filter_set_xx_ (ssget "i"
                                                    (list
                                                      (cons 0 "insert") ;type of object
                                                      ; (cons 8 "000 - GRID")   ;kind of layer
                                                      ; (cons 2 "000-GRID_LINE_DYN")       ;kind of nameblock
                                                      ; (cons 62 0)           ;kind of color call sign with color code index
                                                    )
                                              )
                  )
                  nil
                )
                (progn
                  (setq ss_pre_filter_set_xx_ (ssget 
                                                    (list
                                                      (cons 0 "insert") ;type of object
                                                      ; (cons 8 "000 - GRID")   ;kind of layer
                                                      ; (cons 2 "000-GRID_LINE_DYN")       ;kind of nameblock
                                                      ; (cons 62 0)           ;kind of color call sign with color code index
                                                    )
                                              )
                  )
                )
                (sslength ss_pre_filter_set_xx_)
              )
            ;
          )
          (setq ss_pre_filter_set_xx_ ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_hon_obj_ (vlax-ename->vla-object ss_pre_filter_set_xx_ename_))
          (setq ss_pre_filter_set_xx_hon_obj_ro_ (rad-to-deg (vla-get-rotation ss_pre_filter_set_xx_hon_obj_)))
          
          (vla-put-rotation ss_pre_filter_set_xx_hon_obj_ (deg-to-rad (TA:ModifyRotation ss_pre_filter_set_xx_hon_obj_ro_ -90)))
          
          (setq ss_pre_filter_set_xx_i (+ ss_pre_filter_set_xx_i 1))
        )
      ;)
    )
    (defun c:rotate_clockwise_rcw ()
      ;Note By Code_Developer
      ;The principle of Codework is designed for block objects, where the commands
      ;will rotale block object only
      ;
      ;
      ;sub-FUNC
        (defun TA:ModifyRotation (Ex_rotation New_rotation)
          ;Note By Code_Developer
          ;The principle of this code is designed to modify the angle value, allowing for both increments and decrements based on a reference number.
          ;The reference number used must be a value representing degrees, ranging from 1 to 360.
          ;The number added or subtracted from the angle is calculated based on the number of degrees rotated, considering 1 full rotation as 360 degrees.
          ;
          (cond 
            ( ;normal_rotation_case_1
              (and 
                (>= New_rotation 0)
                (<= New_rotation 360)
              )
              (progn
                (princ "rotation_case_1\n")
                (setq new_rotaion_val_ (+ Ex_rotation New_rotation))
                (if (<= new_rotaion_val_ 360)
                  (progn
                    (setq new_rotaion_val_ (+ Ex_rotation New_rotation))
                  )
                  (setq new_rotaion_val_ (- (+ Ex_rotation New_rotation) 360))
                )
                
                
              )
            )
            (;multi_time_rotation_case_2
              (and 
                (> New_rotation 360)
              )
              (progn 
                (princ "rotation_case_2\n")
                (setq round_time_ (atoi (rtos (/ New_rotation 360) 2 0)))
                (setq round_time_val (* round_time_ 360))
                (setq new_rotaion_val_ (- New_rotation round_time_val))
                (if (> (+ Ex_rotation new_rotaion_val_ ) 360)
                (progn
                  (setq new_rotaion_val_ans_ (-  (+ Ex_rotation new_rotaion_val_ ) 360 ))
                )
                  (setq new_rotaion_val_ans_ (+ Ex_rotation new_rotaion_val_ ))
                )
                
              )
            )
            (;rotation_case_3
              (and 
                (<= New_rotation 0) 
              )
              (progn 
                (princ "rotation_case_3\n")
                (setq round_time_ (atoi (rtos (/ New_rotation 360) 2 0)))
                (setq round_time_val (* round_time_ 360))
                (setq new_rotaion_val_ (- New_rotation round_time_val))
                (setq Ex_rotation_val_ (+ Ex_rotation new_rotaion_val_))
                (if (< Ex_rotation_val_ 0)
                  (progn
                    (setq new_rotaion_val_ans_ (+ 360 Ex_rotation_val_))
                  )
                  (setq new_rotaion_val_ans_ Ex_rotation_val_ )
                )
                
              )
            )
            
          )
        )
      ;
      ;Exaample use
      ;no Example just use it !!!
      ;
      ;user_input_
        (initget "Yes No")
        (setq ss_ ;Detect the variable's result in case of a function error
          (vl-catch-all-apply 
            (function 
              (lambda () 
                (setq DELETE_OBJ_ (not (eq "No" (getkword "\nKeep Existing point with object? [Yes/No] <N>: "))))
              )
            )
          )
        )
        (if (or (= ss_ nil) (= (vl-prin1-to-string ss_) "T")  )
          (progn
            ;selection_set_for_fillter_blk_name
              (if  ;pre_select_ssget_or_post_select_ssget
                (=
                  (setq ss_pre_filter_set_xx_ (ssget "i"
                                                    (list
                                                      (cons 0 "insert") ;type of object
                                                      ; (cons 8 "000 - GRID")   ;kind of layer
                                                      ; (cons 2 "000-GRID_LINE_DYN")       ;kind of nameblock
                                                      ; (cons 62 0)           ;kind of color call sign with color code index
                                                    )
                                              )
                  )
                  nil
                )
                (progn
                  (setq ss_pre_filter_set_xx_ (ssget 
                                                    (list
                                                      (cons 0 "insert") ;type of object
                                                      ; (cons 8 "000 - GRID")   ;kind of layer
                                                      ; (cons 2 "000-GRID_LINE_DYN")       ;kind of nameblock
                                                      ; (cons 62 0)           ;kind of color call sign with color code index
                                                    )
                                              )
                  )
                )
                (sslength ss_pre_filter_set_xx_)
              )
            ;
          )
          (setq ss_pre_filter_set_xx_ ss_pre_filter_set_xx_)
        )
      ;
      ;preloop_and_while
        (setq ss_pre_filter_set_xx_i 0)
        (while (and
                 (= (vl-catch-all-error-p ss_) nil)
                 (< ss_pre_filter_set_xx_i (sslength ss_pre_filter_set_xx_))
               )
          (setq ss_pre_filter_set_xx_ename_ (ssname ss_pre_filter_set_xx_ ss_pre_filter_set_xx_i))
          (setq ss_pre_filter_set_xx_hon_obj_ (vlax-ename->vla-object ss_pre_filter_set_xx_ename_))
          (setq ss_pre_filter_set_xx_hon_obj_ro_ (rad-to-deg (vla-get-rotation ss_pre_filter_set_xx_hon_obj_)))
          
          (vla-put-rotation ss_pre_filter_set_xx_hon_obj_ (deg-to-rad (TA:ModifyRotation ss_pre_filter_set_xx_hon_obj_ro_ 90)))
          
          (setq ss_pre_filter_set_xx_i (+ ss_pre_filter_set_xx_i 1))
        )
      ;)
      
    )
    (defun c:Centroid_rotate_cenro ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget ":s"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq blk_obj_ (vlax-ename->vla-object (ssname ss_pre_filter_set_xx_ 0)))
      (setq blk_obj_BOL-data_list (TA:get-visible-boundingbox blk_obj_))
      (vla-erase (vlax-ename->vla-object (entlast)))
      
      (setq blk_obj_BOL-centroid_ (append (TA:midpoint (car (nth 0 blk_obj_BOL-data_list)) (caddr (nth 0 blk_obj_BOL-data_list))) (list 0)) )
      (setq blk_obj_ro (vla-get-rotation blk_obj_))
      (command "rotate" (ssname ss_pre_filter_set_xx_ 0) "" blk_obj_BOL-centroid_  )
      
      (command "pselect"  (ssname ss_pre_filter_set_xx_ 0) "" )
    )
    (defun c:rotate_by_2_point_ro2point ()
      
      (setq pt1 (getpoint "specify point 1 "))
      (setq pt2 (getpoint "specify point 2 "))
      (setq blk_ename_ (car (entsel "specify Object")))
      (setq blk_obj_ (vlax-ename->vla-object blk_ename_))
      (if (= (getvar "worlducs") 1)
        (progn
          (setq angles (angle (trans pt1 1 0) (trans pt2 1 0) ) )
        )
        (setq angles (angle pt1 pt2 ) )
      )

      
      (vla-put-rotation blk_obj_ 
                        (angle 
                          (trans pt1 1 0)
                          (trans pt2 1 0)
                        )
      )
    )
    (defun c:copy_layer_text_CPLTEXT_ ()
      (setq layer_ename_ (car (entsel "specify Object")))
      (setq layer_obj_ (vlax-ename->vla-object layer_ename_))
      (TA:copytext->clipboard (vla-get-layer layer_obj_))
    )
    (defun c:Xmove ()
      (if 
        (= 
          (vl-catch-all-error-p 
            (vl-catch-all-apply 
              (function 
                (lambda () 
                  (setvar "osmode" 1215)
                  (setq PT_ref_ (getpoint "specify reference point"))
                )
              )
            )
          )
          nil
        )
        (progn 
          (setq target_move_ename_ (car (entsel "specify Object")))
          (setq target_move_obj_ (vlax-ename->vla-object target_move_ename_))
          (if (= (getvar "worlducs") 1)
            (progn
              (setq target_move_ref (trans (getpoint "specify target_move_ref point") 1 1))
              (setvar "osmode" 0)
              (vla-move target_move_obj_ (vlax-3d-point (trans target_move_ref 1 0)) (vlax-3d-point (trans (list (car PT_ref_) (cadr target_move_ref) 0 ) 1 0) ) )
            )
          )
          (if (= (getvar "worlducs") 0)
            (progn
              (setq target_move_ref (getpoint "specify target_move_ref point"))
              (setvar "osmode" 0)
              (vla-move target_move_obj_ (vlax-3d-point target_move_ref) (vlax-3d-point (list (car PT_ref_) (cadr target_move_ref) 0 ) ) )
            )
            
          )
          (setvar "osmode" 1215)
          ;add on command 
            (command "line" PT_ref_ (list (car target_move_ref) (cadr PT_ref_) 0 ) "")
            (command "pselect"  (entlast) "" )
            (if (or 
                  (= (rad-to-deg (vla-get-angle (vlax-ename->vla-object (entlast)))) 0)
                  (= (rad-to-deg (vla-get-angle (vlax-ename->vla-object (entlast)))) 90)
                  (= (rad-to-deg (vla-get-angle (vlax-ename->vla-object (entlast)))) 180)
                  (= (rad-to-deg (vla-get-angle (vlax-ename->vla-object (entlast)))) 270)
                )
              (progn
                (alert "line is straight")
                (vla-delete (vlax-ename->vla-object (entlast)))
              )
            )
          ;
        )
      )
    )
    (defun c:Ymove ()
      (if 
        (= 
          (vl-catch-all-error-p 
            (vl-catch-all-apply 
              (function 
                (lambda () 
                  (setvar "osmode" 1215)
                  (setq PT_ref_ (getpoint "specify reference point"))
                )
              )
            )
          )
          nil
        )
        (progn 
          (setq target_move_ename_ (car (entsel "specify Object")))
          (setq target_move_obj_ (vlax-ename->vla-object target_move_ename_))
          (if (= (getvar "worlducs") 1)
            (progn
              (setq target_move_ref (trans (getpoint "specify target_move_ref point") 1 1))
              (setvar "osmode" 0)
              (vla-move target_move_obj_ (vlax-3d-point (trans target_move_ref 1 0)) (vlax-3d-point (trans (list (car target_move_ref) (cadr PT_ref_) 0 ) 1 0) ) )
            )
          )
          (if (= (getvar "worlducs") 0)
            (progn
              (setq target_move_ref (getpoint "specify target_move_ref point"))
              (setvar "osmode" 0)
              (vla-move target_move_obj_ (vlax-3d-point target_move_ref) (vlax-3d-point (list (car target_move_ref) (cadr PT_ref_) 0 ) ) )
            )
            
          )
          (setvar "osmode" 1215)
          ;add on command 
            (command "line" PT_ref_ (list (car target_move_ref) (cadr PT_ref_) 0 ) "")
            (command "pselect"  (entlast) "" )
            (if (or 
                  (= (rad-to-deg (vla-get-angle (vlax-ename->vla-object (entlast)))) 0)
                  (= (rad-to-deg (vla-get-angle (vlax-ename->vla-object (entlast)))) 90)
                  (= (rad-to-deg (vla-get-angle (vlax-ename->vla-object (entlast)))) 180)
                  (= (rad-to-deg (vla-get-angle (vlax-ename->vla-object (entlast)))) 270)
                )
              (progn
                (alert "line is straight")
                (vla-delete (vlax-ename->vla-object (entlast)))
              )
            )
          ;
        )
      )
    )
    (defun c:ssXmove ()
      (setq PT_ref_ (getpoint "specify reference point"))
      ;selection_set_for_fillter_blk_name
        (if  ;pre_select_ssget_or_post_select_ssget
          (=
            (setq target_move_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq target_move_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength target_move_)
        )
      ;
      ;get_data_process_for_fillter_blk_name
      ;preloop_and_while
        (setq target_move_i 0)
        (while (< target_move_i (sslength target_move_))
          (setq target_move_ename_ (ssname target_move_ target_move_i))
          (setq target_move_obj_ (vlax-ename->vla-object  target_move_ename_))
          (command "pselect"  target_move_ename_ "" )
          (setq target_move_ref (getpoint "specify target_move_ref point"))
          (setvar "osmode" 0)
          (vla-move target_move_obj_ (vlax-3d-point target_move_ref) (vlax-3d-point (list (car PT_ref_) (cadr target_move_ref) 0 ) ) )
          (setvar "osmode" 1215)
          (setq target_move_i (+ target_move_i 1))
        )
      ;
      (command "pselect"  target_move_ "" )
    )
    (defun c:ssYmove ()
      (setq PT_ref_ (getpoint "specify reference point"))
      ;selection_set_for_fillter_blk_name
        (if  ;pre_select_ssget_or_post_select_ssget
          (= 
            (setq target_move_ (ssget "i" 
                                      (list 
                                        (cons 0 "INSERT") ;type of object
                                        ; (cons 8 "000 - GRID")   ;kind of layer
                                        ; (cons 2 "000-GRID_LINE_DYN")       ;kind of nameblock
                                        ; (cons 62 1)           ;kind of color call sign with color code index
                                      )
                               )
            )
            nil
          )
          (progn 
            (setq target_move_ (ssget 
                                 (list 
                                   (cons 0 "INSERT") ;type of object
                                   ; (cons 8 "000 - GRID")   ;kind of layer
                                   ; (cons 2 "000-GRID_LINE_DYN")       ;kind of nameblock
                                   ; (cons 62 1)           ;kind of color call sign with color code index
                                 )
                               )
            )
          )
          (sslength target_move_)
        )
      ;
      ;preloop_and_while
        (setq  target_move_i 0)
        (while (<  target_move_i (sslength  target_move_))
          (setq  target_move_ename_ (ssname  target_move_  target_move_i))
          (setq target_move_obj_ (vlax-ename->vla-object target_move_ename_))
          (command "pselect"  target_move_ename_ "" )
          (setq target_move_ref (getpoint "specify target_move_ref point"))
          (setvar "osmode" 0)
          (vla-move target_move_obj_ (vlax-3d-point target_move_ref) (vlax-3d-point (list (car target_move_ref) (cadr PT_ref_) 0 ) ) )
          (setvar "osmode" 1215)
      
          (setq  target_move_i (+  target_move_i 1))
        )
      ;
      (command "pselect"  target_move_ "" )

    )
    (defun c:txmayy ()
      (setq text_ename_ (car (entsel "specify ref Object")))
      (setq text_obj_ (vlax-ename->vla-object text_ename_))
      (setq text_obj_ins_ (vlax-safearray->list (vlax-variant-value (vla-get-insertionpoint text_obj_))))
      
      (setq text1_ename_ (car (entsel "specify ref Object")))
      (setq text1_obj_ (vlax-ename->vla-object text1_ename_))
      (setq text1_obj_ins_ (vlax-safearray->list (vlax-variant-value (vla-get-insertionpoint text1_obj_))))
      (setq text1_obj_ins_ (vla-put-insertionpoint text1_obj_ 
                                                   (vlax-3d-point 
                                                     (list (car text1_obj_ins_) 
                                                           (cadr text_obj_ins_)
                                                           (caddr text1_obj_ins_)
                                                     )
                                                   )
                           )
      )
    )
    (defun c:centroid_move_cenmo ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setvar "osmode" 0)
        (setq ss_pre_filter_set_xx_centroid_ins_ (TA:ss_vla-getboundingbox ss_pre_filter_set_xx_ ))
        (setq ss_pre_filter_set_xx_centroid_mid_ (TA:midpoint (car ss_pre_filter_set_xx_centroid_ins_) (cadr ss_pre_filter_set_xx_centroid_ins_)))
        
      ;
      (command "pselect"   "" )
      
      (command "point" ss_pre_filter_set_xx_centroid_mid_)
      (command "rectangle" (car ss_pre_filter_set_xx_centroid_ins_) (cadr ss_pre_filter_set_xx_centroid_ins_))
      (setvar "osmode" 1215)
      ;new_blk_entlast object
        (setq rec_ename (entlast))
        (setq rec_obj (vlax-ename->vla-object rec_ename))
        (setq ss_pre_filter_set_xx_ (ssadd rec_ename ss_pre_filter_set_xx_))
      ;
      (command "move" ss_pre_filter_set_xx_ "" ss_pre_filter_set_xx_centroid_mid_ )
      (vla-delete rec_obj)
    )
    (defun c:PPLINE-MAKE_layer_ ()
      ;preloop_and_while
        (setq TA-FL_Layer_ (list "ssddd" "0" "Defpoints" "000 - T E X T" "000 - TITLEBLOCK" 
                              "000 - H A T C H" "000 - L I N E 0.1" "000 - D I M 0.25" 
                              "000 - WIPEOUT" "000 - GRID" "A11_ALU.SOLID SHEET" 
                              "A12_PERFORATED" "A04_TUBE SERIES" "002 - STRUCTURAL STEEL" 
                              "000 - H I D D E N" "000 - D I M" "001 - ASCESSORIES" 
                              "A02_LITEWOOD" "000 - BUBBLE" "000 - SYMBOL CON" "000 - A_XREF" 
                              "000 - GROUND" "000 - L I N E" "000 - TEMP LAYER" "001 - DOOR" 
                              "001 - WINDOWS" "002 - STEEL LRIP" "002 - STEEL TUBE" 
                              "004 - CONCRETE" "004 - DOOR WINDOW" "004 - FLOOR" 
                              "004 - VIVA BOARD" "004 - WALL" "005 - WATER CLOSET EQUIP" 
                              "006 - ROOF" "008 - LIGHTING" "A01_ACP" "A03_SUN LOUVER" 
                              "A05_AHP." "A06_PERFORMANCE LOUVERS" "A07_PRANKCAD" "A08_AEROLITE" 
                              "A09_BIFOLDING" "A10_ENTRANCE MATT" "A13_EXPANDED"
                        )
        )
        (setq ii 0)
        (command "-layer" "filter" "n" "G" "" "0" "PPLINE-FAMELINE" ""  )
        (while (< ii (length TA-FL_Layer_))
          (setq TA-FL_Layer_list_ (nth ii TA-FL_Layer_))
          
          (command "-layer" "filter"  "e" "0" "PPLINE-FAMELINE" "a" TA-FL_Layer_list_ "L" "") 
          
          
          (setq ii (+ ii 1))
        ) 
      ;
      (command "-layer" "filter" "s" "All" "")
    )

    (defun c:match_point_X_mpxx ()
      ;user
      (setq p1_point_ (getpoint "specify reference Y axis Object"))

      ;
      ;preloop_and_while_for_return_selection-set_process
        (setq ERR_ nil)
        (while
          (= (vl-catch-all-error-p ERR_) nil)
          (setq ERR_
            (vl-catch-all-apply
              (function
                (lambda ()
                  ;selection_set_for_fillter_blk_name
                    (if  ;pre_select_ssget_or_post_select_ssget
                      (=
                        (setq ss_pre_filter_set_xx_ (ssget
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                        nil
                      )
                      (progn
                        (setq ss_pre_filter_set_xx_ (ssget
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                      )
                      (sslength ss_pre_filter_set_xx_)
                    )
                  ;
                )
              )
            )
          )
          (if (= (vl-catch-all-error-p ERR_) nil)
            (progn
              ; (setq ss_pre_filter_set_xx_ (TA:EF_Filter_ss_set_ ss_pre_filter_set_xx_ p1_obj_efname))
              ;preloop_and_while
                (setq ss_pre_filter_set_xx_i 0)
                (while (< ss_pre_filter_set_xx_i (sslength ss_pre_filter_set_xx_))
                  (setq ss_pre_filter_set_xx_ename_ (ssname ss_pre_filter_set_xx_ ss_pre_filter_set_xx_i))
                  (setq ss_pre_filter_set_xx_obj_ (vlax-ename->vla-object  ss_pre_filter_set_xx_ename_))
                  (setq ss_pre_filter_set_xx_obj_ins_ (vlax-safearray->list (vlax-variant-value (vla-get-insertionpoint ss_pre_filter_set_xx_obj_))))
                  (vla-put-insertionpoint ss_pre_filter_set_xx_obj_ 
                                          (vlax-3d-point 
                                            (list 
                                              (+ (car p1_point_))
                                              (+ (cadr ss_pre_filter_set_xx_obj_ins_))
                                              (+ (caddr ss_pre_filter_set_xx_obj_ins_))
                                            )
                                          )
                  )
                  (setq ss_pre_filter_set_xx_i (+ ss_pre_filter_set_xx_i 1))
                )
              ;
            )
          )
        )
      ;
    )
    (defun c:match_point_Y_mpyy ()
      ;user
      (setq p1_point_ (getpoint "specify reference Y axis Object"))

      ;
      ;preloop_and_while_for_return_selection-set_process
        (setq ERR_ nil)
        (while
          (= (vl-catch-all-error-p ERR_) nil)
          (setq ERR_
            (vl-catch-all-apply
              (function
                (lambda ()
                  ;selection_set_for_fillter_blk_name
                    (if  ;pre_select_ssget_or_post_select_ssget
                      (=
                        (setq ss_pre_filter_set_xx_ (ssget
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                        nil
                      )
                      (progn
                        (setq ss_pre_filter_set_xx_ (ssget
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                      )
                      (sslength ss_pre_filter_set_xx_)
                    )
                  ;
                )
              )
            )
          )
          (if (= (vl-catch-all-error-p ERR_) nil)
            (progn
              ; (setq ss_pre_filter_set_xx_ (TA:EF_Filter_ss_set_ ss_pre_filter_set_xx_ p1_obj_efname))
              ;preloop_and_while
                (setq ss_pre_filter_set_xx_i 0)
                (while (< ss_pre_filter_set_xx_i (sslength ss_pre_filter_set_xx_))
                  (setq ss_pre_filter_set_xx_ename_ (ssname ss_pre_filter_set_xx_ ss_pre_filter_set_xx_i))
                  (setq ss_pre_filter_set_xx_obj_ (vlax-ename->vla-object  ss_pre_filter_set_xx_ename_))
                  (setq ss_pre_filter_set_xx_obj_ins_ (vlax-safearray->list (vlax-variant-value (vla-get-insertionpoint ss_pre_filter_set_xx_obj_))))
                  (vla-put-insertionpoint ss_pre_filter_set_xx_obj_ 
                                          (vlax-3d-point 
                                            (list 
                                              (+ (car ss_pre_filter_set_xx_obj_ins_))
                                              (+ (cadr p1_point_))
                                              (+ (caddr ss_pre_filter_set_xx_obj_ins_))
                                            )
                                          )
                  )
                  (setq ss_pre_filter_set_xx_i (+ ss_pre_filter_set_xx_i 1))
                )
              ;
            )
          )
        )
      ;
    )
    (defun c:match_axis_X_maxx ()
      ;user
      (setq p1_ename_ (car (entsel "specify reference Y axis Object")))
      (setq p1_obj_ (vlax-ename->vla-object p1_ename_))
      (setq p1_obj_ins_ (vlax-safearray->list (vlax-variant-value (vla-get-insertionpoint p1_obj_))))
      (setq p1_obj_efname (LM:effectivename p1_obj_))
      (command "pselect"   "" )
      ;
      ;preloop_and_while_for_return_selection-set_process
        (setq ERR_ nil)
        (while
          (= (vl-catch-all-error-p ERR_) nil)
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                        nil
                      )
                      (progn
                        (setq ss_pre_filter_set_xx_ (ssget
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                      )
                      (sslength ss_pre_filter_set_xx_)
                    )
                  ;
                )
              )
            )
          )
          (if (= (vl-catch-all-error-p ERR_) nil)
            (progn
              ; (setq ss_pre_filter_set_xx_ (TA:EF_Filter_ss_set_ ss_pre_filter_set_xx_ p1_obj_efname))
              ;preloop_and_while
                (setq ss_pre_filter_set_xx_i 0)
                (while (< ss_pre_filter_set_xx_i (sslength ss_pre_filter_set_xx_))
                  (setq ss_pre_filter_set_xx_ename_ (ssname ss_pre_filter_set_xx_ ss_pre_filter_set_xx_i))
                  (setq ss_pre_filter_set_xx_ename_ (ssname ss_pre_filter_set_xx_ ss_pre_filter_set_xx_i))
                  (setq ss_pre_filter_set_xx_obj_ (vlax-ename->vla-object  ss_pre_filter_set_xx_ename_))
                  (setq ss_pre_filter_set_xx_obj_ins_ (vlax-safearray->list (vlax-variant-value (vla-get-insertionpoint ss_pre_filter_set_xx_obj_))))
                  (vla-put-insertionpoint ss_pre_filter_set_xx_obj_ 
                                          (vlax-3d-point 
                                            (list 
                                              (+ (car p1_obj_ins_))
                                              (+ (cadr ss_pre_filter_set_xx_obj_ins_))
                                              (+ (caddr ss_pre_filter_set_xx_obj_ins_))
                                            )
                                          )
                  )
                  (setq ss_pre_filter_set_xx_i (+ ss_pre_filter_set_xx_i 1))
                )
              ;
            )
          )
        )
      ;
    )
    (defun c:match_axis_Y_mayy ()
      ;user
      (setq p1_ename_ (car (entsel "specify reference Y axis Object")))
      (setq p1_obj_ (vlax-ename->vla-object p1_ename_))
      (setq p1_obj_ins_ (vlax-safearray->list (vlax-variant-value (vla-get-insertionpoint p1_obj_))))
      (setq p1_obj_efname (LM:effectivename p1_obj_ ))
      ;
      ;preloop_and_while_for_return_selection-set_process
        (setq ERR_ nil)
        (while
          (= (vl-catch-all-error-p ERR_) nil)
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                        nil
                      )
                      (progn
                        (setq ss_pre_filter_set_xx_ (ssget
                                                          (list
                                                            (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                      )
                      (sslength ss_pre_filter_set_xx_)
                    )
                  ;
                )
              )
            )
          )
          (if (= (vl-catch-all-error-p ERR_) nil)
            (progn
              ; (setq ss_pre_filter_set_xx_ (TA:EF_Filter_ss_set_ ss_pre_filter_set_xx_ p1_obj_efname))
              ;preloop_and_while
                (setq ss_pre_filter_set_xx_i 0)
                (while (< ss_pre_filter_set_xx_i (sslength ss_pre_filter_set_xx_))
                  (setq ss_pre_filter_set_xx_ename_ (ssname ss_pre_filter_set_xx_ ss_pre_filter_set_xx_i))
                  (setq ss_pre_filter_set_xx_obj_ (vlax-ename->vla-object  ss_pre_filter_set_xx_ename_))
                  (setq ss_pre_filter_set_xx_obj_ins_ (vlax-safearray->list (vlax-variant-value (vla-get-insertionpoint ss_pre_filter_set_xx_obj_))))
                  (vla-put-insertionpoint ss_pre_filter_set_xx_obj_ (vlax-3d-point (list
                                                                                      (+ (car ss_pre_filter_set_xx_obj_ins_))
                                                                                      (+ (cadr p1_obj_ins_))
                                                                                      (+ (caddr ss_pre_filter_set_xx_obj_ins_))
                                                                                  )
                                                                    ) 
                  )
                  (setq ss_pre_filter_set_xx_i (+ ss_pre_filter_set_xx_i 1))
                )
              ;
            )
          )
        )
      ;
    )
    (defun c:selection_match_x_ssmax ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq p1_ename_ (car (entsel "specify reference Y axis Object")))
      (setq p1_obj_ (vlax-ename->vla-object p1_ename_))
      (setq p1_obj_ins_ (vlax-safearray->list (vlax-variant-value (vla-get-insertionpoint p1_obj_))))
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (vla-put-insertionpoint 
            ss_pre_filter_set_xx_obj_
            (vlax-3d-point
              (car p1_obj_ins_)
              (cadr ss_pre_filter_set_xx_obj_ins_)
              (caddr ss_pre_filter_set_xx_obj_ins_)
            )
          )
          (setq ss_pre_filter_set_xx_i (+ ss_pre_filter_set_xx_i 1))
        )
      ;

    )
    (defun c:matching_dynamic_properties_madynprop ()
      (_StartUndo doc)
      ;selection_set_for_fillter_blk_name
        (if  ;pre_select_ssget_or_post_select_ssget
          (=
            (setq ss_pre_filter_set_xx_ (ssget ":S"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (car (entsel "specify ref Object")))
          )
          (sslength ss_pre_filter_set_xx_)
        )
      ;
      ;;get data pickset to ename
      (if (and ;get data pickset to ename 
            (/= ss_pre_filter_set_xx_ nil)
            (or 
              (= (type ss_pre_filter_set_xx_ ) 'pickset)
              (= (type ss_pre_filter_set_xx_ ) 'ENAME)
            )
          )
        (progn
          (if (= (type ss_pre_filter_set_xx_ ) 'pickset)
            (progn
              (setq REF-blk_ename_ (ssname ss_pre_filter_set_xx_ 0))
            )
            (setq REF-blk_ename_ ss_pre_filter_set_xx_)
          )
          (setq REF-blk_obj_ (vlax-ename->vla-object REF-blk_ename_))
          (setq REF-blk_obj_efname_ (LM:effectivename REF-blk_obj_))
          (setq REF-blk_obj_dynlist_ (LM:getdynprops REF-blk_obj_ ))
        )
      )
      ;
      ;preloop
        (setq ERR_ nil)
        
        (while
          (= (vl-catch-all-error-p ERR_) nil)
          (setq ERR_ (vl-catch-all-apply 
                      (function 
                        (lambda () 
                          (setq ss_pre_filter_set_xx_target_ (ssget 
                                                                (list 
                                                                  (cons 0 "INSERT") ;type of object
                                                                  ; (cons 8 "000 - GRID")   ;kind of layer
                                                                  ; (cons 2 "000-GRID_LINE_DYN")       ;kind of nameblock
                                                                  ; (cons 62 1)           ;kind of color call sign with color code index
                                                                )
                                                              )
                          )
                        )
                      )
                    )
          )
          (if (and 
                (/= ss_pre_filter_set_xx_target_ nil)
                (= (vl-catch-all-error-p ERR_) nil)
              )
            (progn
              ;preloop_and_while
                (TA:interface_text_ T)
                (setq ss_pre_filter_set_xx_target_i 0)
                (while (< ss_pre_filter_set_xx_target_i (sslength ss_pre_filter_set_xx_target_))
                  (setq ss_pre_filter_set_xx_target_ename_ (ssname ss_pre_filter_set_xx_target_ ss_pre_filter_set_xx_target_i))
                  (setq ss_pre_filter_set_xx_target_obj_ (vlax-ename->vla-object  ss_pre_filter_set_xx_target_ename_))
                  (setq ss_pre_filter_set_xx_target_obj_efname (LM:effectivename  ss_pre_filter_set_xx_target_obj_))
                  ;preloop_and_while
                    (setq REF-blk_obj_dynlist_i 0)
                    (while (< REF-blk_obj_dynlist_i (length REF-blk_obj_dynlist_))
                      (setq REF-blk_obj_dynlist_name_ (nth  REF-blk_obj_dynlist_i REF-blk_obj_dynlist_))
                      
                        (if (and 
                              ; (= REF-blk_obj_efname_ ss_pre_filter_set_xx_target_obj_efname )
                              (/= (car REF-blk_obj_dynlist_name_ ) "Origin")
                            )
                          (progn
                            (LM:setdynpropvalue 
                              ss_pre_filter_set_xx_target_obj_
                              (car REF-blk_obj_dynlist_name_)
                              (cdr REF-blk_obj_dynlist_name_)
                            )
                          )
                        )
                  
                      (setq REF-blk_obj_dynlist_i (+ REF-blk_obj_dynlist_i 1))
                    )
                  ;
                  (TA:textscr_process_V2 "matching object" ss_pre_filter_set_xx_target_i ss_pre_filter_set_xx_target_)
                  (setq ss_pre_filter_set_xx_target_i (+ ss_pre_filter_set_xx_target_i 1))
                )
              ;
            )
          )
        )
        (TA:interface_text_ nil)
      ;
      (_EndUndo doc)
    )
    (defun c:matching_attribute_properties_maatt ()
      (_StartUndo doc)
      
      ;selection_set_for_fillter_blk_name
        (if  ;pre_select_ssget_or_post_select_ssget
          (=
            (setq ss_pre_filter_set_xx_ (ssget ":S"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (car (entsel "specify ref Object")))
          )
          (sslength ss_pre_filter_set_xx_)
        )
      ;
      ;;get data pickset to ename
      (if (and ;get data pickset to ename 
            (/= ss_pre_filter_set_xx_ nil)
            (or 
              (= (type ss_pre_filter_set_xx_ ) 'pickset)
              (= (type ss_pre_filter_set_xx_ ) 'ENAME)
            )
          )
        (progn
          (if (= (type ss_pre_filter_set_xx_ ) 'pickset)
            (progn
              (setq REF-blk_ename_ (ssname ss_pre_filter_set_xx_ 0))
            )
            (setq REF-blk_ename_ ss_pre_filter_set_xx_)
          )
          (setq REF-blk_obj_ (vlax-ename->vla-object REF-blk_ename_))
          (setq REF-blk_obj_efname_ (LM:effectivename REF-blk_obj_))
          (setq REF-blk_obj_attlist_ (LM:vl-getattributevalues REF-blk_obj_ ))
          (setq REF-blk_obj_atttaglist_ (LM:vl-getattributevalue-tag-TA-Modifies REF-blk_obj_ ))
          (setq REF-blk_obj_attvallist_ (LM:vl-getattributevalue-val-TA-Modifies REF-blk_obj_ ))
        )
      )
      ;
      ;user-input_
        (setq skip_blank_val_ (cond ( (getint (strcat "\nspecify 0 for skip blank value\n<" (rtos (setq skip_blank_val_ (cond (skip_blank_val_) (0) ) ) ) "> : " ) ) ) (skip_blank_val_) ) )
      ;
      ;preloop
        (setq ERR_ nil)
        
        (while
          (= (vl-catch-all-error-p ERR_) nil)
          (setq ERR_ (vl-catch-all-apply 
                      (function 
                        (lambda () 
                          (setq ss_pre_filter_set_xx_target_ (ssget 
                                                                (list 
                                                                  (cons 0 "INSERT") ;type of object
                                                                  ; (cons 8 "000 - GRID")   ;kind of layer
                                                                  ; (cons 2 "000-GRID_LINE_DYN")       ;kind of nameblock
                                                                  ; (cons 62 1)           ;kind of color call sign with color code index
                                                                )
                                                              )
                          )
                        )
                      )
                    )
          )
          (if (and 
                (/= ss_pre_filter_set_xx_target_ nil)
                (= (vl-catch-all-error-p ERR_) nil)
              )
            (progn
              ;preloop_and_while
                (TA:interface_text_ T)
                (setq ss_pre_filter_set_xx_target_i 0)
                (while (< ss_pre_filter_set_xx_target_i (sslength ss_pre_filter_set_xx_target_))
                  (setq ss_pre_filter_set_xx_target_ename_ (ssname ss_pre_filter_set_xx_target_ ss_pre_filter_set_xx_target_i))
                  (setq ss_pre_filter_set_xx_target_obj_ (vlax-ename->vla-object  ss_pre_filter_set_xx_target_ename_))
                  (setq ss_pre_filter_set_xx_target_obj_efname (LM:effectivename  ss_pre_filter_set_xx_target_obj_))
                  ;preloop_and_while
                    (setq REF-blk_obj_attlist_i 0)
                    (while (< REF-blk_obj_attlist_i (length REF-blk_obj_attlist_))
                      (setq REF-blk_obj_attlist_name_ (nth  REF-blk_obj_attlist_i REF-blk_obj_attlist_))
                      
                        (if (and ;EF-name matching = off
                              ; (= REF-blk_obj_efname_ ss_pre_filter_set_xx_target_obj_efname )
                              (/= (member (car REF-blk_obj_attlist_name_) REF-blk_obj_atttaglist_) nil)
                              (/= (car REF-blk_obj_attlist_name_ ) "Origin")
                            )
                          (progn
                            (LM:vl-setattributevalue  
                              ss_pre_filter_set_xx_target_obj_
                              (car REF-blk_obj_attlist_name_)
                              (if (and 
                                    (= skip_blank_val_ 0)
                                    (= (cdr REF-blk_obj_attlist_name_ ) "") ;
                                  )
                                (progn
                                  (LM:vl-getattributevalue ss_pre_filter_set_xx_target_obj_ (car REF-blk_obj_attlist_name_))
                                  
                                )
                                (cdr REF-blk_obj_attlist_name_)
                              )
                            )
                          )
                        )
                  
                      (setq REF-blk_obj_attlist_i (+ REF-blk_obj_attlist_i 1))
                    )
                  ;
                  (TA:textscr_process_V2 "matching object" ss_pre_filter_set_xx_target_i ss_pre_filter_set_xx_target_)
                  (setq ss_pre_filter_set_xx_target_i (+ ss_pre_filter_set_xx_target_i 1))
                )
              ;
            )
          )
        )
        (TA:interface_text_ nil)
      ;
      (_EndUndo doc)
    )
    (defun c:matching_attribute_properties_madeepatt ()
      (_StartUndo doc)
        (setq Er-msg_ 
          (vl-catch-all-apply 
            (function 
              (lambda () 
                (setq deepatt_ename_ (car (nentsel "specify Object")))
                (setq deepatt_obj_ (vlax-ename->vla-object deepatt_ename_))
                (setq deepatt_obj_atttxt_ (vla-get-TextString  deepatt_obj_))
              )
            )
          )
        )

      ;while selection process
        (setq ERR_ nil)
        (while ;for keep insertion point and dist. fix length one side
          (and
            (= (vl-catch-all-error-p ERR_) nil)
          )
          (setq ERR_
            (vl-catch-all-apply
              (function
                (lambda ()
                  (setq att_ename_ (car (nentsel "specify Object")))
                  (setq att_obj_ (vlax-ename->vla-object att_ename_))
                  (setq att_obj_atttag (vla-get-TagString  att_obj_))
                  (vla-put-TextString  att_obj_ deepatt_obj_atttxt_)
                )
              )
            )
          )
        )
      ;
      (_EndUndo doc)
    )
    (defun c:matching_malayer ()
      (setq target_obj_layer_ nil)
      (setq layer_list_ (list 
                           "user input"
                           "000 - EXISTING_FINISHING-WALL_HATCH_" 
                           "000 - EXISTING_COLUMN_HATCH_" 
                           "000 - EXISTING_AAC-WALL_HATCH_" 
                           "" 
                           "" 
                           "" 
                         )
      )
      (setq layer_list_mode
        (TA:choose_list_v4
          layer_list_
          "select layer_list_ mode"
          layer_list_mode
        )
      )
      (if (= layer_list_mode "user input")
        (progn
          (setq target_ename_ (car (entsel "specify Layer Object")))
          (setq target_obj_ (vlax-ename->vla-object target_ename_))
          (setq target_obj_layer_ (vla-get-layer target_obj_))
        )
        (setq target_obj_layer_ layer_list_mode)
      )
      (setq yyy_ename_ (car (nentsel "specify Object")))
      (setq yyy_obj_ (vlax-ename->vla-object yyy_ename_))
      
      (setq yyy_obj_layer_ (vla-put-layer yyy_obj_  target_obj_layer_))
      
    )
    (defun c:polar_x_pox ()
      ;presetting
        (setq polar_move_val 0.125)
      ;
      ;
      ;   (setq target_ename_ (car (entsel "specify Object")))
      ;   (setq sym_num_ (cond ( (getint (strcat "\nspecify get rotation\n<" (rtos (setq sym_num_ (cond (sym_num_) (1.0) ) ) ) "> : " ) ) ) (sym_num_) ) )
      ; ;
      ;getdata_
      ; (cond
      ;   (;_case_1
      ;      (and
      ;         (= 1 1)
      ;         ; (/= sym_num_ nil)
      ;         ; (= sym_num_ 1)
      ;      )
      ;      (progn
      ;         (setq target_ename_ (car (entsel "specify Object")))
      ;         (setq target_obj_ (vlax-ename->vla-object target_ename_))
      ;         (TA:move_polar_insertionpoint target_obj_ "x" (- polar_move_val) )
      ;         (princ "_case_1")
      ;      )
      ;   )
      ;   (;_case_2
      ;      (and
      ;         (= 1 1)
      ;         ; (/= sym_num_ nil)
      ;         ; (= sym_num_ 0)
      ;      )
      ;      (progn
      ;         (setq target_ename_ (car (entsel "specify Object")))
      ;         (setq target_obj_ (vlax-ename->vla-object target_ename_))
      ;         (TA:move_polar_insertionpoint target_obj_ "x" polar_move_val )
      ;        (princ "_case_2")
      ;      )
      ;   )
      ; )
              (setq target_ename_ (car (entsel "specify - Object")))
              (setq target_obj_ (vlax-ename->vla-object target_ename_))
              (TA:move_polar_insertionpoint target_obj_ "x" (- polar_move_val) )
              (setq target_ename_ (car (entsel "specify + Object")))
              (setq target_obj_ (vlax-ename->vla-object target_ename_))
              (TA:move_polar_insertionpoint target_obj_ "x" polar_move_val )
      ;
    )
    (defun c:polar_y_poy ()
      ;presetting
        (setq polar_move_val 0.125)
      ;
      ;
        ; (setq target_ename_ (car (entsel "specify Object")))
        ; (setq sym_num_ (cond ( (getint (strcat "\nspecify get rotation\n<" (rtos (setq sym_num_ (cond (sym_num_) (1.0) ) ) ) "> : " ) ) ) (sym_num_) ) )
      ;
      ;getdata_
      ; (cond
      ;   (;_case_1
      ;      (and
      ;         (= 1 1)
      ;         ; (/= sym_num_ nil)
      ;         ; (= sym_num_ 1)
      ;      )
      ;      (progn
      ;         (setq target_ename_ (car (entsel "specify Object")))
      ;         (setq target_obj_ (vlax-ename->vla-object target_ename_))
      ;         (TA:move_polar_insertionpoint target_obj_ "Y" (- polar_move_val) )
      ;         (princ "_case_1")
      ;      )
      ;   )
      ;   (;_case_2
      ;      (and
      ;         (= 1 1)
      ;         ; (/= sym_num_ nil)
      ;         ; (= sym_num_ 1)
      ;      )
      ;      (progn
      ;         (setq target_ename_ (car (entsel "specify Object")))
      ;         (setq target_obj_ (vlax-ename->vla-object target_ename_))
      ;         (TA:move_polar_insertionpoint target_obj_ "Y" polar_move_val )
      ;        (princ "_case_2")
      ;      )
      ;   )
      ; )
              (setq target_ename_ (car (entsel "specify Object")))
              (setq target_obj_ (vlax-ename->vla-object target_ename_))
              (TA:move_polar_insertionpoint target_obj_ "y" (- polar_move_val) )
              (setq target_ename_ (car (entsel "specify Object")))
              (setq target_obj_ (vlax-ename->vla-object target_ename_))
              (TA:move_polar_insertionpoint target_obj_ "y" polar_move_val )   

      ;
    )
    (defun c:add_cloud_ADCL ()
      ;selection_set_for_fillter_blk_name
        (if  ;pre_select_ssget_or_post_select_ssget
          (=
            (setq ss_pre_filter_set_xx_ (ssget "i"
                                              (list
                                                (cons 0 "INSERT") ;type of object
                                                (cons -4 "<NOT")
                                                (cons 8 "000 - CSD_PL_A-_ANOT----_T-,") 
                                                (cons -4 "NOT>")
                                                (cons 8 "001 - ASCESSORIES,000 - CSD_PL_Defpoints,000 - CSD_PL_001 - ASCESSORIES")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                (cons -4 "<NOT")
                                                (cons 8 "000 - CSD_PL_A-_ANOT----_T-") 
                                                (cons -4 "NOT>")
                                                (cons 8 "001 - ASCESSORIES,000 - CSD_PL_Defpoints,000 - CSD_PL_001 - ASCESSORIES")   ;kind of layer
                                                ; (cons 2 "000-GRID_LINE_DYN")       ;kind of nameblock
                                                ; (cons 62 1)           ;kind of color call sign with color code index
                                              )
                                        )
            )
          )
          (sslength ss_pre_filter_set_xx_)
        )
      ;
      (textscr)
      (setq ss_pre_filter_set_xx_  (TA:EF_Filter_ss_set_ ss_pre_filter_set_xx_  "000 - DYNAMIC_LENGTH+COMBINE+VIEW_ASSCESSORIES_FAMELINE_BK-08_HANGING_SYSTEM_300HK_COMBINE_SET"))
      ;preloop_and_while
        (setq ss_pre_filter_set_xx_i 0)
        (setvar "CMDECHO" 0)
        (TA:interface_text_ T)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          
          (command "circle" 
                   (if (= (getvar "worlducs") 0)(progn (trans ss_pre_filter_set_xx_obj_ins_ 0 1)) ss_pre_filter_set_xx_obj_ins_ ) 
                   140
          )
          ;new_blk_entlast object
            (setq new_revc_ename (entlast))
            (setq new_revc_obj_ (vlax-ename->vla-object new_revc_ename))
            (command "revcloud"  "A"  80 "" "o" new_revc_ename "n") 
            (setq new_revc_ename (entlast))
            (setq new_revc_obj_ (vlax-ename->vla-object new_revc_ename))
            (vla-put-color new_revc_obj_ 6)
            (vla-put-ConstantWidth new_revc_obj_ 10)
          ;
          (TA:textscr_process "\nupdate" ss_pre_filter_set_xx_i ss_pre_filter_set_xx_)
          (setq ss_pre_filter_set_xx_i (+ ss_pre_filter_set_xx_i 1))
        )
        (TA:interface_text_ nil)
        (setvar "CMDECHO" 1)
      ;
    )
    (defun c:seleect_cloud_SECL ()
      ;selection_set_for_fillter_blk_name
        (if  ;pre_select_ssget_or_post_select_ssget
          (=
            (setq ss_pre_filter_set_xx_ (ssget "i"
                                              (list
                                                (cons 0 "LWPOLYLINE") ;type of object
                                                ; (cons 8 "000 - GRID")   ;kind of layer
                                                ; (cons 2 "000-GRID_LINE_DYN")       ;kind of nameblock
                                                (cons 62 6)           ;kind of color call sign with color code index
                                              )
                                        )
            )
            nil
          )
          (progn
            (setq ss_pre_filter_set_xx_ (ssget
                                              (list
                                                (cons 0 "LWPOLYLINE") ;type of object
                                                ; (cons 8 "000 - GRID")   ;kind of layer
                                                ; (cons 2 "000-GRID_LINE_DYN")       ;kind of nameblock
                                                (cons 62 6)           ;kind of color call sign with color code index
                                              )
                                        )
            )
          )
          (sslength ss_pre_filter_set_xx_)
        )
      ;
      (vl-catch-all-apply 
        (function 
          (lambda () 
            (command "erase"  ss_pre_filter_set_xx_ "" )
          )
        )
      )
       
      ;
    )
    (defun c:select_circle_selcir ()
      ;selection_set_for_fillter_blk_name
        (if  ;pre_select_ssget_or_post_select_ssget
          (=
            (setq ss_pre_filter_set_xx_ (ssget "i"
                                              (list
                                                (cons 0 "circle") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "circle") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (command "pselect"  ss_pre_filter_set_xx_  "" )
    )
    (defun c:simsetting ()
      (setq ERR_
        (vl-catch-all-apply
          (function
            (lambda ()
              (command "selectsimilar" "se" )
            )
          )
        )
      )
    )
    (defun c:objdistance ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      
      ; (setq 1_ename_ (car (entsel "specify Object")))
      (setq 1_obj_ (vlax-ename->vla-object (ssname ss_pre_filter_set_xx_ 0)))
      (setq 1_obj_ins_ (vlax-safearray->list (vlax-variant-value (vla-get-insertionpoint 1_obj_))))
      ; (setq 2_ename_ (car (entsel "specify Object")))
      (setq 2_obj_ (vlax-ename->vla-object (ssname ss_pre_filter_set_xx_ 1)))
      (setq 2_obj_ins_ (vlax-safearray->list (vlax-variant-value (vla-get-insertionpoint 2_obj_))))
      (alert (rtos (distance 1_obj_ins_ 2_obj_ins_) 2 4))

    )
    (defun c:objydist ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      
      ; (setq 1_ename_ (car (entsel "specify Object")))
      (setq 1_obj_ (vlax-ename->vla-object (ssname ss_pre_filter_set_xx_ 0)))
      (setq 1_obj_ins_ (vlax-safearray->list (vlax-variant-value (vla-get-insertionpoint 1_obj_))))
      ; (setq 2_ename_ (car (entsel "specify Object")))
      (setq 2_obj_ (vlax-ename->vla-object (ssname ss_pre_filter_set_xx_ 1)))
      (setq 2_obj_ins_ (vlax-safearray->list (vlax-variant-value (vla-get-insertionpoint 2_obj_))))
      (alert (rtos (- (cadr 1_obj_ins_) (cadr 2_obj_ins_)) 2 4))

    )
    (defun c:circledistance_cdit_ ()
      ;selection_set_for_fillter_blk_name
        (if  ;pre_select_ssget_or_post_select_ssget
          (=
            (setq ss_pre_filter_set_xx_ (ssget "i"
                                              (list
                                                (cons 0 "circle") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "circle") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (if (and 
            (/= ss_pre_filter_set_xx_ nil)
            (= (sslength ss_pre_filter_set_xx_) 2)
          )
        (progn
          (setq 1_ename_ (ssname ss_pre_filter_set_xx_ 0))
          (setq 1_obj_ (vlax-ename->vla-object 1_ename_))
          (setq 1_obj_ins_ (vlax-safearray->list (vlax-variant-value (vla-get-center 1_obj_))))
          (setq 2_ename_ (ssname ss_pre_filter_set_xx_ 1))
          (setq 2_obj_ (vlax-ename->vla-object 2_ename_))
          (setq 2_obj_ins_ (vlax-safearray->list (vlax-variant-value (vla-get-center 2_obj_))))
          (alert (rtos (distance 1_obj_ins_ 2_obj_ins_) 2 4))
        )
      )

    )
    (defun c:linedistance ()
      (setq 1_ename_ (car (entsel "specify Object")))
      (setq 1_obj_ (vlax-ename->vla-object 1_ename_))
      (setq 1_obj_ins_ (vlax-safearray->list (vlax-variant-value (vla-get-center 1_obj_))))
      (setq 2_ename_ (car (entsel "specify Object")))
      (setq 2_obj_ (vlax-ename->vla-object 2_ename_))
      (setq 2_obj_ins_ (vlax-safearray->list (vlax-variant-value (vla-get-center 2_obj_))))
      (command "line" 1_obj_ins_ 2_obj_ins_ "" )
    )
    (defun c:sslinedistance ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:EF_Filter_ss_set_ ss_pre_filter_set_xx_ (setq ef_obj_ (vlax-ename->vla-object (setq ef_ename_ (car (entsel "specify Filter EF name Object"))))) ))
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          ;ไว้ก่อน เดวมาทำให้เสด
          (setq ss_pre_filter_set_xx_i (+ ss_pre_filter_set_xx_i 1))
        )
      ;
    )
    (defun c:inerbreak ()
      (setq 1_ename_ (car (entsel "specify Object")))
      (setq 1_obj_ (vlax-ename->vla-object 1_ename_))
      (setq 2_ename_ (car (entsel "specify Object")))
      (setq 2_obj_ (vlax-ename->vla-object 2_ename_))
      (setq pt_break_ (LM:intersections+0 1_obj_ 2_obj_ acextendnone))
      (command "breakatpoint" 1_ename_  (car pt_break_)  )
      
    )
    (defun c:offset_block_ofblk ()
      ;presettting
        ; (setq offset_value -17.5)
        (setq offset_value (cond ( (getreal (strcat "\nspecify_height blank size\n<" (rtos (setq offset_value (cond (offset_value) (1.0) ) ) ) "> : " ) ) ) (offset_value) ) )
        (setq offset_value offset_value)
      ;
      (setq blk_ename_ (ssname (ssget "i" ) 0))
      (setq blk_obj_ (vlax-ename->vla-object blk_ename_))
      ;preloop_and_while
        (setq Er-msg_new_ename nil)
        (setq i_time_ 1)
        (while 
          (= (vl-catch-all-error-p Er-msg_new_ename) nil)
          (_StartUndo doc)
          (setq Er-msg_new_ename
            (vl-catch-all-apply 
              (function 
                (lambda () 
                  (setq new_axis_ ;Get-string by keep previous value
                      (if
                        (or
                          (/= (setq new_axis_val (getstring (strcat "\nSpecify Pattern name <" (if new_axis_ new_axis_ "") ">: ") ) ) "" )
                        )
                          (progn
                            (setq new_axis_ new_axis_val)
                            (setq new_axis_keep_val_ new_axis_val)
                          )
                        (setq new_axis_val new_axis_keep_val_)
                      )
                  )
                )
              )
            )
          )
          (if (= (vl-catch-all-error-p Er-msg_new_ename) nil)
            (progn
              (vla-copy blk_obj_)
              ;new_blk_entlast object
                (setq new_blk_ename (entlast))
                (setq new_blk_obj_ (vlax-ename->vla-object new_blk_ename))
              ;
              (TA:move_polar_insertionpoint new_blk_obj_ new_axis_val (* offset_value i_time_ ))
            )
          )
          (setq i_time_ (+ i_time_ 1))
          (_EndUndo doc)
        )
      ;
      
    )
    (defun c:UOB ()
        
        (setq Er-msg_ 
          (vl-catch-all-apply 
            (function 
              (lambda () 
                (setvar "SELECTIONPREVIEW" 3)
                (setq ucs_ename_ (car (entsel "specify Object")))
                (setq ucs_obj_ (vlax-ename->vla-object ucs_ename_))
                (setvar "SELECTIONPREVIEW" 0)
              )
            )
          )
        )
        (if (= (vl-catch-all-error-p Er-msg_) T)
          (progn
            (getvar "SELECTIONPREVIEW" )
            (setvar "SELECTIONPREVIEW" 0)
          )
          (setvar "SELECTIONPREVIEW" 0)
        )
        
      
      
      (command "ucs" "ob" ucs_ename_)
    )
    (defun c:quick_mirror_qmi ()
      ;selection_set_for_fillter_blk_name
        (if  ;pre_select_ssget_or_post_select_ssget
          (= 
            (setq ss_pre_filter_set_xx_ (ssget "i" 
                                              (list 
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "line,INSERT") ;type of object
                                            ; (cons 8 "000 - GRID")   ;kind of layer
                                            ; (cons 2 "000-GRID_LINE_DYN")       ;kind of nameblock
                                            ; (cons 62 1)           ;kind of color call sign with color code index
                                          )
                                        )
            )
          )
          (sslength ss_pre_filter_set_xx_)
        )
      ;
      ; (setq ss_pre_filter_set_xx_ (TA:EF_Filter_ss_set_V2_ ss_pre_filter_set_xx_ (list "000_CKST-FAMELINE_CEILING_CODE_PANEL") ) )
      ;preloop_and_while
      (setq ss_pre_filter_set_xx_i 0)
      (while 
        (and 
          (< ss_pre_filter_set_xx_i (sslength ss_pre_filter_set_xx_))
        )
        (setq ss_pre_filter_set_xx_ename_ (ssname ss_pre_filter_set_xx_ ss_pre_filter_set_xx_i ) )
        (setq ss_pre_filter_set_xx_obj_ (vlax-ename->vla-object ss_pre_filter_set_xx_ename_))
        (setq ss_pre_filter_set_xx_obj_xyz_scalelist_ (list (vla-get-xscalefactor ss_pre_filter_set_xx_obj_) 
                                                       (vla-get-yscalefactor ss_pre_filter_set_xx_obj_)
                                                       (vla-get-zscalefactor ss_pre_filter_set_xx_obj_)
                                                 )
        )
        (cond 
          ( ;ss_pre_filter_set_xx_obj_case_1
            (and 
              (> (car ss_pre_filter_set_xx_obj_xyz_scalelist_) 0)
              (> (cadr ss_pre_filter_set_xx_obj_xyz_scalelist_) 0)
            )
            (progn 
              (vla-put-xscalefactor ss_pre_filter_set_xx_obj_ (* (car ss_pre_filter_set_xx_obj_xyz_scalelist_) -1 ) )
            )
          )
          ( ;ss_pre_filter_set_xx_obj_case_1
            (and 
              (< (car ss_pre_filter_set_xx_obj_xyz_scalelist_) 0)
              (> (cadr ss_pre_filter_set_xx_obj_xyz_scalelist_) 0)
            )
            (progn 
              (vla-put-yscalefactor ss_pre_filter_set_xx_obj_ (* (cadr ss_pre_filter_set_xx_obj_xyz_scalelist_) -1 ) )
            )
          )
          ( ;ss_pre_filter_set_xx_obj_case_1
            (and 
              (< (car ss_pre_filter_set_xx_obj_xyz_scalelist_) 0)
              (< (cadr ss_pre_filter_set_xx_obj_xyz_scalelist_) 0)
            )
            (progn 
              (vla-put-xscalefactor ss_pre_filter_set_xx_obj_ (* (car ss_pre_filter_set_xx_obj_xyz_scalelist_) -1 ) )
            )
          )
          ( ;ss_pre_filter_set_xx_obj_case_1
            (and 
              (> (car ss_pre_filter_set_xx_obj_xyz_scalelist_) 0)
              (< (cadr ss_pre_filter_set_xx_obj_xyz_scalelist_) 0)
            )
            (progn 
              (vla-put-yscalefactor ss_pre_filter_set_xx_obj_ (* (cadr ss_pre_filter_set_xx_obj_xyz_scalelist_) -1 ) )
            )
          )
        )

        (setq ss_pre_filter_set_xx_i (+ ss_pre_filter_set_xx_i 1))
      )
      ;

      ;while selection process
      (setq ERR_ nil)
      (while  ;for keep insertion point and dist. fix length one side
        (and 
          (= (vl-catch-all-error-p ERR_) nil)
        )
        (setq ERR_ (vl-catch-all-apply 
                     (function 
                       (lambda () 
                         (getstring 
                           (strcat "enter for " " continue" )
                         ) ;input_cond entsel ssget
                       )
                     )
                   )
        )
        ;preloop_and_while
        (setq ss_pre_filter_set_xx_i 0)
        (while 
          (and 
            (= (vl-catch-all-error-p ERR_) nil)
            (< ss_pre_filter_set_xx_i (sslength ss_pre_filter_set_xx_))
          )
          (setq ss_pre_filter_set_xx_ename_ (ssname ss_pre_filter_set_xx_ ss_pre_filter_set_xx_i ) )
          (setq ss_pre_filter_set_xx_obj_ (vlax-ename->vla-object ss_pre_filter_set_xx_ename_))
          (setq ss_pre_filter_set_xx_obj_xyz_scalelist_ (list (vla-get-xscalefactor ss_pre_filter_set_xx_obj_) 
                                                       (vla-get-yscalefactor ss_pre_filter_set_xx_obj_)
                                                       (vla-get-zscalefactor ss_pre_filter_set_xx_obj_)
                                                 )
          )
          (cond 
            ( ;ss_pre_filter_set_xx_obj_case_1
              (and 
                (> (car ss_pre_filter_set_xx_obj_xyz_scalelist_) 0)
                (> (cadr ss_pre_filter_set_xx_obj_xyz_scalelist_) 0)
              )
              (progn 
                (vla-put-xscalefactor ss_pre_filter_set_xx_obj_ (* (car ss_pre_filter_set_xx_obj_xyz_scalelist_) -1 ) )
              )
            )
            ( ;ss_pre_filter_set_xx_obj_case_1
              (and 
                (< (car ss_pre_filter_set_xx_obj_xyz_scalelist_) 0)
                (> (cadr ss_pre_filter_set_xx_obj_xyz_scalelist_) 0)
              )
              (progn 
                (vla-put-yscalefactor ss_pre_filter_set_xx_obj_ (* (cadr ss_pre_filter_set_xx_obj_xyz_scalelist_) -1 ) )
              )
            )
            ( ;ss_pre_filter_set_xx_obj_case_1
              (and 
                (< (car ss_pre_filter_set_xx_obj_xyz_scalelist_) 0)
                (< (cadr ss_pre_filter_set_xx_obj_xyz_scalelist_) 0)
              )
              (progn 
                (vla-put-xscalefactor ss_pre_filter_set_xx_obj_ (* (car ss_pre_filter_set_xx_obj_xyz_scalelist_) -1 ) )
              )
            )
            ( ;ss_pre_filter_set_xx_obj_case_1
              (and 
                (> (car ss_pre_filter_set_xx_obj_xyz_scalelist_) 0)
                (< (cadr ss_pre_filter_set_xx_obj_xyz_scalelist_) 0)
              )
              (progn 
                (vla-put-yscalefactor ss_pre_filter_set_xx_obj_ (* (cadr ss_pre_filter_set_xx_obj_xyz_scalelist_) -1 ) )
              )
            )
          )

          (setq ss_pre_filter_set_xx_i (+ ss_pre_filter_set_xx_i 1))
        )
        ;
      )
      ;
      (if (= (vl-catch-all-error-p ERR_) T) 
        (progn 
          (setq blank_ss (ssadd))
          (sssetfirst nil)
        )
      )
    )
    (defun c:make_intersection_ucs_interucs ()
      (setq line_1_ename_ (car (entsel "specify Object")))
      (setq line_1_obj_ (vlax-ename->vla-object line_1_ename_))
      (setq line_2_ename_ (car (entsel "specify Object")))
      (setq line_2_obj_ (vlax-ename->vla-object line_2_ename_))
      (setvar "osmode" 0)
      (if (= (setq intersection_pt_ (LM:intersections+0 line_1_obj_ line_2_obj_ acextendthisentity  )) nil)
        (progn
          (if (= (setq intersection_pt_ (LM:intersections+0 line_1_obj_ line_2_obj_ acextendotherentity  )) nil)
            (progn
              (if (= (setq intersection_pt_ (LM:intersections+0 line_1_obj_ line_2_obj_ acextendnone  )) nil)
                (progn
                  (if (= (setq intersection_pt_ (LM:intersections+0 line_1_obj_ line_2_obj_ acextendboth  )) nil)
                    (progn
                      (alert "no intersection point")
                    )
                  )
                )
              )
            )
          )
        )
      )
      (setq main_obj_ins_ (car intersection_pt_))
      (if (= (getvar "worlducs") 0)(progn (setq main_obj_ins_ (trans main_obj_ins_ 0 1))) main_obj_ins_ )
      (command "ucs" main_obj_ins_ "")
      (setvar "osmode" 1215)
    )
    (defun c:m2_move_ ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ERR_
        (vl-catch-all-apply
          (function
            (lambda ()
              (setq errdetect (vl-catch-all-apply 
                                (function 
                                  (lambda () 
                                    (setq pt1_ (getpoint "specify point 1 or [Enter for basepoint]"))
                                  )
                                )
                              )
              )
              (if (= errdetect nil)
                (progn
                  (setq _obj_ (vlax-ename->vla-object (ssname ss_pre_filter_set_xx_ 0)))
                  (setq obj_ins (vlax-safearray->list (vlax-variant-value (vla-get-insertionpoint  _obj_))))
                  (setq pt1_ (if (= (getvar "worlducs") 0)(progn (trans obj_ins 0 1)) obj_ins ))
                  (setq pt2_ (getpoint pt1_ "specify point 2"))
                )
                (setq pt2_ (getpoint pt1_ "specify point 2"))
              )
              
              
              (setvar "osmode" 0)
              
              (command "move" ss_pre_filter_set_xx_ "" pt1_ (polar pt1_ (angle pt1_ pt2_) (/ (distance pt1_ pt2_) 2)) )
            )
          )
        )
      )

      (setvar "osmode" 1215)
    )
    (defun c:multi_zoom_mulzoom ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ss_pre_filter_set_xx_ (TA:standard_list_croodinate_sorting ss_pre_filter_set_xx_ "X" ))
      ;preloop_and_while
        (setq ss_pre_filter_set_xx_i 0)
        (while (< ss_pre_filter_set_xx_i (length ss_pre_filter_set_xx_))
          (setq ss_pre_filter_set_xx_ename_ (car (nth ss_pre_filter_set_xx_i ss_pre_filter_set_xx_ )))
          (setq ss_pre_filter_set_xx_obj_ (vlax-ename->vla-object  ss_pre_filter_set_xx_ename_))
          (setq ss_pre_filter_set_xx_obj_getboundingbox (vla-getboundingbox ss_pre_filter_set_xx_obj_ 'min_ 'max_)) 
          (setq ss_pre_filter_set_xx_min_ (vlax-safearray->list min_)) 
          (setq ss_pre_filter_set_xx_max_ (vlax-safearray->list max_)) 
          
          (setq so_easy_to_fall_in_love_ (TA:assembly_coordinate_coner (list ss_pre_filter_set_xx_min_ ss_pre_filter_set_xx_max_) ))
          (setvar "osmode" 0)
          (setq ERR
            (vl-catch-all-apply
              (function
                (lambda ()
                  (getstring "\nHit \nHit \nHit [ENTER] to continue...")
                )
              )
            )
          )
          
          (command "zoom" "window" (nth 0 so_easy_to_fall_in_love_) (nth 2 so_easy_to_fall_in_love_))
          (setvar "osmode" 1215)
          (setq ss_pre_filter_set_xx_i (+ ss_pre_filter_set_xx_i 1))
        )
      ;
    )
    (defun c:temp_sort()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ss_pre_filter_set_xx_ (TA:standard_list_croodinate_sorting ss_pre_filter_set_xx_ "X" ))
      ;preloop_and_while
        (setq ss_pre_filter_set_xx_i 0)
        (while (< ss_pre_filter_set_xx_i (length ss_pre_filter_set_xx_))
          (setq ss_pre_filter_set_xx_ename_ (car (nth ss_pre_filter_set_xx_i ss_pre_filter_set_xx_ )))
          (setq ss_pre_filter_set_xx_obj_ (vlax-ename->vla-object  ss_pre_filter_set_xx_ename_))

          
          (setq ssss (LM:vl-setattributevalue ss_pre_filter_set_xx_obj_ "D" ss_pre_filter_set_xx_i))

          (setq ss_pre_filter_set_xx_i (+ ss_pre_filter_set_xx_i 1))
        )
      ;
    )
    (defun c:Attribute_subfix ()
      (_startundo doc)
        ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        (setq att-tag_ename_ (car (nentsel "specify Object")))
        (setq att-tag_obj_ (vlax-ename->vla-object att-tag_ename_))
        (setq att-tag_obj-tagname (vla-get-TagString att-tag_obj_  )  )
        (setq nom_subfix-text_ (TA:GetClipboardText))
        (setq nom_subfix-text_ ;Get-string by keep previous value
            (if
              (or
                (/= (setq nom_subfix-text_val (getstring (strcat "\nSpecify Pattern name <" (if nom_subfix-text_ nom_subfix-text_ "") ">: ") ) ) "" )
              )
                (progn
                  (setq nom_subfix-text_ nom_subfix-text_val)
                  (setq nom_subfix-text_keep_val_ nom_subfix-text_val)
                )
              (setq nom_subfix-text_val nom_subfix-text_keep_val_)
            )
        )
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            
            (if (and 
                  (=  (vla-get-hasattributes ss_pre_filter_set_xx_obj_  ) :vlax-true)
                  (/= (TA:wcmatch_list (list att-tag_obj-tagname ) (LM:vl-getattributevalue-tag-TA-Modifies ss_pre_filter_set_xx_obj_  ) T) nil)
                )
              (progn
                (LM:vl-setattributevalue 
                  ss_pre_filter_set_xx_obj_ 
                  att-tag_obj-tagname 
                  ;;;;;;;;;;;;;;;;;;;;;;;;;;;;;;;;special event;;;;;;;;;;;;;;;;;;;;;;;;;;;;;;;;;;;;;;;;;;;;;;;;;;;;
                  (if (= (wcmatch (LM:vl-getattributevalue ss_pre_filter_set_xx_obj_ att-tag_obj-tagname) "*(edge-panel)*") nil)
                    (progn
                      (strcat (LM:vl-getattributevalue ss_pre_filter_set_xx_obj_ att-tag_obj-tagname) " " "(edge-panel)")
                    )
                  )
                  ;;;;;;;;;;;;;;;;;;;;;;;;;;;;;;;;special event;;;;;;;;;;;;;;;;;;;;;;;;;;;;;;;;;;;;;;;;;;;;;;;;;;;;
                )
              )
            )
            
            (setq ss_pre_filter_set_xx_i (+ ss_pre_filter_set_xx_i 1))
          )
        ;
      (_endundo doc)
    )
    (defun c:Attribute_subfix0 ()
      (_startundo doc)
        ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        (setq att-tag_obj-tagname "LV_TYPE_VAL"  )
        
        
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            
            (if (and 
                  (=  (vla-get-hasattributes ss_pre_filter_set_xx_obj_  ) :vlax-true)
                  (/= (TA:wcmatch_list (list "LV_TYPE_VAL" ) (LM:vl-getattributevalue-tag-TA-Modifies ss_pre_filter_set_xx_obj_  ) T) nil)
                )
              (progn
                (LM:vl-setattributevalue 
                  ss_pre_filter_set_xx_obj_ 
                  att-tag_obj-tagname 
                  ;;;;;;;;;;;;;;;;;;;;;;;;;;;;;;;;special event;;;;;;;;;;;;;;;;;;;;;;;;;;;;;;;;;;;;;;;;;;;;;;;;;;;;
                  (if (or
                        (= (wcmatch (LM:vl-getattributevalue ss_pre_filter_set_xx_obj_ att-tag_obj-tagname) "*(edge-panel)*") T)
                        (= (wcmatch (LM:vl-getattributevalue ss_pre_filter_set_xx_obj_ att-tag_obj-tagname) "*(corner-panel)*") T)
                      )
                    (progn
                      (LM:StringSubst
                        ""
                        "(edge-panel)"
                       (LM:StringSubst "" "(corner-panel)" (LM:vl-getattributevalue ss_pre_filter_set_xx_obj_ att-tag_obj-tagname) )
                       )
                    )
                    (LM:vl-getattributevalue ss_pre_filter_set_xx_obj_ att-tag_obj-tagname)
                  )
                  ;;;;;;;;;;;;;;;;;;;;;;;;;;;;;;;;special event;;;;;;;;;;;;;;;;;;;;;;;;;;;;;;;;;;;;;;;;;;;;;;;;;;;;
                )
              )
            )
            
            (setq ss_pre_filter_set_xx_i (+ ss_pre_filter_set_xx_i 1))
          )
        ;
      (_endundo doc)
    )
    (defun c:Attribute_subfix2 ()
      (_startundo doc)
        ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        (setq att-tag_obj-tagname "LV_TYPE_VAL"  )
        
        
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            
            (if (and 
                  (=  (vla-get-hasattributes ss_pre_filter_set_xx_obj_  ) :vlax-true)
                  (/= (TA:wcmatch_list (list "LV_TYPE_VAL" ) (LM:vl-getattributevalue-tag-TA-Modifies ss_pre_filter_set_xx_obj_  ) T) nil)
                )
              (progn
                (LM:vl-setattributevalue 
                  ss_pre_filter_set_xx_obj_ 
                  att-tag_obj-tagname 
                  ;;;;;;;;;;;;;;;;;;;;;;;;;;;;;;;;special event;;;;;;;;;;;;;;;;;;;;;;;;;;;;;;;;;;;;;;;;;;;;;;;;;;;;
                  (if (or
                        (= (wcmatch (LM:vl-getattributevalue ss_pre_filter_set_xx_obj_ att-tag_obj-tagname) "*(edge-panel)*") nil)
                        (= (wcmatch (LM:vl-getattributevalue ss_pre_filter_set_xx_obj_ att-tag_obj-tagname) "*(corner-panel)*") nil)
                      )
                    (progn
                      (strcat (LM:vl-getattributevalue ss_pre_filter_set_xx_obj_ att-tag_obj-tagname) " " "(edge-panel)")
                    )
                    (LM:vl-getattributevalue ss_pre_filter_set_xx_obj_ att-tag_obj-tagname)
                  )
                  ;;;;;;;;;;;;;;;;;;;;;;;;;;;;;;;;special event;;;;;;;;;;;;;;;;;;;;;;;;;;;;;;;;;;;;;;;;;;;;;;;;;;;;
                )
              )
            )
            
            (setq ss_pre_filter_set_xx_i (+ ss_pre_filter_set_xx_i 1))
          )
        ;
      (_endundo doc)
    )
    (defun c:Attribute_subfix3 ()
      (_startundo doc)
        ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        (setq att-tag_obj-tagname "LV_TYPE_VAL"  )
        
        
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            
            (if (and 
                  (=  (vla-get-hasattributes ss_pre_filter_set_xx_obj_  ) :vlax-true)
                  (/= (TA:wcmatch_list (list "LV_TYPE_VAL" ) (LM:vl-getattributevalue-tag-TA-Modifies ss_pre_filter_set_xx_obj_  ) T) nil)
                )
              (progn
                (LM:vl-setattributevalue 
                  ss_pre_filter_set_xx_obj_ 
                  att-tag_obj-tagname 
                  ;;;;;;;;;;;;;;;;;;;;;;;;;;;;;;;;special event;;;;;;;;;;;;;;;;;;;;;;;;;;;;;;;;;;;;;;;;;;;;;;;;;;;;
                  (if (or
                        (= (wcmatch (LM:vl-getattributevalue ss_pre_filter_set_xx_obj_ att-tag_obj-tagname) "*(edge-panel)*") nil)
                        (= (wcmatch (LM:vl-getattributevalue ss_pre_filter_set_xx_obj_ att-tag_obj-tagname) "*(corner-panel)*") nil)
                      )
                    (progn
                      (strcat (LM:vl-getattributevalue ss_pre_filter_set_xx_obj_ att-tag_obj-tagname) " " "(corner-panel)")
                    )
                    (LM:vl-getattributevalue ss_pre_filter_set_xx_obj_ att-tag_obj-tagname)
                  )
                  ;;;;;;;;;;;;;;;;;;;;;;;;;;;;;;;;special event;;;;;;;;;;;;;;;;;;;;;;;;;;;;;;;;;;;;;;;;;;;;;;;;;;;;
                )
              )
            )
            
            (setq ss_pre_filter_set_xx_i (+ ss_pre_filter_set_xx_i 1))
          )
        ;
      (_endundo doc)
    )
  ;
  ;Fastern Func
    (defun c:insSSHex ()
      ;selection_set_for_fillter_blk_name
        (if  ;pre_select_ssget_or_post_select_ssget
          (=
            (setq ss_pre_filter_set_xx_ (ssget "i"
                                              (list
                                                (cons 0 "line") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "line") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_start_end_pt_ (list
                                          (setq ss_pre_filter_set_xx_obj_startpt_ (vlax-safearray->list
                                                                     (vlax-variant-value ( vla-get-startpoint ss_pre_filter_set_xx_obj_ ))
                                                                   )
                                          )
                                          (setq ss_pre_filter_set_xx_obj_endpt_ (vlax-safearray->list
                                                                    (vlax-variant-value ( vla-get-endpoint ss_pre_filter_set_xx_obj_ ))
                                                                 )
                                          )
                                        )
          )
          (TA:vla-insertblock "HEX_BOLT-M5_set" ss_pre_filter_set_xx_obj_startpt_ 1 (angle ss_pre_filter_set_xx_obj_startpt_ ss_pre_filter_set_xx_obj_endpt_ ) )
          ;new_blk_entlast object
            (setq newblk_ename (entlast))
            (setq newblk_obj (vlax-ename->vla-object newblk_ename))
            (LM:setdynpropvalue newblk_obj  "L" (distance ss_pre_filter_set_xx_obj_startpt_ ss_pre_filter_set_xx_obj_endpt_))
          ;
          (setq ss_pre_filter_set_xx_i (+ ss_pre_filter_set_xx_i 1))
        )
      ;
      ;delete line ssset process
        (initget "Yes No")
        (setq ss_ ;Detect the variable's result in case of a function error
          (vl-catch-all-apply 
            (function 
              (lambda () 
                (setq DELETE_OBJ_ (not (eq "No" (getkword "\nKeep Existing object? [Yes/No] <Y>: "))))
              )
            )
          )
        )
        (if (= DELETE_OBJ_ t)
          (progn
            (princ "pass")
          )
          (command "erase" ss_pre_filter_set_xx_  )
        )
      ;
    )
    (defun c:insHex ()
      ;preloop_and_while
        (setq bypass_inspt_1 nil)
        (while (and 
                (= bypass_inspt_1 nil)
               )
          (setq bypass_inspt_1 
            (vl-catch-all-apply
              (function
                (lambda ()
                  (setq inspt_1 (getpoint "input point 1" ))  
                )
              )
            )
          )
          (if (and 
                (= (vl-catch-all-error-p bypass_inspt_1) nil)
                (= (getvar "worlducs") 0)
              )
            (progn 
              (setq inspt_2 (getpoint (trans inspt_1 1 1)  "input point 2" ))
              (setq ang_ (angle inspt_1 inspt_2 ))
              (setq dist_ (distance inspt_1 inspt_2 ))
            ) 
          )
          (if (and 
                (= (vl-catch-all-error-p bypass_inspt_1) nil)
                (= (getvar "worlducs") 1)
              )
            (progn 
              (setq inspt_2 (getpoint inspt_1 "input point 2" ))
              (setq ang_ (angle inspt_1 inspt_2 ))
              (setq dist_ (distance inspt_1 inspt_2 ))
            ) 
          )
          (if (= (vl-catch-all-error-p bypass_inspt_1) nil)
            (progn
              (TA:vla-insertblock "000 - DYNAMIC_LENGTH+VIEW_ACESSORIES_HEX_BOLT-M5_COMBINE_SET" 
                (if (= (getvar "worlducs") 0)(progn (trans inspt_1 1 0)) inspt_1 ) 
                1 
                ang_ 
              )
              ;new_blk_entlast object
                (setq newblk_ename (entlast))
                (setq newblk_obj (vlax-ename->vla-object newblk_ename))
                (LM:setdynpropvalue newblk_obj  "L" dist_)
                (cond  ; condition for input visibility for thraed length
                  ( ;_case_1
                    (and 
                      (= (fix dist_) 0)
                    )
                    (progn 
                      (LM:setdynpropvalue newblk_obj "view" "top_view")
                    )
                  )
                  ( ;_case_1
                    (and 
                      (/= (fix dist_ ) 0)

                      (>= (+ dist_ 8) 10)
                      (<= (+ dist_ 8) 12)
                    )
                    (progn 
                      (LM:setdynpropvalue newblk_obj "view" "x12mm.")
                    )
                  )
                  ( ;_case_1
                    (and 
                      (/= (fix dist_ ) 0)

                      (>= (+ dist_ 8) 10)
                      (<= (+ dist_ 8) 14)
                    )
                    (progn 
                      (LM:setdynpropvalue newblk_obj "view" "x14mm.")
                    )
                  )
                  ( ;_case_1
                    (and 
                      (/= (fix dist_ ) 0)

                      (>= (+ dist_ 8) 12)
                      (<= (+ dist_ 8) 15)
                    )
                    (progn 
                      (LM:setdynpropvalue newblk_obj "view" "x15mm.")
                    )
                  )
                  ( ;_case_2
                    (and 
                      (/= (fix dist_ ) 0)

                      (>= (+ dist_ 8) 15)
                      (<= (+ dist_ 8) 20)
                    )
                    (progn 
                      (LM:setdynpropvalue newblk_obj "view" "x20mm.")
                    )
                  )
                  ( ;_case_2
                    (and 
                      (/= (fix dist_ ) 0)

                      (>= (+ dist_ 8) 20)
                      (<= (+ dist_ 8) 25)
                    )
                    (progn 
                      (LM:setdynpropvalue newblk_obj "view" "x25mm.")
                    )
                  )
                  ( ;_case_2
                    (and 
                      (/= (fix dist_ ) 0)

                      (>= (+ dist_ 8) 30)
                      (<= (+ dist_ 8) 35)
                    )
                    (progn 
                      (LM:setdynpropvalue newblk_obj "view" "x30mm.")
                    )
                  )
                  ( ;_case_2
                    (and 
                      (/= (fix dist_ ) 0)

                      (>= (+ dist_ 8) 35)
                      (<= (+ dist_ 8) 40)
                    )
                    (progn 
                      (LM:setdynpropvalue newblk_obj "view" "x40mm.")
                    )
                  )
                  ( ;_case_2
                    (and 
                      (/= (fix dist_ ) 0)

                      (>= (+ dist_ 8) 40)
                      (<= (+ dist_ 8) 45)
                    )
                    (progn 
                      (LM:setdynpropvalue newblk_obj "view" "x45mm.")
                    )
                  )
                  ( ;_case_2
                    (and 
                      (/= (fix dist_ ) 0)

                      (>= (+ dist_ 8) 45)
                      (<= (+ dist_ 8) 50)
                    )
                    (progn 
                      (LM:setdynpropvalue newblk_obj "view" "x50mm.")
                    )
                  )
                  ( ;_case_2
                    (and 
                      (/= (fix dist_ ) 0)

                      (>= (+ dist_ 8) 50)
                      (<= (+ dist_ 8) 55)
                    )
                    (progn 
                      (LM:setdynpropvalue newblk_obj "view" "x55mm.")
                    )
                  )
                  ( ;_case_2
                    (and 
                      (/= (fix dist_ ) 0)

                      (>= (+ dist_ 8) 55)
                      (<= (+ dist_ 8) 60)
                    )
                    (progn 
                      (LM:setdynpropvalue newblk_obj "view" "x60mm.")
                    )
                  )
                  ( ;_case_2
                    (and 
                      (/= (fix dist_ ) 0)

                      (>= (+ dist_ 8) 60)
                      (<= (+ dist_ 8) 65)
                    )
                    (progn 
                      (LM:setdynpropvalue newblk_obj "view" "x65mm.")
                    )
                  )
                  ( ;_case_2
                    (and 
                      (/= (fix dist_ ) 0)

                      (>= (+ dist_ 8) 65)
                      (<= (+ dist_ 8) 70)
                    )
                    (progn 
                      (LM:setdynpropvalue newblk_obj "view" "x70mm.")
                    )
                  )
                  ( ;_case_2
                    (and 
                      (/= (fix dist_ ) 0)

                      (>= (+ dist_ 8) 70)
                      (<= (+ dist_ 8) 75)
                    )
                    (progn 
                      (LM:setdynpropvalue newblk_obj "view" "x75mm.")
                    )
                  )
                  ( ;_case_2
                    (and 
                      (/= (fix dist_ ) 0)

                      (>= (+ dist_ 8) 75)
                      (<= (+ dist_ 8) 80)
                    )
                    (progn 
                      (LM:setdynpropvalue newblk_obj "view" "x80mm.")
                    )
                  )
                  ( ;_case_2
                    (and 
                      (/= (fix dist_ ) 0)

                      (>= (+ dist_ 8) 80)
                      (<= (+ dist_ 8) 90)
                    )
                    (progn 
                      (LM:setdynpropvalue newblk_obj "view" "x90mm.")
                    )
                  )
                  ( ;_case_2
                    (and 
                      (/= (fix dist_ ) 0)

                      (>= (+ dist_ 8) 90)
                      (<= (+ dist_ 8) 100)
                    )
                    (progn 
                      (LM:setdynpropvalue newblk_obj "view" "x100mm.")
                    )
                  )
                )
              ;
              (setq bypass_inspt_1 nil)
            )
          )
        )
      ;
    )
  ;
  ;text window func
    (defun TA:interface_text_ ( symbol )
      (if (= symbol T)
        (progn
          ;switch window
            (textscr)
            (vla-put-WindowState (vlax-get-acad-object) acmax)
          ;
        )
        (graphscr)
      )
      
    )
  ;
  ;xline
    (defun c:Offset_xline_ ()
      (if (= offset_value_ nil)
        (progn
          (setq offset_value_ 0)
        )
        offset_value_
      )
      (setq offvalue_detect (TA:getkword "keep input offset value ?"  "Yes" "No"  offset_value_ "false"))
      (if (= offvalue_detect "false")
        (progn
          (setq user_input_offset_value_ (cond ( (getreal (strcat "\nspecify user_input_offset_value_ \n<" (rtos (setq user_input_offset_value_ (cond (user_input_offset_value_) (1.0) ) ) ) "> : " ) ) ) (user_input_offset_value_) ) )
        )
        (setq user_input_offset_value_ offset_value_)
      )
      (getp)
      
    )
    (defun c:midline_vxl ()
      (setq pt1 (getpoint))
      (setq pt2 ( getpoint pt1))
      (setq pt2 (list 
                  (car pt2)
                  (cadr pt1)
                  (caddr pt2)
                )
      )
      (setq getdistt_ (distance pt1 pt2))
      (setq getanglee_  (angle pt1 pt2))
      (command "xline" "V" (polar pt1 0 (/ getdistt_ 2) ) "")
    )
    (defun c:midline_hxl ()
      (setq pt1 (getpoint))
      (setq pt2 ( getpoint pt1))
      (setq pt2 (list 
                  (car pt1)
                  (cadr pt2)
                  (caddr pt2)
                )
      )
      (setq getdistt_ (distance pt1 pt2))
      (setq getanglee_  (angle pt1 pt2))
      (command "xline" "H" (polar pt1 getanglee_ (/ getdistt_ 2) ) "")
    )
  ;
  ;INSERT_FUNC
    (defun c:quick-insert_qqq0ins ()
      (TA:vla-insertblock
        "DIM-0S"
        (getpoint)
        1
        0
      )
      (Setq sss (vlax-ename->vla-object (entlast)) )
      (vla-put-layer (vlax-ename->vla-object (entlast)) "000 - 0_SYM_DWG_GRIDLINE_MAIN_COLOR_251")
      ; (vla-explode sss)
      ; (vla-delete sss)
    )
    (defun c:quick-insert_qqq1ins ()
      (TA:vla-insertblock
        "DIM-1SSS"
        (getpoint)
        1
        0
      )
      (Setq sss (vlax-ename->vla-object (entlast)) )
      (vla-put-layer (vlax-ename->vla-object (entlast)) "000 - 0_SYM_DWG_GRIDLINE_MAIN_COLOR_251")
    )
    (defun c:quick-insert_qqq2ins ()
      (TA:vla-insertblock
        "DIM-2SS"
        (getpoint)
        1
        0
      )
      (Setq sss (vlax-ename->vla-object (entlast)) )
      (vla-put-layer (vlax-ename->vla-object (entlast)) "000 - 0_SYM_DWG_GRIDLINE_MAIN_COLOR_251")
    )
    
    (defun c:quick-insert_qqq3ins ()
      (TA:vla-insertblock
        "DSASDADSA"
        (getpoint)
        1
        0
      )
      (Setq sss (vlax-ename->vla-object (entlast)) )
      (vla-put-layer (vlax-ename->vla-object (entlast)) "000 - 0_SYM_DWG_GRIDLINE_MAIN_COLOR_251")
      ; (vla-explode sss)
      ; (vla-delete sss)
    )
    (defun c:qblk ()
      (setq kword_result_ (TA:getkword "Keep block name for insert block ?"  "Yes" "No"  "yes" "false"))
      (if (and 
            (/= kword_blk_efname_ nil)
            (= kword_result_ "yes")
          )
        (progn
          (setq kword_blk_efname_ kword_blk_efname_)
        )
        (setq ERR_
          (vl-catch-all-apply
            (function
              (lambda ()
                (setq kword_blk_efname_ (LM:effectivename (vlax-ename->vla-object (car (entsel "specify block reference to get block name : ")))))
                (setq err_i 0)
              )
            )
          )
        )
      )
      
    )
    (defun c:insert_butween_two_object_insbtwobj ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              ) 
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq blk1_ename_ (ssname ss_pre_filter_set_xx_ 0))
      (setq blk1_obj_ (vlax-ename->vla-object blk1_ename_))
      (setq blk1_obj_ins_ (vlax-safearray->list (vlax-variant-value (vla-get-insertionpoint blk1_obj_))))
      (setq blk1_obj_ro (vla-get-rotation blk1_obj_))
      (setq blk2_ename_ (ssname ss_pre_filter_set_xx_ 1))
      (setq blk2_obj_ (vlax-ename->vla-object blk2_ename_))
      (setq blk2_obj_ins_ (vlax-safearray->list (vlax-variant-value (vla-get-insertionpoint blk2_obj_))))
      (setq insmid_ (TA:midpoint blk1_obj_ins_ blk2_obj_ins_))
      
      (setq target-move_ename_ (car (entsel "specify Object")))
      (setq target-move_obj_ (vlax-ename->vla-object target-move_ename_))
      
      (vla-copy target-move_obj_)
      ;new_blk_entlast object
        (setq newblk_ename (entlast))
        (setq newblk_obj (vlax-ename->vla-object newblk_ename))
      ;
      (vla-put-insertionpoint
        newblk_obj
        (vlax-3d-point insmid_)
      )
    )
    (defun c:insert_by_polyline_blk2pline ()
      (_startundo doc)
      (setq pline-intesert_ename_ (car (entsel "specify Object")))
      (setq pline-intesert_obj_ (vlax-ename->vla-object pline-intesert_ename_))
      (setq pline-intesert_obj_vertex_ (cadr (TA:Get_Pline_vertext_ins_point_ pline-intesert_ename_)))
      (setvar  "osmode" 1215)
      ;while selection process
        (setq ERR_ nil)
        (setq err-pass_ 1)
        (setq err-pass_ 0)
        (setq pline-intesert_obj_vertex_i 0)
        (setq bypass-value_ (TA:getkword "select block bypass ?"  "Yes" "No"  "yes" "false"))
        (while ;for keep insertion point and dist. fix length one side
          (and
            (= (vl-catch-all-error-p ERR_) nil)
            ; (= err-pass_ 0)
            (= (getvar "osmode") 1215)
          )
          (setq ERR_
            (vl-catch-all-apply
              (function
                (lambda ()
                  (setvar "osmode" 0)
                  (setvar "selectionpreview" 3)
                  (command "redraw")
                  (setq pline-intesert_obj_vertex_insxy (if (= (getvar "worlducs") 0)(progn (trans (nth pline-intesert_obj_vertex_i pline-intesert_obj_vertex_) 0 1)) (nth  pline-intesert_obj_vertex_i pline-intesert_obj_vertex_) ))
                  (setq h (/ (getvar "VIEWSIZE") 10))
                  (grdraw (polar pline-intesert_obj_vertex_insxy  (deg-to-rad 45) h ) (polar pline-intesert_obj_vertex_insxy  (deg-to-rad 225) h ) 30)
                  (grdraw (polar pline-intesert_obj_vertex_insxy  (deg-to-rad 135) h ) (polar pline-intesert_obj_vertex_insxy  (deg-to-rad 315) h ) 30)\
                  (setq pline-intesert_obj_vertex_insxy (if (= (getvar "worlducs") 0)(progn (trans (nth pline-intesert_obj_vertex_i pline-intesert_obj_vertex_) 1 1)) (nth  pline-intesert_obj_vertex_i pline-intesert_obj_vertex_) ))
                  ;while selection process
                    (setq ERR_r1 nil)
                    (setq err-pass_ 0)

                    (if (= bypass-value_ "yes")
                      (progn
                        ;selection_set_for_fillter_blk_name
                          (if  ;pre_select_ssget_or_post_select_ssget
                            (=
                              (setq ss_pre_filter_set_xx_ (ssget "i"
                                                                (list
                                                                  (cons 0 "INSERT") ;type of object
                                                                  ; (cons 8 "000 - GRID")   ;kind of layer
                                                                  ; (cons 2 "000-GRID_LINE_DYN")       ;kind of nameblock
                                                                  ; (cons 62 1)           ;kind of color call sign with color code index
                                                                )
                                                          )
                              )
                              nil
                            )
                            (progn
                              (setq ss_pre_filter_set_xx_ (ssget
                                                                (list
                                                                  (cons 0 "INSERT") ;type of object
                                                                  ; (cons 8 "000 - GRID")   ;kind of layer
                                                                  ; (cons 2 "000-GRID_LINE_DYN")       ;kind of nameblock
                                                                  ; (cons 62 1)           ;kind of color call sign with color code index
                                                                )
                                                          )
                              )
                            )
                            (sslength ss_pre_filter_set_xx_)
                          )
                        ;
                        ;preloop_and_while
                          (setq ss_pre_filter_set_xx_i 0)
                          (setq pline-intesert_obj_vertex_val 0)
                          (setq ss_pre_filter_set_xx_ename_ 0)
                          (while (and 
                                  (/= pline-intesert_obj_vertex_val nil)
                                  (/= ss_pre_filter_set_xx_ename_ nil)
                                  (< ss_pre_filter_set_xx_i (sslength ss_pre_filter_set_xx_))
                                )
                            (setq ss_pre_filter_set_xx_ename_ (ssname ss_pre_filter_set_xx_ ss_pre_filter_set_xx_i))
                            (setq ss_pre_filter_set_xx_obj_ (vlax-ename->vla-object  ss_pre_filter_set_xx_ename_))
                            (setq pline-intesert_obj_vertex_insxy (nth ss_pre_filter_set_xx_i pline-intesert_obj_vertex_))
                            (vla-put-insertionpoint 
                              ss_pre_filter_set_xx_obj_
                              (vlax-3d-point pline-intesert_obj_vertex_insxy)
                            )
                            (setq ss_pre_filter_set_xx_i (+ ss_pre_filter_set_xx_i 1))
                          )
                          (setvar  "osmode" 1215)
                        ;
                      )
                      (while ;for keep insertion point and dist. fix length one side
                        (and
                          (= (vl-catch-all-error-p ERR_r1) nil)
                          (or 
                            (= err-pass_ 0)
                          )
                        )
                        (setq ERR_r1
                          (vl-catch-all-apply
                            (function
                              (lambda ()
                                (setq target_blk_ename_ (car (entsel "specify Object or select Xline for exit")))
                                (setq target_blk_obj_ (vlax-ename->vla-object target_blk_ename_))
                                (if (= (vla-get-objectname target_blk_obj_ ) "AcDbBlockReference")
                                  (progn
                                    (setq err-pass_ 1)
                                    (vla-put-insertionpoint 
                                      (setq target_blk_obj_ (vlax-ename->vla-object target_blk_ename_))
                                      (vlax-3d-point pline-intesert_obj_vertex_insxy)
                                    )
                                    (setvar  "osmode" 1215)
                                  )
                                )
                                (if (and 
                                      (= (vl-catch-all-error-p ERR_r1) nil)
                                      (= (vla-get-objectname target_blk_obj_ ) "AcDbPolyline")
                                      (= (vl-princ-to-string target_blk_obj_) (vl-princ-to-string pline-intesert_obj_))
                                    )
                                  (progn
                                    (setq err-pass_ 1)
                                    (setvar  "osmode" 1215)
                                  )
                                )
                                (if (and 
                                      (/= (vl-catch-all-error-p ERR_r1) nil)
                                    )
                                  (progn
                                    (setq err-pass_ 1)
                                  )
                                )
                              )
                            )
                          )
                        )
                      )
                    )

                  ;
                  
                  (setq pline-intesert_obj_vertex_i (+ pline-intesert_obj_vertex_i 1))
                )
              )
            )
          )
        )
      ;
      (setvar  "osmode" 1215)
      (_endundo doc)
    )
    (defun c:insert_by_line_blk2pline ()
      (_startundo doc)
      (setq line_ename_ (car (entsel "specify LINE Object")))
      (setq line_obj_ (vlax-ename->vla-object line_ename_))
      (setq line_obj_start_end_pt_ (list
                                      (setq line_obj_startpt_ (vlax-safearray->list
                                                                (vlax-variant-value ( vla-get-startpoint line_obj_ ))
                                                              )
                                      )
                                      (setq line_obj_endpt_ (vlax-safearray->list
                                                                (vlax-variant-value ( vla-get-endpoint line_obj_ ))
                                                            )
                                      )
                                    )
      )
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq div_all_ (- (sslength ss_pre_filter_set_xx_) 1))
      ;
      ;preloop_and_while
        (setq div_i 1)
        (setq list_divpt_ ())
        (setq list_divpt_ (cons line_obj_startpt_ list_divpt_))
        ; (setq list_divpt_ (cons line_obj_endpt_ list_divpt_))
        (setq 1st_trans ())
        (setq line_obj_all_length_ (vla-get-length line_obj_))
        (while (< div_i (+ div_all_ 1))
          (setq line_obj_div_ (/ line_obj_all_length_ div_all_  ))
          (setq summary_div_ (vlax-curve-getPointAtDist line_obj_ (* line_obj_div_ div_i)))
          (if (= (getvar "worlducs") 0)
            (progn
              (setq 1st_trans (list 
                                (car (trans summary_div_ 1 1) )
                                (cadr (trans summary_div_ 1 1) )
                                0
                              )
              )  
            )
            
          )
          (if (= (getvar "worlducs") 1)
            (progn
              (setq 1st_trans (list 
                                (car summary_div_ )
                                (cadr summary_div_ )
                                0
                              )
              )  
            )
            
          )
          (setq list_divpt_ (cons 1st_trans list_divpt_ ))
          (setq div_i (+ div_i 1))
        )
      ;
      ; (setq newblk_obj_efname_ (LM:Effectivename (vlax-ename->vla-object (car (entsel "specify block to insert")))))
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq list_divpt_xy (nth ss_pre_filter_set_xx_i list_divpt_))
          (vla-put-insertionpoint 
            ss_pre_filter_set_xx_obj_
            (vlax-3d-point list_divpt_xy)
          )
          (setq ss_pre_filter_set_xx_i (+ ss_pre_filter_set_xx_i 1))
        )
      ;
      (setvar "osmode" 1215)
      (_endundo doc)
    )
    (defun c:insert_by_intersect_blk2in_ ()
      ;selection_set_for_fillter_blk_name
        (if  ;pre_select_ssget_or_post_select_ssget
          (=
            (setq ss_pre_filter_set_xx_ (ssget "i"
                                              (list
                                                (cons 0 "xline") ;type of object
                                                ; (cons 0 "xline,line") ;type of object
                                                ; (cons 8 "Defpoints")   ;kind of layer
                                                ; (cons 2 "000-GRID_LINE_DYN")       ;kind of nameblock
                                                ; (cons 62 6)           ;kind of color call sign with color code index
                                              )
                                        )
            )
            nil
          )
          (progn
            (setq ss_pre_filter_set_xx_ (ssget
                                              (list
                                                (cons 0 "xline,line") ;type of object
                                                ; (cons 8 "Defpoints")   ;kind of layer
                                                ; (cons 2 "000-GRID_LINE_DYN")       ;kind of nameblock
                                                ; (cons 62 6)           ;kind of color call sign with color code index
                                              )
                                        )
            )
          )
          (sslength ss_pre_filter_set_xx_)
        )
      ;
      (setq inters_list_ (LM:intersectionsinset  ss_pre_filter_set_xx_))
      (command "pselect"   "" )
      ;TA:stanndard_lambda_sorting
        (setq inters_list_sorted_ (vl-sort inters_list_  ;bigest open indent list
                                                  (function 
                                                    (lambda (a b) 
                                                      (< (car a) (car b))
                                                    )
                                                  )
                              ) ;bigest close indent list
        )
      ;
      (setq inters_ss_ (ssadd))
      ;while selection process
        (setq ERR_ nil)
        (setq inters_list_time_i_ 0)
        (setq exit-pass 0)
        (setq target_blk_obj_ nil)
        (setvar "osmode" 0)
        (while ;for keep insertion point and dist. fix length one side
          (and
            (= (vl-catch-all-error-p ERR_) nil)
            (< inters_list_time_i_ (length inters_list_))
            (/= (getvar "osmode") 1215)
          )
          (setq ERR_
            (vl-catch-all-apply
              (function
                (lambda ()
                    (setvar "osmode" 0)
                    (setvar "selectionpreview" 3)
                    (command "redraw")
                    (setq inters_list_sorted_val_ (if (= (getvar "worlducs") 0)(progn (trans (nth inters_list_time_i_ inters_list_sorted_) 0 1)) (nth  inters_list_time_i_ inters_list_sorted_) ))
                    (setq h (/ (getvar "VIEWSIZE") 10))
                    (grdraw (polar inters_list_sorted_val_  (deg-to-rad 45) h ) (polar inters_list_sorted_val_  (deg-to-rad 225) h ) 30)
                    (grdraw (polar inters_list_sorted_val_  (deg-to-rad 135) h ) (polar inters_list_sorted_val_  (deg-to-rad 315) h ) 30)
                    (setq inters_list_sorted_val_ (if (= (getvar "worlducs") 0)(progn (trans (nth inters_list_time_i_ inters_list_sorted_) 1 1)) (nth  inters_list_time_i_ inters_list_sorted_) ))
                    ;while selection process
                      (setq ERR_r1 nil)
                      (setq err-pass_ 0)
                      (while ;for keep insertion point and dist. fix length one side
                        (and
                          (= (vl-catch-all-error-p ERR_r1) nil)
                          (or 
                            (= err-pass_ 0)
                          )
                        )
                        (setq ERR_r1
                          (vl-catch-all-apply
                            (function
                              (lambda ()
                                (setq target_blk_ename_ (car (entsel "specify Object or select Xline for exit")))
                                (setq target_blk_obj_ (vlax-ename->vla-object target_blk_ename_))
                                (if (= (vla-get-objectname target_blk_obj_ ) "AcDbBlockReference")
                                  (progn
                                    (setq err-pass_ 1)
                                    (vla-put-insertionpoint 
                                      (setq target_blk_obj_ (vlax-ename->vla-object target_blk_ename_))
                                      (vlax-3d-point inters_list_sorted_val_)
                                    )
                                  )
                                )
                                (if (= (vla-get-objectname target_blk_obj_ ) "AcDbXline")
                                  (progn
                                    (setq err-pass_ 1)
                                    (setvar  "osmode" 1215)
                                  )
                                )
                              )
                            )
                          )
                        )
                      )
                    ;

                    (setq inters_list_time_i_ (+ inters_list_time_i_ 1))
                    (setvar "selectionpreview" 0)
                )
              )
            )
          )
        )
        (setvar "osmode" 1215)
      ;
    )
    (defun c:insert_by_centroid_blk2ct ()
      (setvar "selectionpreview" 3)
      (setq pline_ename_ (car (entsel "specify Object")))
      (setq pline_ename_obj_ (vlax-ename->vla-object pline_ename_))
      (setq pline-intesert_obj_vertex_insxy (if (= (getvar "worlducs") 0)(progn (trans (LM:PolyCentroid pline_ename_) 1 1)) (LM:PolyCentroid pline_ename_) ))
      (setq target_blk_ename_ (car (entsel "specify Object or select Xline for exit")))
      (setq target_blk_obj_ (vlax-ename->vla-object target_blk_ename_))
      (if (= (vla-get-objectname target_blk_obj_ ) "AcDbBlockReference")
        (progn
          (setq err-pass_ 1)
          (vla-put-insertionpoint 
            (setq target_blk_obj_ (vlax-ename->vla-object target_blk_ename_))
            (vlax-3d-point pline-intesert_obj_vertex_insxy)
          )
          (setvar  "osmode" 1215)
        )
      )
      (setvar "selectionpreview" 0)
    )
    (defun c:insert_by_centroid_blk2cen ()
      (setvar "selectionpreview" 3)
      (setq point_conner (getpoint "specify conner point") )
      (setq point_upper (getcorner point_conner "specify conner point") )
      (setq assembly_coordinate_ (TA:assembly_coordinate_coner (list point_conner point_upper )))
      (setq pline-intesert_obj_vertex_insxy (if (= (getvar "worlducs") 0)(progn (trans (nth 4 assembly_coordinate_) 1 0)) (nth 4 assembly_coordinate_) ))
      (setq target_blk_ename_ (car (entsel "specify Object or select Xline for exit")))
      (setq target_blk_obj_ (vlax-ename->vla-object target_blk_ename_))
      (if (= (vla-get-objectname target_blk_obj_ ) "AcDbBlockReference")
        (progn
          (setq err-pass_ 1)
          (vla-put-insertionpoint 
            (setq target_blk_obj_ (vlax-ename->vla-object target_blk_ename_))
            (vlax-3d-point pline-intesert_obj_vertex_insxy)
          )
          (setvar  "osmode" 1215)
        )
      )
      ;SPECIAL EVENT
        (setq ERR_
          (vl-catch-all-apply
            (function
              (lambda ()
                (setq 1-2 (distance (nth 0 assembly_coordinate_) (nth 1 assembly_coordinate_)))
                (setq 1-4 (distance (nth 0 assembly_coordinate_) (nth 3 assembly_coordinate_)))
                (LM:setdynpropvalue target_blk_obj_ "distance1" 1-2 )
                (LM:setdynpropvalue target_blk_obj_ "distnace2" 1-4 )
              )
            )
          )
        )
      ; 
      (setvar "selectionpreview" 0)
    )
    (defun c:xline_intersect_block_xl4_ ()
      ;presettting
        ; (setq blkname_inter_target_ "000 - CKST_DOWNLIGHT_SYMBOL")
        ; (setq blkname_inter_target_ "000 - STARTER SYMBOL_REV03")
        ; (setq blkname_inter_target_ "A$Ce6835291")
        ; (setq blkname_inter_target_ "ACM_Linear Slot_Supply_Side Connected _1590x200x450_ - 1590x200-21133948-CONCOURSE LEVEL CB CEILING PLAN")
        ; (setq blkname_inter_ename_ (car (entsel "specify Object")))
        ; (setq blkname_inter_obj_ (vlax-ename->vla-object blkname_inter_ename_))
        ; (setq blkname_inter_obj_ro (vla-get-rotation blkname_inter_obj_ ))
        ; (setq blkname_inter_target_ (LM:effectivename blkname_inter_obj_ ))
      ;
      ;selection_set_for_fillter_blk_name
        (if  ;pre_select_ssget_or_post_select_ssget
          (=
            (setq ss_pre_filter_set_xx_ (ssget "i"
                                              (list
                                                (cons 0 "spline,xline") ;type of object
                                                ; (cons 8 "Defpoints")   ;kind of layer
                                                ; (cons 2 "000-GRID_LINE_DYN")       ;kind of nameblock
                                                ; (cons 62 6)           ;kind of color call sign with color code index
                                              )
                                        )
            )
            nil
          )
          (progn
            (setq ss_pre_filter_set_xx_ (ssget
                                              (list
                                                (cons 0 "spline,xline") ;type of object
                                                ; (cons 8 "Defpoints")   ;kind of layer
                                                ; (cons 2 "000-GRID_LINE_DYN")       ;kind of nameblock
                                                (cons 62 6)           ;kind of color call sign with color code index
                                              )
                                        )
            )
          )
          (sslength ss_pre_filter_set_xx_)
        )
      ;
      ; (setq ss_pre_filter_set_xx_ename (ssname ss_pre_filter_set_xx_ 0 ))
      ; (setq ss_pre_filter_set_xx_obj_ (vlax-ename->vla-object ss_pre_filter_set_xx_ename))
      ; (setq ss_pre_filter_set_xx_obj_ins_ (vlax-safearray->list (vlax-variant-value (vla-get-basepoint ss_pre_filter_set_xx_obj_))))
      ; (setq ss_pre_filter_set_xx_obj_2ndins_ (vlax-safearray->list (vlax-variant-value (vla-get-SecondPoint  ss_pre_filter_set_xx_obj_))))
      (setq inters_list_ (LM:intersectionsinset  ss_pre_filter_set_xx_))
      (setq inters_ss_ (ssadd))
      (setq target_blk_ename_ (car (entsel "specify Object")))
      (setq target_blk_obj_ (vlax-ename->vla-object target_blk_ename_))
      (setq target_blk_obj_ (vlax-ename->vla-object target_blk_ename_))
      (if (= (vla-get-objectname target_blk_obj_) "AcDbBlockReference")
        (progn
          (setq blkname_inter_target_ (LM:effectivename target_blk_obj_ ))
          (setq blkname_inter_target_xsc (vla-get-xeffectivescalefactor target_blk_obj_ ))
        )
      )
      
      ;preloop_and_while
        (setq inters_ss_new_trans_i 0)
        (setq inters_ss_new_trans_ ())
        (while (< inters_ss_new_trans_i (length inters_list_))
          (setq inters_ss_new_trans_val_ (if (= (getvar "worlducs") 0)(progn (trans (nth  inters_ss_new_trans_i inters_list_) 1 1)) (nth  inters_ss_new_trans_i inters_list_) ))
          (TA:vla-insertblock
            blkname_inter_target_
            inters_ss_new_trans_val_
            blkname_inter_target_xsc
            (vla-get-rotation target_blk_obj_)
          )
          ;new_blk_entlast object
            (setq new_dn_ename (entlast))
            (setq new_dn_obj (vlax-ename->vla-object new_dn_ename))
            ; (vla-put-layer new_dn_obj "E-LITE-EQPM")
            (vla-put-color new_dn_obj 256)
            (setq inters_ss_ (ssadd new_dn_ename inters_ss_))
            (if (= (vla-get-isdynamicblock target_blk_obj_) :vlax-true)
              (progn
                (setq target_blk_obj_dynprop_list_ (LM:getdynprops target_blk_obj_ ))
                ;preloop_and_while
                  (setq target_blk_obj_dynprop_list_i 0)
                  (while (< target_blk_obj_dynprop_list_i (length target_blk_obj_dynprop_list_))
                    (setq target_blk_obj_dynprop_list_tag_ (strcase (car (nth  target_blk_obj_dynprop_list_i target_blk_obj_dynprop_list_))))
                    (setq target_blk_obj_dynprop_list_val_ (cdr (nth  target_blk_obj_dynprop_list_i target_blk_obj_dynprop_list_)))
                    (if (/= (wcmatch target_blk_obj_dynprop_list_tag_ "*ORIGIN*") T)
                      (progn
                        (LM:setdynpropvalue new_dn_obj  target_blk_obj_dynprop_list_tag_ target_blk_obj_dynprop_list_val_)
                      )
                    )
                
                    (setq target_blk_obj_dynprop_list_i (+ target_blk_obj_dynprop_list_i 1))
                  )
                ;
              )
            )
          ;
          ; (setq inters_ss_new_trans_ (cons inters_ss_new_trans_val_ inters_ss_new_trans_ ))
          (setq inters_ss_new_trans_i (+ inters_ss_new_trans_i 1))
        )
      ;
      (command "pselect"  inters_ss_ "" )
    )
    (defun c:xline_intersect_block_xl2_ ()
      ;presettting
        ; (setq blkname_inter_target_ "000 - CKST_DOWNLIGHT_SYMBOL")
        ; (setq blkname_inter_target_ "000 - STARTER SYMBOL_REV03")
        ; (setq blkname_inter_target_ "A$Ce6835291")
        ; (setq blkname_inter_target_ "ACM_Linear Slot_Supply_Side Connected _1590x200x450_ - 1590x200-21133948-CONCOURSE LEVEL CB CEILING PLAN")
        ; (setq blkname_inter_ename_ (car (entsel "specify Object")))
        ; (setq blkname_inter_obj_ (vlax-ename->vla-object blkname_inter_ename_))
        ; (setq blkname_inter_obj_ro (vla-get-rotation blkname_inter_obj_ ))
        ; (setq blkname_inter_target_ (LM:effectivename blkname_inter_obj_ ))
      ;
      ;selection_set_for_fillter_blk_name
        (if  ;pre_select_ssget_or_post_select_ssget
          (=
            (setq ss_pre_filter_set_xx_ (ssget "i"
                                              (list
                                                (cons 0 "xline") ;type of object
                                                ; (cons 8 "Defpoints")   ;kind of layer
                                                ; (cons 2 "000-GRID_LINE_DYN")       ;kind of nameblock
                                                ; (cons 62 6)           ;kind of color call sign with color code index
                                              )
                                        )
            )
            nil
          )
          (progn
            (setq ss_pre_filter_set_xx_ (ssget
                                              (list
                                                (cons 0 "xline") ;type of object
                                                ; (cons 8 "Defpoints")   ;kind of layer
                                                ; (cons 2 "000-GRID_LINE_DYN")       ;kind of nameblock
                                                ; (cons 62 6)           ;kind of color call sign with color code index
                                              )
                                        )
            )
          )
          (sslength ss_pre_filter_set_xx_)
        )
      ;
      ; (setq ss_pre_filter_set_xx_ename (ssname ss_pre_filter_set_xx_ 0 ))
      ; (setq ss_pre_filter_set_xx_obj_ (vlax-ename->vla-object ss_pre_filter_set_xx_ename))
      ; (setq ss_pre_filter_set_xx_obj_ins_ (vlax-safearray->list (vlax-variant-value (vla-get-basepoint ss_pre_filter_set_xx_obj_))))
      ; (setq ss_pre_filter_set_xx_obj_2ndins_ (vlax-safearray->list (vlax-variant-value (vla-get-SecondPoint  ss_pre_filter_set_xx_obj_))))
      (setq inters_list_ (LM:intersectionsinset  ss_pre_filter_set_xx_))
      (setq inters_ss_ (ssadd))
      (setq target_blk_ename_ (car (entsel "specify Object")))
      (setq target_blk_obj_ (vlax-ename->vla-object target_blk_ename_))
      (setq target_blk_obj_ (vlax-ename->vla-object target_blk_ename_))
      (if (= (vla-get-objectname target_blk_obj_) "AcDbBlockReference")
        (progn
          (setq blkname_inter_target_ (LM:effectivename target_blk_obj_ ))
          (setq blkname_inter_target_xsc (vla-get-xeffectivescalefactor target_blk_obj_ ))
        )
      )
      
      ;preloop_and_while
        (setq inters_ss_new_trans_i 0)
        (setq inters_ss_new_trans_ ())
        (while (< inters_ss_new_trans_i (length inters_list_))
          (setq inters_ss_new_trans_val_ (if (= (getvar "worlducs") 0)(progn (trans (nth  inters_ss_new_trans_i inters_list_) 1 1)) (nth  inters_ss_new_trans_i inters_list_) ))
          (TA:vla-insertblock
            blkname_inter_target_
            inters_ss_new_trans_val_
            blkname_inter_target_xsc
            (vla-get-rotation target_blk_obj_)
          )
          ;new_blk_entlast object
            (setq new_dn_ename (entlast))
            (setq new_dn_obj (vlax-ename->vla-object new_dn_ename))
            ; (vla-put-layer new_dn_obj "E-LITE-EQPM")
            (vla-put-color new_dn_obj 256)
            (setq inters_ss_ (ssadd new_dn_ename inters_ss_))
            (if (= (vla-get-isdynamicblock target_blk_obj_) :vlax-true)
              (progn
                (setq target_blk_obj_dynprop_list_ (LM:getdynprops target_blk_obj_ ))
                ;preloop_and_while
                  (setq target_blk_obj_dynprop_list_i 0)
                  (while (< target_blk_obj_dynprop_list_i (length target_blk_obj_dynprop_list_))
                    (setq target_blk_obj_dynprop_list_tag_ (strcase (car (nth  target_blk_obj_dynprop_list_i target_blk_obj_dynprop_list_))))
                    (setq target_blk_obj_dynprop_list_val_ (cdr (nth  target_blk_obj_dynprop_list_i target_blk_obj_dynprop_list_)))
                    (if (/= (wcmatch target_blk_obj_dynprop_list_tag_ "*ORIGIN*") T)
                      (progn
                        (LM:setdynpropvalue new_dn_obj  target_blk_obj_dynprop_list_tag_ target_blk_obj_dynprop_list_val_)
                      )
                    )
                
                    (setq target_blk_obj_dynprop_list_i (+ target_blk_obj_dynprop_list_i 1))
                  )
                ;
              )
            )
          ;
          ; (setq inters_ss_new_trans_ (cons inters_ss_new_trans_val_ inters_ss_new_trans_ ))
          (setq inters_ss_new_trans_i (+ inters_ss_new_trans_i 1))
        )
      ;
      (command "pselect"  inters_ss_ "" )
    )
    (defun c:xline_intersect_block_xl3_ ()
      ;presettting
        ; (setq blkname_inter_target_ "000 - CKST_DOWNLIGHT_SYMBOL")
        ; (setq blkname_inter_target_ "000 - STARTER SYMBOL_REV03")
        ; (setq blkname_inter_target_ "A$Ce6835291")
        ; (setq blkname_inter_target_ "ACM_Linear Slot_Supply_Side Connected _1590x200x450_ - 1590x200-21133948-CONCOURSE LEVEL CB CEILING PLAN")
        ; (setq blkname_inter_ename_ (car (entsel "specify Object")))
        ; (setq blkname_inter_obj_ (vlax-ename->vla-object blkname_inter_ename_))
        ; (setq blkname_inter_obj_ro (vla-get-rotation blkname_inter_obj_ ))
        ; (setq blkname_inter_target_ (LM:effectivename blkname_inter_obj_ ))
      ;
      ;selection_set_for_fillter_blk_name
        (if  ;pre_select_ssget_or_post_select_ssget
          (=
            (setq ss_pre_filter_set_xx_ (ssget "i"
                                              (list
                                                (cons 0 "insert") ;type of object
                                                ; (cons 8 "Defpoints")   ;kind of layer
                                                ; (cons 2 "000-GRID_LINE_DYN")       ;kind of nameblock
                                                ; (cons 62 6)           ;kind of color call sign with color code index
                                              )
                                        )
            )
            nil
          )
          (progn
            (setq ss_pre_filter_set_xx_ (ssget
                                              (list
                                                (cons 0 "insert") ;type of object
                                                ; (cons 8 "Defpoints")   ;kind of layer
                                                ; (cons 2 "000-GRID_LINE_DYN")       ;kind of nameblock
                                                ; (cons 62 6)           ;kind of color call sign with color code index
                                              )
                                        )
            )
          )
          (sslength ss_pre_filter_set_xx_)
        )
      ;
      ; (setq ss_pre_filter_set_xx_ename (ssname ss_pre_filter_set_xx_ 0 ))
      ; (setq ss_pre_filter_set_xx_obj_ (vlax-ename->vla-object ss_pre_filter_set_xx_ename))
      ; (setq ss_pre_filter_set_xx_obj_ins_ (vlax-safearray->list (vlax-variant-value (vla-get-basepoint ss_pre_filter_set_xx_obj_))))
      ; (setq ss_pre_filter_set_xx_obj_2ndins_ (vlax-safearray->list (vlax-variant-value (vla-get-SecondPoint  ss_pre_filter_set_xx_obj_))))
        (setq Er-msg_ 
          (vl-catch-all-apply 
            (function 
              (lambda () 
                (setq ss_pre_filter_set_xx_ (TA:EF_Filter_ss_set_ ss_pre_filter_set_xx_ (LM:effectivename (vlax-ename->vla-object (car (entsel "filter name block")))) ))
              )
            )
          )
        )
      (if (and
            (= (vl-catch-all-error-p ERR_) T)
          )
        (progn
          (setq inters_list_ (LM:intersectionsinset  ss_pre_filter_set_xx_))
          (setq inters_ss_ (ssadd))
          (setq target_blk_ename_ (car (entsel "specify Object")))
          (setq target_blk_obj_ (vlax-ename->vla-object target_blk_ename_))
          (if (= (vla-get-objectname target_blk_obj_) "AcDbBlockReference")
            (progn
              (setq blkname_inter_target_ (LM:effectivename target_blk_obj_ ))
            )
          )
          
          ;preloop_and_while
            (setq inters_ss_new_trans_i 0)
            (setq inters_ss_new_trans_ ())
            (while (< inters_ss_new_trans_i (length inters_list_))
              (setq inters_ss_new_trans_val_ (if (= (getvar "worlducs") 0)(progn (trans (nth  inters_ss_new_trans_i inters_list_) 1 1)) (nth  inters_ss_new_trans_i inters_list_) ))
              (TA:vla-insertblock
                blkname_inter_target_
                inters_ss_new_trans_val_
                1
                (deg-to-rad 90)
              )
              ;new_blk_entlast object
                (setq new_dn_ename (entlast))
                (setq new_dn_obj (vlax-ename->vla-object new_dn_ename))
                ; (vla-put-layer new_dn_obj "E-LITE-EQPM")
                (vla-put-color new_dn_obj 256)
                (setq inters_ss_ (ssadd new_dn_ename inters_ss_))
              ;
              ; (setq inters_ss_new_trans_ (cons inters_ss_new_trans_val_ inters_ss_new_trans_ ))
              (setq inters_ss_new_trans_i (+ inters_ss_new_trans_i 1))
            )
          ;
          (command "pselect"  inters_ss_ "" )
        )
      )
    )
    (defun TA:insert_indentblk_  (target-blk_obj_ block-name_ indent_x indent_y indent_z)
      ; (setq indent_x 1750)
      ; (setq indent_y 0)
      ; (setq indent_z 0)
      ; (setq target-blk_ename_ (car (entsel "specify target Object")))
      (if (= (vla-get-objectname target-blk_obj_ ) "AcDbBlockReference")
        (progn
          ; (setq target-blk_obj_ (vlax-ename->vla-object target-blk_ename_))
          (setq target-blk_obj_ins_ (vlax-safearray->list (vlax-variant-value (vla-get-insertionpoint target-blk_obj_))))
          (if (= (getvar "worlducs") 0)(progn (setq target-blk_obj_ins_ (trans target-blk_obj_ins_ 1 1))) target-blk_obj_ins_ )
          (setq target-blk_obj_ins_re-insert_pt (list 
                                                  (if (<  indent_x 0) (progn (- (car target-blk_obj_ins_ ) indent_x) ) (+ (car target-blk_obj_ins_ ) indent_x) )
                                                  (if (<  indent_y 0) (progn (- (cadr target-blk_obj_ins_ ) indent_y) ) (+ (cadr target-blk_obj_ins_ ) indent_y) )
                                                  (if (<  indent_z 0) (progn (- (caddr target-blk_obj_ins_ ) indent_z) ) (+ (caddr target-blk_obj_ins_ ) indent_z) )
                                                )
          )
          (TA:vla-insertblock 
            block-name_
            target-blk_obj_ins_re-insert_pt
            1
            0
          )
        )
      )
    )
    (defun c:insert_by_indent_denxb_blk ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ; (setq target_block_for_indent-insert_ename_ (car (entsel "specify target_block_for_indent-insert_ename_ Object")))
      ; (setq target_block_for_indent-insert_obj_ (vlax-ename->vla-object target_block_for_indent-insert_ename_))
      ; (setq target_block_for_indent-insert_obj_EFname_ (LM:effectivename target_block_for_indent-insert_obj_ ))
      ; (setq target_block_for_indent-insert_obj_EFname_ "010 - ALU_TRAY_PANEL_FOR_AIR_GRILLE_STANDARD-SHAPE_BOTTOM-VIEW")
      ; (setq target_block_for_indent-insert_obj_EFname_ "010 - ALU_TRAY_PANEL_FOR_BLANK-RECESSED-LIGHT_STANDARD-SHAPE_BOTTOM-VIEW")
      (setq indentnamelist (list 
                      (setq indent-block_0 "blank")
                      (setq indent-block_1 "010 - ALU_TRAY_PANEL_FOR_AIR_GRILLE_STANDARD-SHAPE_BOTTOM-VIEW")
                      (setq indent-block_2 "010 - ALU_TRAY_PANEL_FOR_BLANK-RECESSED-LIGHT_STANDARD-SHAPE_BOTTOM-VIEW")
                      (setq indent-block_3 "")
                      (setq indent-block_4 "")
                      (setq indent-block_5 "")
                      (setq indent-block_6 "")
                      (setq indent-block_7 "")
                      (setq indent-block_8 "")
                      (setq indent-block_9 "")
                     )
      )
      (setq choose_indent-block_di (cond ( (getint (strcat "\nSpecify indent-block"
                                                    "\n1 = " indent-block_1 
                                                    "\n2 = " indent-block_2
                                                    "\n3 = " indent-block_3
                                                    "\n4 = " indent-block_4
                                                    "\n5 = " indent-block_5 
                                                    "\n6 = " indent-block_6 
                                                    "\n7 = " indent-block_7 
                                                    "\n8 = " indent-block_8 
                                                    "\n9 = " indent-block_9 
                                                    "\n<" 
                                                    (rtos 
                                                      (setq choose_indent-block_di (cond 
                                                                              (choose_indent-block_di)
                                                                              (1.0)
                                                                            )
                                                      )
                                                    )
                                                    "> : "
                                            ) ) ) (choose_indent-block_di) ) )
      
    
    
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (TA:insert_indentblk_ 
            ss_pre_filter_set_xx_obj_
            (nth (fix choose_indent-block_di) indentnamelist)
            1750
            0
            0
          )
          (setq ss_pre_filter_set_xx_i (+ ss_pre_filter_set_xx_i 1))
        )
      ;
    )
    (defun c:insert_by_indent_denyb_blk ()
      ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        ; (setq target_block_for_indent-insert_ename_ (car (entsel "specify target_block_for_indent-insert_ename_ Object")))
        ; (setq target_block_for_indent-insert_obj_ (vlax-ename->vla-object target_block_for_indent-insert_ename_))
        ; (setq target_block_for_indent-insert_obj_EFname_ (LM:effectivename target_block_for_indent-insert_obj_ ))
        ; (setq target_block_for_indent-insert_obj_EFname_ "010 - ALU_TRAY_PANEL_FOR_AIR_GRILLE_STANDARD-SHAPE_BOTTOM-VIEW")
        ; (setq target_block_for_indent-insert_obj_EFname_ "010 - ALU_TRAY_PANEL_FOR_BLANK-RECESSED-LIGHT_STANDARD-SHAPE_BOTTOM-VIEW")
        (setq indentnamelist (list 
                        (setq indent-block_0 "blank")
                        (setq indent-block_1 "010 - ALU_TRAY_PANEL_FOR_AIR_GRILLE_STANDARD-SHAPE_BOTTOM-VIEW")
                        (setq indent-block_2 "010 - ALU_TRAY_PANEL_FOR_BLANK-RECESSED-LIGHT_STANDARD-SHAPE_BOTTOM-VIEW")
                        (setq indent-block_3 "")
                        (setq indent-block_4 "")
                        (setq indent-block_5 "")
                        (setq indent-block_6 "")
                        (setq indent-block_7 "")
                        (setq indent-block_8 "")
                        (setq indent-block_9 "")
                      )
        )
        (setq choose_indent-block_di (cond ( (getint (strcat "\nSpecify indent-block"
                                                      "\n1 = " indent-block_1 
                                                      "\n2 = " indent-block_2
                                                      "\n3 = " indent-block_3
                                                      "\n4 = " indent-block_4
                                                      "\n5 = " indent-block_5 
                                                      "\n6 = " indent-block_6 
                                                      "\n7 = " indent-block_7 
                                                      "\n8 = " indent-block_8 
                                                      "\n9 = " indent-block_9 
                                                      "\n<" 
                                                      (rtos 
                                                        (setq choose_indent-block_di (cond 
                                                                                (choose_indent-block_di)
                                                                                (1.0)
                                                                              )
                                                        )
                                                      )
                                                      "> : "
                                              ) ) ) (choose_indent-block_di) ) )
        
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (TA:insert_indentblk_ 
            ss_pre_filter_set_xx_obj_
            (nth (fix choose_indent-block_di) indentnamelist)
            0
            1750
            0
          )
          ;new_blk_entlast object
            (setq new_ename (entlast))
            (setq new_obj (vlax-ename->vla-object new_ename))
            (setq new_obj (vla-put-rotation new_obj (deg-to-rad 90)))
          ;
          (setq ss_pre_filter_set_xx_i (+ ss_pre_filter_set_xx_i 1))
        )
      ;
    )
    (defun c:Rotate_by_basepoint_RBP ()
      (setvar "selectionpreview" 3)
      (setq target_ename_ (car (entsel "specify basepoint block Object")))
      (setq target_obj_ (vlax-ename->vla-object target_ename_))
      (setq target_obj_rotation_ (vla-get-rotation target_obj_))
      (setq target_obj_ins_ (vlax-safearray->list (vlax-variant-value (vla-get-insertionpoint target_obj_))))
      (if (= (getvar "worlducs") 0)(progn (setq target_obj_ins_ (trans target_obj_ins_ 1 1))) target_obj_ins_ )
      
      (setq rotater_ename_ (car (entsel "specify block Object for rotate")))
      (setq rotater_obj_ (vlax-ename->vla-object rotater_ename_))
      (vla-rotate rotater_obj_ (vlax-3d-point target_obj_ins_) (deg-to-rad ( - (rad-to-deg target_obj_rotation_) 90  ))  )
      (vla-put-rotation rotater_obj_ target_obj_rotation_)
      ;while selection process
        (setq ERR_ nil)
        (while ;for keep insertion point and dist. fix length one side
          (and
            (= (vl-catch-all-error-p ERR_) nil)
          )
          (setq ERR_
            (vl-catch-all-apply
              (function
                (lambda ()
                  (getstring "\nHit \nHit \nHit [ENTER] to continue...")
                  (vla-rotate rotater_obj_ (vlax-3d-point target_obj_ins_) (deg-to-rad 90) )
                  (setvar "selectionpreview" 0)
                )
              )
            )
          )
        )
      ;
    )
    (defun c:intert_by_boundary-area_blk2bol ()
      (setq vertext_seq_ 0)
      (setq blocklist_list_ (list 
                         "USER-INPUT"
                         "000 - EXISTING_COLUMN"
                         "000 - CONCRETE_WALL"
                         "000 - CONCRETE_PRECAST"
                         "010 - C10_PANEL_FRAMING_CUTVIEW"
                         "010 - C10_PANEL_ACCESSORIES_SET-1"
                         "010 - C10_PANEL_PANEL_GREEN_PLATE_SET-A-BOT-VIEW"
                         "010 - C10_PANEL_PANEL_GREEN_PLATE_SET-B-BOT-VIEW"
                         "010 - C10_PANEL_PANEL_GREEN_PLATE_SET-C-BOT-VIEW"
                         "A$C7f42c79f"
                       )
      )
      (setq blocklayer_ (list 
                          "0"
                          "000 - EXISTING_CONCRETE_CUT_COLOR_1"
                          "000 - EXISTING_CONCRETE_CUT_COLOR_5"
                          "000 - CONCRETE_PRECAST_CUT_COLOR_4"
                        )
      )
      (setq blocklayer_number (nth 0  blocklayer_))
      (setq ERR_ nil)
      (setq ERR_ (vl-catch-all-apply 
                   (function 
                     (lambda () 
                       (setq blocklist_name_ (TA:choose_list_v4 
                                               blocklist_list_
                                               "select block"
                                               blocklist_name_
                                             )
                       )
                       (if (= blocklist_name_ "USER-INPUT")
                            (progn
                              (setq blocklist_name_ (LM:effectivename 
                                                      (setq blocklist_name_obj_ (vlax-ename->vla-object 
                                                                                  (car ( entsel "specify Object" ) )
                                                                                )
                                                      )
                                                    )
                              ) 
                              
                            )
                        )
                     )
                   )
                 )
      )
      
      
      ;while selection process
        (setq ERR_ nil)
        (while ;for keep insertion point and dist. fix length one side
          (and
            (= (vl-catch-all-error-p ERR_) nil)
          )
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            ; (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                        nil
                      )
                      (progn
                        (setq ss_pre_filter_set_xx_ (ssget
                                                          (list
                                                            ; (cons 0 "INSERT") ;type of object
                                                            ; (cons 8 "000 - GRID")   ;kind of layer
                                                            ; (cons 2 "000-GRID_LINE_DYN")       ;kind of nameblock
                                                            ; (cons 62 1)           ;kind of color call sign with color code index
                                                          )
                                                    )
                        )
                      )
                      (sslength ss_pre_filter_set_xx_)
                    )
                  ;
                  (setq ssbol_vertex_list_0 (nth 0 (TA:assembly_coordinate_coner (TA:ss_vla-getboundingbox ss_pre_filter_set_xx_))))
                  (setq ssbol_vertex_list_1 (nth 1 (TA:assembly_coordinate_coner (TA:ss_vla-getboundingbox ss_pre_filter_set_xx_))))
                  (TA:vla-insertblock 
                    blocklist_name_
                    (TA:midpoint ssbol_vertex_list_0 ssbol_vertex_list_1)
                    1
                    (deg-to-rad 0)
                  )
                  (command "pselect"   "" )
                  
                  ;
                    ;new_blk_entlast object
                      ; (setq vx_list (TA:assembly_coordinate_coner (TA:ss_vla-getboundingbox ss_pre_filter_set_xx_)))
                      (setq newinsert_ename (entlast))
                      (setq newinsert_obj (vlax-ename->vla-object newinsert_ename))
                      ; (vla-put-layer newinsert_obj blocklayer_number)
                      ; (vla-put-color newinsert_obj 256)
                      (LM:setdynpropvalue newinsert_obj "distance1" (distance ssbol_vertex_list_0 ssbol_vertex_list_1))

                    ;


                  ;
                  ; ;uncomment this repeat for delete ssset 
                  ;   (repeat (setq i (sslength ss_pre_filter_set_xx_)) 
                  ;     (vla-delete 
                  ;       (vlax-ename->vla-object 
                  ;         (ssname ss_pre_filter_set_xx_ (setq i (1- i)))
                  ;       )
                  ;     )
                  ;   )
                  ; ;
                )
              )
            )
          )
        )
      ;
      
    )
    (defun c:intert_by_boundary-area_blk2bols ()
      (setq vertext_seq_ 0)
      ;selection_set_for_fillter_blk_name
        (if  ;pre_select_ssget_or_post_select_ssget
          (=
            (setq ss_pre_filter_set_xx_ (ssget "i"
                                              (list
                                                (cons 0 "INSERT,LWPOLYLINE") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT,LWPOLYLINE") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;user-input blocklist 
        (setq blocklist_list_ (list 
                          "user_input"
                          "A$Ce1a8a797"
                          "000 - EXISTING_COLUMN"
                          "000 - CONCRETE_WALL"
                          "000 - CONCRETE_PRECAST"
                          "010 - C10_PANEL_FRAMING_CUTVIEW"
                          "010 - C10_PANEL_ACCESSORIES_SET-1"
                          "010 - C10_PANEL_PANEL_GREEN_PLATE_SET-A-BOT-VIEW"
                          "010 - C10_PANEL_PANEL_GREEN_PLATE_SET-B-BOT-VIEW"
                          "010 - C10_PANEL_PANEL_GREEN_PLATE_SET-C-BOT-VIEW"
                          "300HK ORDER FROM CHINA REV.2-LOT 2_C10_3001750HK-A-PF-S-ACOUS"
                        )
        )
        (setq blocklayer_ (list 
                            "0"
                            "000 - EXISTING_CONCRETE_CUT_COLOR_1"
                            "000 - EXISTING_CONCRETE_CUT_COLOR_5"
                            "000 - CONCRETE_PRECAST_CUT_COLOR_4"
                          )
        )
        (setq blocklayer_number (nth 0  blocklayer_))
        (setq ERR_ nil)
        (setq ERR_ (vl-catch-all-apply (function (lambda () (setq blocklist_name_ (TA:choose_list_v4 blocklist_list_ "select block" blocklist_name_ ) ) ) ) ) )
        (if (= ERR_ "user_input")
          (progn
            (setq blocklist_input_obj_efname_ (LM:effectivename (setq blocklist_input_obj_ (vlax-ename->vla-object (car ( entsel "specify Object" ) ) ) ) ) )
          )
          (setq blocklist_input_obj_efname_ blocklist_name_ )
        )
      ;
      ;preloop_and_while
        (setq ss_pre_filter_set_xx_i 0)
        ; (setq dictr_ (getstring "vertical or honlizontal :"))
        (while (and 
                ;  (= (vla-get-objectname blocklist_input_obj_) "AcDbBlockReference")
                 (< ss_pre_filter_set_xx_i (sslength ss_pre_filter_set_xx_))
               )
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_getboundingbox (vla-getboundingbox ss_pre_filter_set_xx_obj_ 'min_ 'max_)) 
          (setq ss_pre_filter_set_xx_min_ (vlax-safearray->list min_)) 
          (setq ss_pre_filter_set_xx_max_ (vlax-safearray->list max_)) 
          
          (setq ssbol_vertex_list_2 (nth 2 (TA:assembly_coordinate_coner (list ss_pre_filter_set_xx_min_ ss_pre_filter_set_xx_max_ ))))
          (setq ssbol_vertex_list_3 (nth 3 (TA:assembly_coordinate_coner (list ss_pre_filter_set_xx_min_ ss_pre_filter_set_xx_max_ ))))
          (TA:vla-insertblock
            blocklist_input_obj_efname_
            (nth 0 (TA:assembly_coordinate_coner (list ss_pre_filter_set_xx_min_ ss_pre_filter_set_xx_max_ )))
            1
            (deg-to-rad 0)
          )
          ;EXTENSION_FUNCTION
            ;new_blk_entlast object
              ; (setq newcode_ename (entlast))
              ; (setq newcode_obj (vlax-ename->vla-object newcode_ename))
              ; (setq newcode_obj_layer_ (vla-put-layer newcode_obj "009 - AHP_06_DATA_TEXT" ))
              ; (setq newcode_obj_color_ (vla-put-color newcode_obj 256))
              ; (setq overerall_size_ (TA:assembly_coordinate_coner (list ss_pre_filter_set_xx_min_ ss_pre_filter_set_xx_max_ )))
              ; (setq overerall_size_1 (list 
              ;                       (distance (nth 0 overerall_size_) (nth 1 overerall_size_))
              ;                       (distance (nth 0 overerall_size_) (nth 3 overerall_size_))
              ;                     )
              ; )
              ; (if (= dictr_  "v")
              ;   (progn 
              ;     (LM:vl-setattributevalue newcode_obj "panel_length" (distance (nth 0 overerall_size_) (nth 3 overerall_size_)) )
              ;     (LM:vl-setattributevalue newcode_obj "panel_width" (distance (nth 0 overerall_size_) (nth 1 overerall_size_))  )
              ;   )
              ;   ( list
              ;     (LM:vl-setattributevalue newcode_obj "panel_length" (distance (nth 0 overerall_size_) (nth 1 overerall_size_)) )
              ;     (LM:vl-setattributevalue newcode_obj "panel_width" (distance (nth 0 overerall_size_) (nth 3 overerall_size_)) )
              ;   )
              ; )

            ;
          ;
          
          
          
          (setq ss_pre_filter_set_xx_i (+ ss_pre_filter_set_xx_i 1))
        )
      ;
      ; (setq bypass-for-kill_ss_
        ;   (vl-catch-all-apply
        ;     (function
        ;       (lambda ()
        ;         (getstring "\nHit [ENTER] to kill selection set ...")
        ;         (TA:ss-erase ss_pre_filter_set_xx_)
        ;       )
        ;     )
        ;   )
      ; )

    )
    (defun c:intert_by_boundary-area_blk4[temp] ()
      (setq vertext_seq_ 0)
      ;selection_set_for_fillter_blk_name
        (if  ;pre_select_ssget_or_post_select_ssget
          (=
            (setq ss_pre_filter_set_xx_ (ssget "i"
                                              (list
                                                (cons 0 "INSERT,LWPOLYLINE") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT,LWPOLYLINE") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_code_ss_ (ssadd))
        (setq dictr_ ;Get-string by keep previous value
            (if
              (or
                (/= (setq dictr_val (getstring (strcat "\nvertical or honlizontal <" (if dictr_ dictr_ "") ">: ") ) ) "" )
              )
                (progn
                  (setq dictr_ dictr_val)
                  (setq dictr_keep_val_ dictr_val)
                )
              (setq dictr_val dictr_keep_val_)
            )
        )
        (while (and 
                ;  (= (vla-get-objectname blocklist_input_obj_) "AcDbBlockReference")
                 (< ss_pre_filter_set_xx_i (sslength ss_pre_filter_set_xx_))
               )
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_getboundingbox (vla-getboundingbox ss_pre_filter_set_xx_obj_ 'min_ 'max_)) 
          (setq ss_pre_filter_set_xx_min_ (vlax-safearray->list min_)) 
          (setq ss_pre_filter_set_xx_max_ (vlax-safearray->list max_)) 
          
          (setq ssbol_vertex_list_2 (nth 2 (TA:assembly_coordinate_coner (list ss_pre_filter_set_xx_min_ ss_pre_filter_set_xx_max_ ))))
          (setq ssbol_vertex_list_3 (nth 3 (TA:assembly_coordinate_coner (list ss_pre_filter_set_xx_min_ ss_pre_filter_set_xx_max_ ))))
          (TA:vla-insertblock
            "000_CKST-FAMELINE_CEILING06_CODE_PANEL"
            (nth 4 (TA:assembly_coordinate_coner (list ss_pre_filter_set_xx_min_ ss_pre_filter_set_xx_max_ )))
            0.03
            (deg-to-rad 90)
          )
          ;EXTENSION_FUNCTION
            ;new_blk_entlast object
              (setq newcode_ename (entlast))
              (setq newcode_obj (vlax-ename->vla-object newcode_ename))
              (setq newcode_obj_layer_ (vla-put-layer newcode_obj "009 - AHP_06_DATA_TEXT" ))
              (setq newcode_obj_color_ (vla-put-color newcode_obj 256))
              (setq overerall_size_ (TA:assembly_coordinate_coner (list ss_pre_filter_set_xx_min_ ss_pre_filter_set_xx_max_ )))
              (setq overerall_size_1 (list 
                                    (distance (nth 0 overerall_size_) (nth 1 overerall_size_))
                                    (distance (nth 0 overerall_size_) (nth 3 overerall_size_))
                                  )
              )
              (if (= dictr_ "v")
                (progn 
                  (LM:vl-setattributevalue newcode_obj "panel_length" (distance (nth 0 overerall_size_) (nth 3 overerall_size_)) )
                  (LM:vl-setattributevalue newcode_obj "panel_width" (distance (nth 0 overerall_size_) (nth 1 overerall_size_))  )
                )
                ( list
                  (LM:vl-setattributevalue newcode_obj "panel_length" (distance (nth 0 overerall_size_) (nth 1 overerall_size_)) )
                  (LM:vl-setattributevalue newcode_obj "panel_width" (distance (nth 0 overerall_size_) (nth 3 overerall_size_)) )
                )
              )
              (setq new_code_ss_ (ssadd newcode_ename new_code_ss_))

            ;
          ;
          
          
          
          (setq ss_pre_filter_set_xx_i (+ ss_pre_filter_set_xx_i 1))
        )
      ;
      ; (setq bypass-for-kill_ss_
        ;   (vl-catch-all-apply
        ;     (function
        ;       (lambda ()
        ;         (getstring "\nHit [ENTER] to kill selection set ...")
        ;         (TA:ss-erase ss_pre_filter_set_xx_)
        ;       )
        ;     )
        ;   )
      ; )
      (command "pselect"  new_code_ss_ "" )
    )
    (defun c:insert_array_insarray ()
      (if 
        (= (setq ss_pre_filter_set_xx_ (ssget "i" (list (cons 0 "insert" ) ) ) ) nil)
        (progn 
          (setq marray_ename_ (car (entsel "specify Object")))
        )
        (setq marray_ename_ (ssname (setq ss_pre_filter_set_xx_ (ssget "i" (list (cons 0 "insert" ) ) ) ) 0 ) )
      )
        
      
      ; (setq marray_ename_ (car (entsel "specify Object")))
      (setq marray_obj_ (vlax-ename->vla-object marray_ename_))
      (setq marray_obj_ins_ (vlax-safearray->list (vlax-variant-value (vla-get-insertionpoint marray_obj_))))
      (setq marray_obj_ins_re-insert_pt (if (= (getvar "worlducs") 0)(progn (trans marray_obj_ins_ 0 1)) marray_obj_ins_ ))
      (setq user-input-point_ nil)
      (setq user-input-point_1 nil)
      (setq user-input-point_2 nil)
      (if (and 
            (= (vl-catch-all-error-p (vl-catch-all-apply (function (lambda () (setq user-input-point_1 (getpoint  "specify point" ) ) ) ) ) ) nil )
            (/= user-input-point_1 nil)
            (= (vl-catch-all-error-p (vl-catch-all-apply (function (lambda () (setq user-input-point_ (getpoint user-input-point_1 "specify point" ) ) ) ) ) ) nil )
            
          )
        (progn
        (setq mlar_current-ang_ (angle  user-input-point_1 user-input-point_ ))
        )
        (setq user-input-point_ (if (= (getvar "worlducs") 0)(progn (trans (getpoint marray_obj_ins_re-insert_pt "specify point") 1 1)) (getpoint marray_obj_ins_re-insert_pt "specify point") )
              mlar_current-ang_ (angle   marray_obj_ins_re-insert_pt user-input-point_)
        )
      )
      
      
      (setq array_length_ (cond ( (getreal (strcat "\nspecify get move to point\n<" (rtos (setq array_length_ (cond (array_length_) (0) ) ) ) "> : " ) ) ) (array_length_) ) )
      ;while selection process
        (setq ERR_ nil)
        (setq mul_i 1)
        (while ;for keep insertion point and dist. fix length one side
          (and
            (= (vl-catch-all-error-p ERR_) nil)
          )
          (setq ERR_
            (vl-catch-all-apply
              (function
                (lambda ()
                  (getstring (strcat "enter for continue"))
                )
              )
            )
          )
          (if (and 
                (= (vl-catch-all-error-p ERR_) nil)
              )
            (progn
              (vla-copy marray_obj_ )
              (vla-move 
                (vlax-ename->vla-object (entlast))
                (vlax-3d-point marray_obj_ins_re-insert_pt)
                (vlax-3d-point 
                  (polar marray_obj_ins_re-insert_pt mlar_current-ang_ (* array_length_ mul_i))
                )
                
              )
              (setq mul_i (+ mul_i 1 ))
            )
          )

        )
      ;
    )
    (defun c:special_blk-insert_tittle-block_paum1 ()
      ;selection_set_for_fillter_blk_name
        (if  ;pre_select_ssget_or_post_select_ssget
          (=
            (setq ss_pre_filter_set_xx_ (ssget "i"
                                              (list
                                                (cons 0 "INSERT,text,mtext") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT,text,mtext") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ss_fitler_mtext_ (ssget "i" 
                                         (list 
                                           (cons 0 "mtext") ;type of object
                                           (cons 8 "0")   ;kind of layer
                                           ; (cons 2 "000-GRID_LINE_DYN")       ;kind of nameblock
                                           ; (cons 62 1)           ;kind of color call sign with color code index
                                         )
                                  )
      )
      (setq ss_fitler_ttblock_ (ssget "i" 
                                         (list 
                                           (cons 0 "insert") ;type of object
                                           (cons 8 "0")   ;kind of layer
                                          ;  (cons 2 "000-GRID_LINE_DYN")       ;kind of nameblock
                                           ; (cons 62 1)           ;kind of color call sign with color code index
                                         )
                                  )
      )
      (setq ERR_ (vl-catch-all-apply (function (lambda () (setq ss_fitler_ttblock_ (TA:EF_Filter_ss_set_V2_ ss_fitler_ttblock_ (list "D5HU_FAKE")) ) ) ) ) )
      
      (setq new-asem_  (TA:ss_vla-getboundingbox ss_fitler_ttblock_ ))
      (if (/= new-asem_ nil)
        (progn
          (TA:vla-insertblock 
            "D5HU"
            (nth 0 new-asem_)
            1
            0
          )
        )
      )
      ;new_blk_entlast object
        (setq new-D5HU_ename (entlast))
        (setq new-D5HU_obj (vlax-ename->vla-object new-D5HU_ename))
        (setq ss_fitler_mtext_val (vla-get-textstring (vlax-ename->vla-object (ssname ss_fitler_mtext_ 0)))  )
        (LM:vl-setattributevalue new-D5HU_obj "TTL_PJ_NO" "FL-PJ-26-031")
        (LM:vl-setattributevalue new-D5HU_obj "TTL_PJ_NAME_" "MRT PURPLE LINE  4\\PSTATION (PP17 - PP20)")
        (LM:vl-setattributevalue new-D5HU_obj "TTL_PJ_PART-CODE" "xxx")
        (LM:vl-setattributevalue new-D5HU_obj "TTL_PJ_PART-NAME" "xxx")
        (LM:vl-setattributevalue new-D5HU_obj "TTL_PJ_MATTERIAL" "xxx")
        (LM:vl-setattributevalue new-D5HU_obj "TTL_PJ_THK" "xxx")
        (LM:vl-setattributevalue new-D5HU_obj "TTL_PJ_SPEC" "xxx")
        (LM:vl-setattributevalue new-D5HU_obj "TTL_PJ_FINISH_1" "xxx")
        
        (LM:vl-setattributevalue new-D5HU_obj "TTL_PJ_DWG_TITLE" ss_fitler_mtext_val)
        (LM:vl-setattributevalue new-D5HU_obj "TTL_PJ_DRAW-BY" "Aummarin.ltd")
        (LM:vl-setattributevalue new-D5HU_obj "TTL_PJ_CHECKED" "Aummarin.ltd")
      ;
      (TA:ss-erase ss_pre_filter_set_xx_)
    )
    (defun c:special_blk-insert_tittle-block_paum2 ()
      ;selection_set_for_fillter_blk_name
        (if  ;pre_select_ssget_or_post_select_ssget
          (=
            (setq ss_pre_filter_set_xx_ (ssget "i"
                                              (list
                                                (cons 0 "INSERT,text,mtext") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT,text,mtext") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ss_fitler_mtext_ (ssget "i" 
                                         (list 
                                           (cons 0 "mtext") ;type of object
                                           (cons 8 "0")   ;kind of layer
                                           ; (cons 2 "000-GRID_LINE_DYN")       ;kind of nameblock
                                           ; (cons 62 1)           ;kind of color call sign with color code index
                                         )
                                  )
      )
      (setq ss_fitler_ttblock_ (ssget "i" 
                                         (list 
                                           (cons 0 "insert") ;type of object
                                           (cons 8 "0")   ;kind of layer
                                          ;  (cons 2 "000-GRID_LINE_DYN")       ;kind of nameblock
                                           ; (cons 62 1)           ;kind of color call sign with color code index
                                         )
                                  )
      )
      (setq ERR_ (vl-catch-all-apply (function (lambda () (setq ss_fitler_ttblock_ (TA:EF_Filter_ss_set_V2_ ss_fitler_ttblock_ (list "D5HU_FAKE")) ) ) ) ) )
      
      (setq new-asem_  (TA:ss_vla-getboundingbox ss_fitler_ttblock_ ))
      (if (/= new-asem_ nil)
        (progn
          (TA:vla-insertblock 
            "D5HU"
            (nth 0 new-asem_)
            1
            0
          )
        )
      )
      ;new_blk_entlast object
        (setq new-D5HU_ename (entlast))
        (setq new-D5HU_obj (vlax-ename->vla-object new-D5HU_ename))
        (setq ss_fitler_mtext_val (vla-get-textstring (vlax-ename->vla-object (ssname ss_fitler_mtext_ 0)))  )
        (LM:vl-setattributevalue new-D5HU_obj "TTL_PJ_NO" "FL-PJ-26-031")
        (LM:vl-setattributevalue new-D5HU_obj "TTL_PJ_NAME_" "MRT PURPLE LINE  4\\PSTATION (PP17 - PP20)")
        (LM:vl-setattributevalue new-D5HU_obj "TTL_PJ_PART-CODE" "")
        (LM:vl-setattributevalue new-D5HU_obj "TTL_PJ_PART-NAME" "")
        (LM:vl-setattributevalue new-D5HU_obj "TTL_PJ_MATTERIAL" "")
        (LM:vl-setattributevalue new-D5HU_obj "TTL_PJ_THK" "")
        (LM:vl-setattributevalue new-D5HU_obj "TTL_PJ_SPEC" "")
        (LM:vl-setattributevalue new-D5HU_obj "TTL_PJ_FINISH_1" "paint")
        
        (LM:vl-setattributevalue new-D5HU_obj "TTL_PJ_DWG_TITLE" ss_fitler_mtext_val)
        (LM:vl-setattributevalue new-D5HU_obj "TTL_PJ_DRAW-BY" "Aummarin.ltd")
        (LM:vl-setattributevalue new-D5HU_obj "TTL_PJ_CHECKED" "Aummarin.ltd")
      ;
      (TA:ss-erase ss_pre_filter_set_xx_)
    )
    
    (defun c:paum3 ()
      ;selection_set_for_fillter_blk_name
        (if  ;pre_select_ssget_or_post_select_ssget
          (=
            (setq ss_pre_filter_set_xx_ (ssget "i"
                                              (list
                                                (cons 0 "mtext") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "mtext") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq sorted_list_ (TA:Sort_mtext_top_to_bottom_ ss_pre_filter_set_xx_))
      (setq mtext_string_list_ (mapcar (function (lambda (ename_) (vla-get-TextString (vlax-ename->vla-object ename_) ) ) ) (TA:Sort_mtext_top_to_bottom_ ss_pre_filter_set_xx_ ) ) )
      (setq attribute_tag_list_
        (list
          "TTL_PJ_PART-CODE"
          "TTL_PJ_PART-NAME"
          "TTL_PJ_MATTERIAL"
          "TTL_PJ_SPEC"
          "TTL_PJ_THK"
          "TTL_PJ_FINISH_1"
          "TTL_PJ_DWG_TITLE"
        )
      )
      ;preloop_and_while
        (setq newatt_ename_ (car (entsel "specify ttitle Object")))
        (setq newatt_obj_ (vlax-ename->vla-object newatt_ename_))
        
        (setq attribute_tag_list_i 0)
        (while (and 
                 (< attribute_tag_list_i (length attribute_tag_list_))
                 (< attribute_tag_list_i (length mtext_string_list_))
               )
          (setq attribute_tag_list_val_ (nth  attribute_tag_list_i attribute_tag_list_))
          (if (> attribute_tag_list_i 1)
            (progn
              (LM:vl-setattributevalue newatt_obj_ attribute_tag_list_val_ (TA:Mtext_format_to_text_ (nth attribute_tag_list_i mtext_string_list_)))
            )
            (LM:vl-setattributevalue newatt_obj_ attribute_tag_list_val_ (nth attribute_tag_list_i mtext_string_list_))
          )
          (setq attribute_tag_list_i (+ attribute_tag_list_i 1))
        )
      ;
      (TA:ss-erase ss_pre_filter_set_xx_)
    )
    
  ; 
  ;COUNTING_FUNC

    (defun c:counting_blklist_ ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ; 
      ;preloop_and_while
        (setq ss_pre_filter_set_xx_i 0)
        (setq ss_pre_filter_set_xx_obj_blk_efname_list_ ())
        (setq ss_pre_filter_set_xx_obj_blk_efname_list_summary_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (if (and 
                ; (= (LM:effectivename ss_pre_filter_set_xx_obj_  ) EF_targetname_)
                (= (vla-get-isdynamicblock ss_pre_filter_set_xx_obj_) :vlax-true)
              )
            (progn
              ; (setq ss_pre_filter_set_xx_obj_blk_efname_ (LM:getdynpropvalue ss_pre_filter_set_xx_obj_ "Distance1" ))
              (Setq ss_pre_filter_set_xx_obj_blk_efname_list_ (cons (list 
                                                                          (LM:effectivename ss_pre_filter_set_xx_obj_  )
                                                                    ) 
                                                                    ss_pre_filter_set_xx_obj_blk_efname_list_
                                                              )
              )
              (setq ss_pre_filter_set_xx_obj_blk_efname_list_summary_ (TA:Count_item_in_list_ ss_pre_filter_set_xx_obj_blk_efname_list_))
            )
          )
          (setq ss_pre_filter_set_xx_i (+ ss_pre_filter_set_xx_i 1))
        )
      ;
      (TA:List_to_mtext_ 
        ;TA:stanndard_lambda_sorting
          (append 
            (list (LM:effectivename ss_pre_filter_set_xx_obj_  ) )
            (setq ss_pre_filter_set_xx_obj_blk_efname_list_summary_sorted_ 
                 (vl-sort ss_pre_filter_set_xx_obj_blk_efname_list_summary_  ;bigest open indent list
                                                    (function 
                                                      (lambda (a b) 
                                                        (< (nth 0 (car a)) (nth 0 (car b)))
                                                      )
                                                    )
                                ) ;bigest close indent list
            )
          )
        ; 
        
        (getpoint "SSSS") 
        100
      )
    )
    (defun c:counting_parameter_sumparameter (/ err_)
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ERR_
        (vl-catch-all-apply
          (function
            (lambda ()
              (setq ss_pre_filter_set_xx_ (TA:EF_Filter_ss_set_ ss_pre_filter_set_xx_ 
                                            (setq EF_targetname_ (LM:EffectiveName (setq target_obj_ (vlax-ename->vla-object (setq target_ename_ (car (entsel "specify Object")))))))
                                          )
              )
            )
          )
        )
      )
      ;preloop_and_while
        (setq ss_pre_filter_set_xx_i 0)
        (setq ss_pre_filter_set_xx_obj_parameter_list_ ())
        (setq ss_pre_filter_set_xx_obj_parameter_list_summary_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (if (and 
                (= (LM:effectivename ss_pre_filter_set_xx_obj_  ) EF_targetname_)
                (= (vla-get-isdynamicblock ss_pre_filter_set_xx_obj_) :vlax-true)
              )
            (progn
              (setq ss_pre_filter_set_xx_obj_parameter_ (LM:getdynpropvalue ss_pre_filter_set_xx_obj_ "Distance1" ))
              (Setq ss_pre_filter_set_xx_obj_parameter_list_ (cons (list 
                                                                         (LM:round ss_pre_filter_set_xx_obj_parameter_)
                                                                   ) 
                                                                   ss_pre_filter_set_xx_obj_parameter_list_
                                                             )
              )
              (setq ss_pre_filter_set_xx_obj_parameter_list_summary_ (TA:Count_item_in_list_ ss_pre_filter_set_xx_obj_parameter_list_))
            )
          )
          (setq ss_pre_filter_set_xx_i (+ ss_pre_filter_set_xx_i 1))
        )
      ;
      (TA:List_to_mtext_ 
        ;TA:stanndard_lambda_sorting
          (append 
            (list (LM:effectivename ss_pre_filter_set_xx_obj_  ) )
            (setq ss_pre_filter_set_xx_obj_parameter_list_summary_sorted_ 
                 (vl-sort ss_pre_filter_set_xx_obj_parameter_list_summary_  ;bigest open indent list
                                                    (function 
                                                      (lambda (a b) 
                                                        (< (nth 0 (car a)) (nth 0 (car b)))
                                                      )
                                                    )
                                ) ;bigest close indent list
            )
          )
        ; 
        
        (getpoint "SSSS") 
        100
      )
    )
    (defun c:counting_blklist_ ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;user-input-color
        (and
          (setq usert-input-point_1 (getpoint "\nSpecify point for insert mtext : "))
          (setq usert-input-point_2 (getpoint usert-input-point_1 "\nSpecify point for insert mtext : "))
          (setq usert-input-distance_ (distance usert-input-point_1 usert-input-point_2 ))
          (setq usert-input-angle_ (angle usert-input-point_1 usert-input-point_2 ))
          (setq  usert-input-point_1_base usert-input-point_1 )
         )
      

      ;
      ; 
      ;preloop_and_while filter dynamic ef name process
        (setq ss_pre_filter_set_xx_i 0)
        (setq ss_pre_filter_set_xx_obj_blk_efname_list_ ())
        (setq ss_pre_filter_set_xx_obj_blk_efname_list_summary_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (if (and 
                ; (= (LM:effectivename ss_pre_filter_set_xx_obj_  ) EF_targetname_)
                (= (vla-get-isdynamicblock ss_pre_filter_set_xx_obj_) :vlax-true)
              )
            (progn
              ; (setq ss_pre_filter_set_xx_obj_blk_efname_ (LM:getdynpropvalue ss_pre_filter_set_xx_obj_ "Distance1" ))
              (Setq ss_pre_filter_set_xx_obj_blk_efname_list_ (cons (list 
                                                                          (LM:effectivename ss_pre_filter_set_xx_obj_  )
                                                                    ) 
                                                                    ss_pre_filter_set_xx_obj_blk_efname_list_
                                                              )
              )
              (setq ss_pre_filter_set_xx_obj_blk_efname_list_summary_ (TA:Count_item_in_list_ ss_pre_filter_set_xx_obj_blk_efname_list_))
            )
          )
          (setq ss_pre_filter_set_xx_i (+ ss_pre_filter_set_xx_i 1))
        )
      ;
      ;preloop_and_while
        (setq ss_pre_filter_set_xx_obj_blk_efname_list_summary_i 0)
        (while (< ss_pre_filter_set_xx_obj_blk_efname_list_summary_i (length ss_pre_filter_set_xx_obj_blk_efname_list_summary_))
          (setq ss_pre_filter_set_xx_obj_blk_efname_list_summary_item_ (TA:EF_Filter_ss_set_ 
                                                                          ss_pre_filter_set_xx_
                                                                          (setq ss_pre_filter_set_xx_obj_blk_efname_list_summary_efname_ 
                                                                                  (car ( car ( nth ss_pre_filter_set_xx_obj_blk_efname_list_summary_i ss_pre_filter_set_xx_obj_blk_efname_list_summary_ ) ))
                                                                          )
                                                                       )
          ) 
          ;preloop_and_while
            (setq ss_pre_filter_set_xx_obj_blk_efname_list_summary_item_i 0)
            (setq ss_pre_filter_set_xx_obj_parameter_list_ ())
            (while (< ss_pre_filter_set_xx_obj_blk_efname_list_summary_item_i (sslength ss_pre_filter_set_xx_obj_blk_efname_list_summary_item_))
              (setq ss_pre_filter_set_xx_obj_blk_efname_list_summary_item_ename_ (ssname ss_pre_filter_set_xx_obj_blk_efname_list_summary_item_ ss_pre_filter_set_xx_obj_blk_efname_list_summary_item_i))
              (setq ss_pre_filter_set_xx_obj_blk_efname_list_summary_item_obj_ (vlax-ename->vla-object  ss_pre_filter_set_xx_obj_blk_efname_list_summary_item_ename_))
              (if (and 
                    (= (LM:effectivename ss_pre_filter_set_xx_obj_blk_efname_list_summary_item_obj_  ) ss_pre_filter_set_xx_obj_blk_efname_list_summary_efname_)
                    (= (vla-get-isdynamicblock ss_pre_filter_set_xx_obj_blk_efname_list_summary_item_obj_) :vlax-true)
                  )
                (progn
                  (setq ss_pre_filter_set_xx_obj_parameter_ (LM:getdynpropvalue ss_pre_filter_set_xx_obj_blk_efname_list_summary_item_obj_ "Distance1" ))
                  (Setq ss_pre_filter_set_xx_obj_parameter_list_ (cons (list 
                                                                        ;  (LM:effectivename ss_pre_filter_set_xx_obj_blk_efname_list_summary_item_obj_  )
                                                                        (LM:round ss_pre_filter_set_xx_obj_parameter_)
                                                                      ) 
                                                                      ss_pre_filter_set_xx_obj_parameter_list_
                                                                )
                  )
                  (setq ss_pre_filter_set_xx_obj_parameter_list_summary_ (TA:Count_item_in_list_ ss_pre_filter_set_xx_obj_parameter_list_))
                )
              )
              (setq ss_pre_filter_set_xx_obj_blk_efname_list_summary_item_i (+ ss_pre_filter_set_xx_obj_blk_efname_list_summary_item_i 1))
            )
          ;
          ;
          ;insert mtext array process
            ; (TA:List_to_mtext_ 
            ;   ;TA:stanndard_lambda_sorting
            ;     (append 
            ;       (list ss_pre_filter_set_xx_obj_blk_efname_list_summary_efname_ )
            ;       (setq ss_pre_filter_set_xx_obj_parameter_list_summary_sorted_ 
            ;           (vl-sort ss_pre_filter_set_xx_obj_parameter_list_summary_  ;bigest open indent list
            ;                                               (function 
            ;                                                 (lambda (a b) 
            ;                                                   (< (nth 0 (car a)) (nth 0 (car b)))
            ;                                                 )
            ;                                               )
            ;                           ) ;bigest close indent list
            ;       )
            ;     )
            ;   ; 
            ;   (setq usert-input-point_1
            ;     (polar
            ;       usert-input-point_1_base
            ;       usert-input-angle_
            ;       (* usert-input-distance_
            ;         ss_pre_filter_set_xx_obj_blk_efname_list_summary_i
            ;       )
            ;     )
            ;   ) 
            ;   100
            ; )
          ;
          (TA:List_to_mtext_ 
            ;TA:stanndard_lambda_sorting
              (append 
                (list ss_pre_filter_set_xx_obj_blk_efname_list_summary_efname_ )
                (setq ss_pre_filter_set_xx_obj_parameter_list_summary_sorted_ 
                    (vl-sort ss_pre_filter_set_xx_obj_parameter_list_summary_  ;bigest open indent list
                                                        (function 
                                                          (lambda (a b) 
                                                            (< (nth 0 (car a)) (nth 0 (car b)))
                                                          )
                                                        )
                                    ) ;bigest close indent list
                )
              )
            ; 
            (if (= ss_pre_filter_set_xx_obj_blk_efname_list_summary_i 0)
              (progn
                usert-input-point_1
              )
              (setq mtext_vertex_list_
                (polar
                  mtext_vertex_list_base
                  usert-input-angle_
                  50
                )
              ) 
            )  
            75
          )
          ;new_blk_entlast object
            (setq mtext_ename (entlast))
            (setq mtext_obj_ (vlax-ename->vla-object mtext_ename))
            (setq mtext_obj_getboundingbox (vla-getboundingbox mtext_obj_ 'min_ 'max_)) 
            (setq mtext_min_ (vlax-safearray->list min_)) 
            (setq mtext_max_ (vlax-safearray->list max_))
            (setq mtext_vertex_list_ (nth 0 (TA:assembly_coordinate_coner (list mtext_min_ mtext_max_ ))))
            (setq mtext_vertex_list_base mtext_vertex_list_ )
          
          ;
      
          (setq ss_pre_filter_set_xx_obj_blk_efname_list_summary_i (+ ss_pre_filter_set_xx_obj_blk_efname_list_summary_i 1))
        )
      ;
    )
    
  ;
  ;LAYOUT_FUNC
    
    (defun c:F78 ()
      ;return
        (command "ucs" "world")
      ;
      ;go_to_layout-process
        (if 
          (or 
            (= (getvar "ctab") "model")
            (/= (getvar "ctab") "layout1")
          )
          (progn 
            (setvar "ctab" "layout1")
            (if  ;pre_select_ssget_or_post_select_ssget
              (=
                (setq ss_pre_filter_set_xx_ (ssget "x"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "X"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          )
        )
        (if (= (getvar "ctab") "Layout1")
          (progn
            (command "copybase" (list 0 0 0) ss_pre_filter_set_xx_ "")
            (command "layout" "n" "AR-LIGHT_E&M")

            
            (setvar "ctab" "AR-LIGHT_E&M")
            (setq delete_ss_ (ssget "X" 
                                    (list 
                                      ; (cons 0 "INSERT") ;type of object
                                      (cons 410 (getvar "CTAB"))
                                      ; (cons 8 "000 - GRID")   ;kind of layer
                                      ; (cons 2 "000-GRID_LINE_DYN")       ;kind of nameblock
                                      ; (cons 62 1)           ;kind of color call sign with color code index
                                    )
                             )
            )
            (command "erase" delete_ss_ "")
            (command "pasteclip" (list 0 0 0))
          )
        )
        (setq ss_pre_filter_set_xx_ (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )   
        ;preloop_and_while
          (setq ss_pre_filter_set_xx_ (TA:EF_Filter_ss_set_V2_ ss_pre_filter_set_xx_ (list "Title Block_Under Ground_C1 v3" "Title Block_Under Ground_C2 v3" )))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "DRAWING_NO_val" 
              (strcat 
                (LM:vl-getattributevalue ss_pre_filter_set_xx_obj_ "DRAWING_NO_val" )
                "_reviewE&M"
              )
            )
            (setq ss_pre_filter_set_xx_i (+ ss_pre_filter_set_xx_i 1))
          )
        ; 
            
      ;
      
    )
    (defun c:F79 ()
      ;return
        (command "ucs" "world")
      ;
      ;go_to_layout-process
        (if 
          (or 
            (= (getvar "ctab") "model")
            (/= (getvar "ctab") "layout1")
          )
          (progn 
            (setvar "ctab" "layout1")
            (if  ;pre_select_ssget_or_post_select_ssget
              (=
                (setq ss_pre_filter_set_xx_ (ssget "x"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "X"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          )
        )
        (if (= (getvar "ctab") "Layout1")
          (progn
            (command "copybase" (list 0 0 0) ss_pre_filter_set_xx_ "")
            (command "layout" "n" "FAMING")

            
            (setvar "ctab" "FAMING")
            (setq delete_ss_ (ssget "X" 
                                    (list 
                                      ; (cons 0 "INSERT") ;type of object
                                      (cons 410 (getvar "CTAB"))
                                      ; (cons 8 "000 - GRID")   ;kind of layer
                                      ; (cons 2 "000-GRID_LINE_DYN")       ;kind of nameblock
                                      ; (cons 62 1)           ;kind of color call sign with color code index
                                    )
                             )
            )
            (command "erase" delete_ss_ "")
            (command "pasteclip" (list 0 0 0))
          )
        )
        (setq ss_pre_filter_set_xx_set1 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )   
        ;preloop_and_while
          (setq ss_pre_filter_set_xx_ (TA:EF_Filter_ss_set_ ss_pre_filter_set_xx_set1 "Title Block_Under Ground_C1 v3"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "Title_2_val" 
              (LM:StringSubst "HANGING & FRAMING PLAN" "REFLECTED CEILING PLAN" (LM:vl-getattributevalue ss_pre_filter_set_xx_obj_ "Title_2_val" ))
            )
            (LM:vl-setattributevalue ss_pre_filter_set_xx_obj_ "DRAWING_NO_val" 
              (LM:StringSubst "-02" "-01" (LM:vl-getattributevalue ss_pre_filter_set_xx_obj_ "DRAWING_NO_val" ))
            )
            
            (setq ss_pre_filter_set_xx_i (+ ss_pre_filter_set_xx_i 1))
          )
        ; 
        (setq ss_pre_filter_set_xx_set2 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )  
        ;preloop_and_while
          (setq ss_pre_filter_set_xx_ (TA:EF_Filter_ss_set_ ss_pre_filter_set_xx_set2 "000 - CKST_HEADING_VAL"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "HEADING-NAME" 
              (LM:StringSubst "HANGING & FRAMING PLAN" "REFLECTED CEILING PLAN" (LM:vl-getattributevalue ss_pre_filter_set_xx_obj_ "HEADING-NAME" ))
            )
            (setq ss_pre_filter_set_xx_i (+ ss_pre_filter_set_xx_i 1))
          )
        ;       
      ;
      
    )
    (defun c:F80AS ()
      ;return
        (command "ucs" "world")
      ;
      ;go_to_layout-process
        (if 
          (or 
            (= (getvar "ctab") "model")
            (/= (getvar "ctab") "layout1")
          )
          (progn 
            (setvar "ctab" "layout1")
            (if  ;pre_select_ssget_or_post_select_ssget
              (=
                (setq ss_pre_filter_set_xx_ (ssget "x"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "X"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          )
        )
        (if (= (getvar "ctab") "Layout1")
          (progn
            (command "copybase" (list 0 0 0) ss_pre_filter_set_xx_ "")
            (command "layout" "n" "ASBUILT_WALL_REV02")

            
            (setvar "ctab" "ASBUILT_WALL_REV02")
            (setq delete_ss_ (ssget "X" 
                                    (list 
                                      ; (cons 0 "INSERT") ;type of object
                                      (cons 410 (getvar "CTAB"))
                                      ; (cons 8 "000 - GRID")   ;kind of layer
                                      ; (cons 2 "000-GRID_LINE_DYN")       ;kind of nameblock
                                      ; (cons 62 1)           ;kind of color call sign with color code index
                                    )
                             )
            )
            (command "erase" delete_ss_ "")
            (command "pasteclip" (list 0 0 0))
          )
        )
        (setq ss_pre_filter_set_xx_set1 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )   
        ;preloop_and_while
          (setq ss_pre_filter_set_xx_ (TA:EF_Filter_ss_set_V2_  ss_pre_filter_set_xx_set1 (list "Title Block_Under Ground_C1 v3" "Title Block_Under Ground_C2 v3")))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "Title_2_val" 
              (LM:StringSubst "REFLECTED CEILING AS-BUILT " "REFLECTED CEILING PLAN" (LM:vl-getattributevalue ss_pre_filter_set_xx_obj_ "Title_2_val" ))
            )
            (LM:vl-setattributevalue ss_pre_filter_set_xx_obj_ "DRAWING_NO_val" 
              (LM:StringSubst "-01-AS-BUILT" "-01" (LM:vl-getattributevalue ss_pre_filter_set_xx_obj_ "DRAWING_NO_val" ))
            )
            
            (setq ss_pre_filter_set_xx_i (+ ss_pre_filter_set_xx_i 1))
          )
        ; 
        (setq ss_pre_filter_set_xx_set2 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )  
        ;preloop_and_while
          (setq ss_pre_filter_set_xx_ (TA:EF_Filter_ss_set_ ss_pre_filter_set_xx_set2 "000 - CKST_HEADING_VAL"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "HEADING-NAME" 
              (LM:StringSubst "HANGING & FRAMING PLAN" "REFLECTED CEILING PLAN" (LM:vl-getattributevalue ss_pre_filter_set_xx_obj_ "HEADING-NAME" ))
            )
            (setq ss_pre_filter_set_xx_i (+ ss_pre_filter_set_xx_i 1))
          )
        ;       
      ;
      
    )
    (defun c:F90AS ()
      ;return
        (command "ucs" "world")
      ;
      ;go_to_layout-process
        (if 
          (or 
            (= (getvar "ctab") "model")
            (/= (getvar "ctab") "AREA")
          )
          (progn 
            (setvar "ctab" "AREA")
            (if  ;pre_select_ssget_or_post_select_ssget
              (=
                (setq ss_pre_filter_set_xx_ (ssget "x"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "X"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          )
        )
        (if (= (getvar "ctab") "AREA")
          (progn
            (command "copybase" (list 0 0 0) ss_pre_filter_set_xx_ "")
            (command "layout" "n" "ASBUILT_WALL_REV02")

            
            (setvar "ctab" "ASBUILT_WALL_REV02")
            (setq delete_ss_ (ssget "X" 
                                    (list 
                                      ; (cons 0 "INSERT") ;type of object
                                      (cons 410 (getvar "CTAB"))
                                      ; (cons 8 "000 - GRID")   ;kind of layer
                                      ; (cons 2 "000-GRID_LINE_DYN")       ;kind of nameblock
                                      ; (cons 62 1)           ;kind of color call sign with color code index
                                    )
                             )
            )
            (command "erase" delete_ss_ "")
            (command "pasteclip" (list 0 0 0))
          )
        )
        (setq ss_pre_filter_set_xx_set1 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )   
        ;preloop_and_while
          (setq ss_pre_filter_set_xx_ (TA:EF_Filter_ss_set_ ss_pre_filter_set_xx_set1 "Title Block_Under Ground_C1 v3"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "Title_2_val" 
              (LM:StringSubst "REFLECTED CEILING AS-BUILT " "REFLECTED CEILING PLAN" (LM:vl-getattributevalue ss_pre_filter_set_xx_obj_ "Title_2_val" ))
            )
            (LM:vl-setattributevalue ss_pre_filter_set_xx_obj_ "DRAWING_NO_val" 
              (LM:StringSubst "-01-AS-BUILT" "-01-AREA" (LM:vl-getattributevalue ss_pre_filter_set_xx_obj_ "DRAWING_NO_val" ))
            )
            
            (setq ss_pre_filter_set_xx_i (+ ss_pre_filter_set_xx_i 1))
          )
        ; 
        (setq ss_pre_filter_set_xx_set2 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )  
        ;preloop_and_while
          (setq ss_pre_filter_set_xx_ (TA:EF_Filter_ss_set_ ss_pre_filter_set_xx_set2 "000 - CKST_HEADING_VAL"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "HEADING-NAME" 
              (LM:StringSubst "CEILING (AS-BUILT)" "CEILING" (LM:vl-getattributevalue ss_pre_filter_set_xx_obj_ "HEADING-NAME" ))
            )
            (LM:setdynpropvalue ss_pre_filter_set_xx_obj_ "distance1" 0 )
            (setq ss_pre_filter_set_xx_obj_assembly_point_ (TA:assembly_coordinate_coner (cdr (TA:ename+vla-getboundingbox ss_pre_filter_set_xx_obj_))))
            (LM:setdynpropvalue ss_pre_filter_set_xx_obj_ "distance1" 
              (distance 
                (nth 0 ss_pre_filter_set_xx_obj_assembly_point_)
                (nth 1 ss_pre_filter_set_xx_obj_assembly_point_)
              )
              ; (/ (* (vla-get-xscalefactor ss_pre_filter_set_xx_obj_) 8.5) 2)
            )
            (setq ss_pre_filter_set_xx_i (+ ss_pre_filter_set_xx_i 1))
          )
        ;       
      ;
      
    )
    (defun c:F100AS ()
      ;return
        (command "ucs" "world")
      ;
      ;go_to_layout-process
        (if 
          (or 
            (= (getvar "ctab") "model")
            (/= (getvar "ctab") "Layout1")
          )
          (progn 
            (setvar "ctab" "Layout1")
            (if  ;pre_select_ssget_or_post_select_ssget
              (=
                (setq ss_pre_filter_set_xx_ (ssget "x"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "X"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          )
        )
        (if (= (getvar "ctab") "Layout1")
          (progn
            (command "copybase" (list 0 0 0) ss_pre_filter_set_xx_ "")
            (command "layout" "n" "ASBUILT_WALL_REV02")

            
            (setvar "ctab" "ASBUILT_WALL_REV02")
            (setq delete_ss_ (ssget "X" 
                                    (list 
                                      ; (cons 0 "INSERT") ;type of object
                                      (cons 410 (getvar "CTAB"))
                                      ; (cons 8 "000 - GRID")   ;kind of layer
                                      ; (cons 2 "000-GRID_LINE_DYN")       ;kind of nameblock
                                      ; (cons 62 1)           ;kind of color call sign with color code index
                                    )
                             )
            )
            (command "erase" delete_ss_ "")
            (command "pasteclip" (list 0 0 0))
          )
        )
        (setq ss_pre_filter_set_xx_set1 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )   
        ;preloop_and_while
          (setq ss_pre_filter_set_xx_ (TA:EF_Filter_ss_set_V2_ ss_pre_filter_set_xx_set1 (list "Title Block_Under Ground_C1 v3" "Title Block_Under Ground_C2 v3")))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "Title_3_val" 
              "(AS-BUILT)"
            )
            (LM:vl-setattributevalue ss_pre_filter_set_xx_obj_ "DRAWING_NO_val" 
              (LM:StringSubst "-01-AS-BUILT" "-01" (LM:vl-getattributevalue ss_pre_filter_set_xx_obj_ "DRAWING_NO_val" ))
            )
            
            (setq ss_pre_filter_set_xx_i (+ ss_pre_filter_set_xx_i 1))
          )
        ; 
        (setq ss_pre_filter_set_xx_set2 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )  
        ;preloop_and_while
          (setq ss_pre_filter_set_xx_ (TA:EF_Filter_ss_set_ ss_pre_filter_set_xx_set2 "000 - CKST_HEADING_VAL"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "HEADING-NAME" 
              (if (= (wcmatch (LM:vl-getattributevalue ss_pre_filter_set_xx_obj_ "HEADING-NAME" ) "*SHEET*") T )
                (progn
                  (strcat (LM:vl-getattributevalue ss_pre_filter_set_xx_obj_ "HEADING-NAME" ) " (AS-BUILT)" )
                )
              )
            )
            (LM:setdynpropvalue ss_pre_filter_set_xx_obj_ "distance1" 0 )
            (setq ss_pre_filter_set_xx_obj_assembly_point_ (TA:assembly_coordinate_coner (cdr (TA:ename+vla-getboundingbox ss_pre_filter_set_xx_obj_))))
            (LM:setdynpropvalue ss_pre_filter_set_xx_obj_ "distance1" 
              (distance 
                (nth 0 ss_pre_filter_set_xx_obj_assembly_point_)
                (nth 1 ss_pre_filter_set_xx_obj_assembly_point_)
              )
              ; (/ (* (vla-get-xscalefactor ss_pre_filter_set_xx_obj_) 8.5) 2)
            )
            (setq ss_pre_filter_set_xx_i (+ ss_pre_filter_set_xx_i 1))
          )
        ;       
      ;
      
    )
    (defun c:createC06layout ()
      ;return
        (command "ucs" "world")
      ;
      ;go_to_layout-process
        (if 
          (or 
            (= (getvar "ctab") "model")
            (/= (getvar "ctab") "Layout1")
          )
          (progn 
            (setvar "ctab" "Layout1")
            (if  ;pre_select_ssget_or_post_select_ssget
              (=
                (setq ss_pre_filter_set_xx_ (ssget "x"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget "X"
                                                  (list
                                                    ; (cons 0 "INSERT") ;type of object
                                                    (cons 410 (getvar "CTAB"))
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          )
        )
        (if (= (getvar "ctab") "Layout1")
          (progn
            (command "copybase" (list 0 0 0) ss_pre_filter_set_xx_ "")
            (command "layout" "n" "Layout-C06")

            
            (setvar "ctab" "Layout-C06")
            (setq delete_ss_ (ssget "X" 
                                    (list 
                                      ; (cons 0 "INSERT") ;type of object
                                      (cons 410 (getvar "CTAB"))
                                      ; (cons 8 "000 - GRID")   ;kind of layer
                                      ; (cons 2 "000-GRID_LINE_DYN")       ;kind of nameblock
                                      ; (cons 62 1)           ;kind of color call sign with color code index
                                    )
                             )
            )
            (command "erase" delete_ss_ "")
            (command "pasteclip" (list 0 0 0))
          )
        )
        (setq ss_pre_filter_set_xx_set1 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )   
        ;preloop_and_while
          (setq ss_pre_filter_set_xx_ (TA:EF_Filter_ss_set_v2_ ss_pre_filter_set_xx_set1 (list "Title Block_Under Ground_C1 v3" "Title Block_Under Ground_C2 v3" )))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "Title_3_val" 
              "(C06 - BULKHEAD)"
            )
            (LM:vl-setattributevalue ss_pre_filter_set_xx_obj_ "DRAWING_NO_val" 
              (LM:StringSubst "-03" "-01" (LM:vl-getattributevalue ss_pre_filter_set_xx_obj_ "DRAWING_NO_val" ))
            )
            
            (setq ss_pre_filter_set_xx_i (+ ss_pre_filter_set_xx_i 1))
          )
        ; 
        (setq ss_pre_filter_set_xx_set2 (ssget "X"
                                          (list
                                            (cons 0 "INSERT") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )  
        ;preloop_and_while
          (setq ss_pre_filter_set_xx_ (TA:EF_Filter_ss_set_ ss_pre_filter_set_xx_set2 "000 - CKST_HEADING_VAL"))
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (LM:vl-setattributevalue ss_pre_filter_set_xx_obj_ "HEADING-NAME" 
              (if (= (wcmatch (LM:vl-getattributevalue ss_pre_filter_set_xx_obj_ "HEADING-NAME" ) "*SHEET*") T )
                (progn
                  (strcat (LM:vl-getattributevalue ss_pre_filter_set_xx_obj_ "HEADING-NAME" ) " (C06)" )
                )
              )
            )
            (LM:setdynpropvalue ss_pre_filter_set_xx_obj_ "distance1" 0 )
            (setq ss_pre_filter_set_xx_obj_assembly_point_ (TA:assembly_coordinate_coner (cdr (TA:ename+vla-getboundingbox ss_pre_filter_set_xx_obj_))))
            (LM:setdynpropvalue ss_pre_filter_set_xx_obj_ "distance1" 
              (distance 
                (nth 0 ss_pre_filter_set_xx_obj_assembly_point_)
                (nth 1 ss_pre_filter_set_xx_obj_assembly_point_)
              )
              ; (/ (* (vla-get-xscalefactor ss_pre_filter_set_xx_obj_) 8.5) 2)
            )
            (setq ss_pre_filter_set_xx_i (+ ss_pre_filter_set_xx_i 1))
          )
        ;       
      ;
      
    )
  ;
  ;TIME_FUNC
    (defun TA:CDATE (split-sym time_format)
      (cond
        (;_case_1
          (and
              (= (type split-sym) 'str)
              (and (= (type time_format) 'str) (= time_format "MMDDYYY"))    
          )
          (progn
                (setq now_val_ (strcat 
                          (setq month_val_ (substr (rtos (getvar "cdate") 2 0) 5 2))
                          split-sym
                          (setq today_val_ (substr (rtos (getvar "cdate") 2 0) 7 2))
                          split-sym
                          (setq year_val_ (substr (rtos (getvar "cdate") 2 0) 1 4))
                        )
                )
            
          )
        )
        (;_case_2
          (and
              (= (type split-sym) 'str)
              (and (= (type time_format) 'str) (= time_format "DDMMYYYY"))    
          )
          (progn
                (setq now_val_ (strcat 
                          (setq today_val_ (substr (rtos (getvar "cdate") 2 0) 7 2))
                          split-sym
                          (setq month_val_ (substr (rtos (getvar "cdate") 2 0) 5 2))
                          split-sym
                          (setq year_val_ (substr (rtos (getvar "cdate") 2 0) 1 4))
                        )
                )
            
          )
        )
        (;_case_2
          (and
              (= (type split-sym) 'str)
              (and (= (type time_format) 'str) (= time_format "YYYYMMDD"))    
          )
          (progn
                (setq now_val_ (strcat 
                          (setq year_val_ (substr (rtos (getvar "cdate") 2 0) 1 4))    
                          split-sym  
                          (setq month_val_ (substr (rtos (getvar "cdate") 2 0) 5 2))                                 
                          split-sym                                 
                          (setq today_val_ (substr (rtos (getvar "cdate") 2 0) 7 2))
                        )
                )
            
          )
        )
        
      )
    )
  ;
  ;COLOR_FUNC
    (defun TA:put-RGB  (vla-obj R G B)
      ;Note By Code_Developer
      ;This command is designed to work exclusively with a block named 'LV_DATA_FROM_EXCEl'.
      ;The operation of the command will read the block's attribute values and generate a set of text.
      ;Fully command must have sub-functions with names starting with TA: or LM:
      ;
      ;
      ;example argument
      ; (setq R 22
      ;       G 22
      ;       B 222
      ; )
      ;
      (setq truecolor_obj_ (vla-get-truecolor vla-obj ))
      (vla-setrgb truecolor_obj_ R G B)
      (vla-put-TrueColor  vla-obj truecolor_obj_)
    )
    (defun c:deep_color_DPC ()
      (setq DEEP_color_ename_ (car (nentsel "specify Object")))
      (setq DEEP_color_obj_ (vlax-ename->vla-object DEEP_color_ename_))
      (vla-get-layer DEEP_color_obj_ )
      (vla-put-color DEEP_color_obj_ 
        (setq LV_3_ans_int_ (cond ( (getint (strcat "\nspecify get move to point\n<" (rtos (setq LV_3_ans_int_ (cond (LV_3_ans_int_) (0) ) ) ) "> : " ) ) ) (LV_3_ans_int_) ) )
      )
    )
  ;
  ;STR_FUNC
    (defun TA:rightstr (str_value_ right_value_)
      ; (setq str_value_ "abcdefg")
      ; (setq right_value_ 2)
      (setq str_value_length (strlen str_value_))
      (substr str_value_ (- (+ str_value_length 1) right_value_ ) 100)
    )
    (defun c:combinetext ()
      (setvar "selectionpreview" 3)
      (setq combine-text_ () )
      (setq err_ nil )
      (while (/= (wcmatch (strcase (vl-princ-to-string err_)) "*ERROR*") T) 
        (setq err_ (vl-catch-all-apply 
                    (function 
                      (lambda () 
                        (setq combine-text_ (cons (vla-get-textstring (setq ee (vlax-ename->vla-object (car (entsel "specify Object")) ) ) ) combine-text_ ) )
                      )
                    )
                  )
        )
      )
      
      (create-text-vla 
        (vlax-3d-point (if (= (getvar "worlducs") 0)(progn (setq VPBB_min_ (trans (getpoint "specify point") 1 0))) (getpoint "specify point") ))
        
        (LM:lst->str (reverse combine-text_) "")
        50
        0
      )
    )
    (defun TA:ss_text_to_list
      (
        ss_
        /
        ss_i_
        text_ename_
        text_obj_
        point_
        data_list_
      )

      (vl-load-com)
      (setq ss_i_ 0)
      (setq data_list_ nil)

      (if (and ss_ (eq (type ss_) 'PICKSET))
        (progn
          (while (< ss_i_ (sslength ss_))
            (setq text_ename_ (ssname ss_ ss_i_))
            (setq text_obj_ (vlax-ename->vla-object text_ename_))

            (if
              (and
                (vlax-property-available-p text_obj_ 'TextString)
                (vlax-property-available-p text_obj_ 'InsertionPoint)
              )
              (progn
                ;; InsertionPoint เป็น WCS; แปลงเป็น UCS ปัจจุบันก่อนเรียง
                (setq point_
                  (vlax-safearray->list
                    (vlax-variant-value
                      (vla-get-InsertionPoint text_obj_)
                    )
                  )
                )
                (setq point_ (trans point_ 0 1))

                (setq data_list_
                  (cons
                    (list (vla-get-TextString text_obj_) point_ ss_i_)
                    data_list_
                  )
                )
              )
            )

            (setq ss_i_ (1+ ss_i_))
          )

          (setq data_list_
            (vl-sort
              data_list_
              (function
                (lambda (a_ b_ / xa_ xb_ ya_ yb_)
                  (setq xa_ (car (cadr a_)))
                  (setq xb_ (car (cadr b_)))
                  (setq ya_ (cadr (cadr a_)))
                  (setq yb_ (cadr (cadr b_)))

                  (cond
                    ((/= ya_ yb_) (> ya_ yb_))
                    ((/= xa_ xb_) (< xa_ xb_))
                    (T (< (caddr a_) (caddr b_)))
                  )
                )
              )
            )
          )

          (mapcar 'car data_list_)
        )
      )
    )
  ;
  ;UCS_FUNC
    (defun TA:saveucs () 
      (if (= (getvar "worlducs") 0)
        (progn
          (setq save-ucs (getvar "UCSORG"))
          (setq save-ucs-ang (atof (angtos (angle '(0 0 0) (getvar "UCSXDIR")) 0 2)))
        )
      )
      (setq save-ucs-data (list save-ucs save-ucs-ang))
    )
    (defun c:saveucs ()
      (if (= (getvar "worlducs") 0)
        (progn
          (setq save-ucs (getvar "UCSORG"))
          (setq save-ucs-ang (atof (angtos (angle '(0 0 0) (getvar "UCSXDIR")) 0 2)))
          
        )
      )
      
    )
    (defun c:loaducs ()
      (if (= (getvar "worlducs") 0)
        (progn
          (setq curent-ucs-ang (atof (angtos (angle '(0 0 0) (getvar "UCSXDIR")) 0 2)))
          (setq curent-new_ucs-ang (+ (- curent-ucs-ang 360 ) (* -1 save-ucs-ang )) )
          (command "ucs" (trans save-ucs 0 1) "" )
          (command "ucs" "z" (- 360 curent-ucs-ang  ) )
          (command "ucs" "z" save-ucs-ang )
          
        )
      )
      
    )
    (defun TA:loaducs (save-ucs save-ucs-ang)
      (if (= (getvar "worlducs") 0)
        (progn
          (setq curent-ucs-ang (atof (angtos (angle '(0 0 0) (getvar "UCSXDIR")) 0 2)))
          (setq curent-new_ucs-ang (+ (- curent-ucs-ang 360 ) (* -1 save-ucs-ang )) )
          (command "ucs" (trans save-ucs 0 1) "" )
          (command "ucs" "z" (- 360 curent-ucs-ang  ) )
          (command "ucs" "z" save-ucs-ang )
          
        )
      )
      
    )
    (defun TA:get-ins-current (point_) 
      (if (= (getvar "WORLDUCS") 1) 
        point_ ; ตอนนี้ใช้ World UCS: คืนค่าเดิม
        (trans point_ 0 1) ; ตอนนี้ใช้ UCS อื่น: แปลง WCS → UCS
      )
    )
    (defun c:saveview(/ name)
      (setq name "TA_LAST_PAPER_VIEW")
      (setq cur-view-center (getvar "VIEWCTR"))
      (setq cur-view-size   (getvar "VIEWSIZE"))
    )
    (defun c:loadview (/ name)
      (vla-ZoomCenter 
        (vlax-get-acad-object)
        (vlax-3d-point cur-view-center)
        cur-view-size
      )
    )

  ;
  ;VIEWPORT_FUNC
    (defun c:vp10asdasdas ()
        (setq vp_ss_ (ssget "i" (list (cons 0 "VIEWPORT") (cons 410 (getvar "CTAB")))))
        (setq vp_ss_ename (ssname vp_ss_ 0))
        (setq vp1_obj_ (vlax-ename->vla-object vp_ss_ename))
        (setq vp1_obj_cenpt (vlax-safearray->list (vlax-variant-value (vla-get-center vp1_obj_))))
        (setq vp1_obj_cussc (/ 1 (vla-get-customscale vp1_obj_ )))
        (command "scale"  vp_ss_ename     )
      (vla-put-customscale vp1_obj_ (/ (float 1) (float 10)))
      (vlax-dump-object vp1_obj_)
      (vla-put-DisplayLocked vp1_obj_ :vlax-true)
    )
    (defun c:viewport_vpbubble_ ()
      (setq VPBB_ename_ (car (entsel "specify Object")))
      (setq VPBB_obj_ (vlax-ename->vla-object VPBB_ename_))
      (setq y (LM:getdynpropvalue VPBB_obj_ "distance1"))
      (setq x (LM:getdynpropvalue VPBB_obj_ "distance2"))
      (setq px1 (LM:getdynpropvalue VPBB_obj_ "position2 x"))
      (setq py1 (LM:getdynpropvalue VPBB_obj_ "position2 y"))
      (setq VPBB_obj_getboundingbox (vla-getboundingbox VPBB_obj_ 'min_ 'max_)) 
      
      (setq VPBB_min_ (vlax-safearray->list min_)) 
      (setq VPBB_max_ (vlax-safearray->list max_)) 
      (if (= (getvar "worlducs") 0)(progn (setq VPBB_min_ (trans VPBB_min_ 0 1))) VPBB_min_ )
      (if (= (getvar "worlducs") 0)(progn (setq VPBB_max_ (trans VPBB_max_ 0 1))) VPBB_max_ )
      (setq sc_val (getreal "specify scale factor for viewport bubble : " ))
      (vla-put-xscalefactor VPBB_obj_ sc_val ) 
      (vla-put-yscalefactor VPBB_obj_ sc_val ) 
      (vla-put-zscalefactor VPBB_obj_ sc_val ) 
      
      ; (setq new_obj_getboundingbox (vla-getboundingbox VPBB_obj_ 'min_ 'max_)) 
      ; (setq new_min_ (vlax-safearray->list min_)) 
      ; (setq new_max_ (vlax-safearray->list max_)) 
      ; (if (= (getvar "worlducs") 0)(progn (setq new_min_ (trans new_min_ 0 1))) new_min_ )
      ; (if (= (getvar "worlducs") 0)(progn (setq new_max_ (trans new_max_ 0 1))) new_max_ )
      ; (vla-move VPBB_obj_ (vlax-3d-point new_min_) (vlax-3d-point VPBB_min_))
      (LM:setdynpropvalue VPBB_obj_ "distance1" y)
      (LM:setdynpropvalue VPBB_obj_ "distance2" x)
      (LM:setdynpropvalue VPBB_obj_ "position2 x" px1)
      (LM:setdynpropvalue VPBB_obj_ "position2 y" py1)
    )
    (defun c:viewport_vpmultimove ()
      (defun TAS:convert-list-ucs (lst /)
        (mapcar
          '(lambda (a)
            (list
              (car a)
              (trans (cadr a) 0 1)
            )
          )
          lst
        )
      )
      (_startundo doc)
      ;block for selection and sorting
        ;selection_set_for_fillter_blk_name
          (if  ;pre_select_ssget_or_post_select_ssget
            (=
              (setq ss_pre_filter_set_xx_ (ssget "i"
                                                (list
                                                  (cons 0 "INSERT") ;type of object
                                                  ; (cons 8 "C0x_300HK_CODE_*")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "C0x_300HK_CODE_*")   ;kind of layer
                                                  ; (cons 2 "000-GRID_LINE_DYN")       ;kind of nameblock
                                                  ; (cons 62 1)           ;kind of color call sign with color code index
                                                )
                                          )
              )
            )
            (sslength ss_pre_filter_set_xx_)
          )
          (setq ss_pre_filter_set_xx_list_ (TA:standard_list_croodinate_sorting ss_pre_filter_set_xx_ "X"))
        ;
        (setq tol 0.01)
        (if (= (getvar "worlducs" ) 0 )
          (progn
            (setq ss_pre_filter_set_xx_list_ (TAS:convert-list-ucs ss_pre_filter_set_xx_list_))
            (setq sorted_
              (vl-sort ss_pre_filter_set_xx_list_
                '(lambda (a b)

                  (setq ya (cadr (cadr a)))
                  (setq yb (cadr (cadr b)))

                  (setq xa (car (cadr a)))
                  (setq xb (car (cadr b)))

                  (if (> (abs (- ya yb)) tol)
                    (> ya yb) ; แถวบน -> ล่าง
                    (< xa xb) ; ซ้าย -> ขวา
                  )

                )
              )

            )
          )
          (setq sorted_
            (vl-sort ss_pre_filter_set_xx_list_
              '(lambda (a b)

                (setq ya (cadr (cadr a)))
                (setq yb (cadr (cadr b)))

                (setq xa (car (cadr a)))
                (setq xb (car (cadr b)))

                (if (> (abs (- ya yb)) tol)
                  (> ya yb) ; แถวบน -> ล่าง
                  (< xa xb) ; ซ้าย -> ขวา
                )

              )
            )
          )
          
        ) 
      ;
      ;lwpolyine for viewport 
        ;selection_set_for_fillter_blk_name
          (if  ;pre_select_ssget_or_post_select_ssget 
            (=
              (setq ss_pre_filter_set_xx_ (ssget "i"
                                                (list
                                                  (cons 0 "lwpolyline") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "lwpolyline") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        ;preloop_and_while
          (setq ss_pre_filter_set_xx_i 0)
          (setq for-moving_list_ ())
          (while (< ss_pre_filter_set_xx_i (sslength ss_pre_filter_set_xx_))
            (setq ss_pre_filter_set_xx_ename_ (ssname ss_pre_filter_set_xx_ ss_pre_filter_set_xx_i)) 
            (setq ss_pre_filter_set_xx_obj_ (vlax-ename->vla-object  ss_pre_filter_set_xx_ename_))
            (setq ss_pre_filter_set_xx_obj_getboundingbox (vla-getboundingbox ss_pre_filter_set_xx_obj_ 'min_ 'max_ ) )
            (setq assembly_xy_ (nth 4 (TA:assembly_coordinate_coner (list (vlax-safearray->list min_ ) (vlax-safearray->list max_ ) ) )) )
            (setq vp-list_ (list ss_pre_filter_set_xx_ename_ (list (car assembly_xy_) (cadr assembly_xy_) 0)))
            (setq for-moving_list_ (cons vp-list_ for-moving_list_))
            (setq ss_pre_filter_set_xx_i (+ ss_pre_filter_set_xx_i 1))
          )
        ;
        (setq tol 0.01)
        (if (= (getvar "worlducs" ) 0 )
          (progn
            (setq for-moving_list_ (TAS:convert-list-ucs for-moving_list_))
            (setq for-moving_list_sorted_
              (vl-sort for-moving_list_
                '(lambda (a b)

                  (setq ya (cadr (cadr a)))
                  (setq yb (cadr (cadr b)))

                  (setq xa (car (cadr a)))
                  (setq xb (car (cadr b)))

                  (if (> (abs (- ya yb)) tol)
                    (> ya yb) ; แถวบน -> ล่าง
                    (< xa xb) ; ซ้าย -> ขวา
                  )

                )
              )

            )
          )
          (setq for-moving_list_sorted_
            (vl-sort for-moving_list_
              '(lambda (a b)

                (setq ya (cadr (cadr a)))
                (setq yb (cadr (cadr b)))

                (setq xa (car (cadr a)))
                (setq xb (car (cadr b)))

                (if (> (abs (- ya yb)) tol)
                  (> ya yb) ; แถวบน -> ล่าง
                  (< xa xb) ; ซ้าย -> ขวา
                )

              )
            )
          )
        )
      ;
      ;preloop_and_while
        (setq for-moving_list_sorted_i 0)
        (setq ERR_bypass-1 nil)
        (setq ERR_bypass-2 nil)
        (while (and 
                 (= (vl-catch-all-error-p ERR_bypass-1) nil)
                 (= (vl-catch-all-error-p ERR_bypass-2) nil)
                 (< for-moving_list_sorted_i (length for-moving_list_sorted_))
                 (< for-moving_list_sorted_i (length sorted_))
               )
          (setq ERR_bypass-1
            (vl-catch-all-apply
              (function
                (lambda () 
                  (setq for-moving_list_sorted_ename_ (car (nth  for-moving_list_sorted_i for-moving_list_sorted_)))   
                  (setq for-moving_list_sorted_obj_ (vlax-ename->vla-object  for-moving_list_sorted_ename_))
                  (setq for-moving_list_sorted_ins_ (cadr (nth  for-moving_list_sorted_i for-moving_list_sorted_)))
                )
              )
            )
          )
          (if (and
                (= (vl-catch-all-error-p ERR_bypass-1) nil)
              )
            (progn
              (setq ERR_bypass-2
                (vl-catch-all-apply
                  (function
                    (lambda ()
                      (setq sorted_ins_ (cadr (nth for-moving_list_sorted_i sorted_)))
                      (vla-move for-moving_list_sorted_obj_ (vlax-3d-point for-moving_list_sorted_ins_) (vlax-3d-point sorted_ins_))
                      
                    )
                  )
                )
              )
            )
          )
          (setq for-moving_list_sorted_i (+ for-moving_list_sorted_i 1))
        )
      ;
      (_endUndo doc)
    )

  ;
  ;Dyeing Layer 
    (defun c:Dyeing_layer_Dyebyname ()
      (setq line_color 256)
      (setq layer_name "000 - 0_HIDE_OBJ_FRAMING_DEF_DIMS")
      (defun TA:all-editblock_ (blockname line_color layer_name)
        ; (setq blockname "PZG35")
        ; (setq line_color 256)
        ; (setq layer_name "008 - E&M_ACESSORIES_MAIN_COLOR_1")
        (setq target_ '())
        (setq blkdef (tblobjname "BLOCK" blockname))
        (setq ent (entnext blkdef))
        (while ent
          (setq ed (entget ent))
          (if (= (cdr (assoc 0 ed)) "HATCH")
            (progn
              (setq target_ (cons ent target_))
              ;main idea of code keep or delete don't affect with core code
                (setq target_obj_ (vlax-ename->vla-object (cdr (assoc -1 ed))))
                (vla-put-color target_obj_  line_color)
                (vla-put-layer target_obj_  layer_name)
                ; (vla-put-EntityTransparency target_obj_ 80 )
              ;
            )
          )
          (if (= (cdr (assoc 0 ed)) "ARC")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "LINE")
            (progn
              ; (setq target_ (cons ent target_))
              ;main idea of code keep or delete don't affect with core code
                (setq target_obj_ (vlax-ename->vla-object (cdr (assoc -1 ed))))
                (if (/= (vla-get-layer target_obj_ ) "A-ANNO-SYMB")
                  (progn
                    (vla-put-color target_obj_  line_color)
                    (vla-put-layer target_obj_  layer_name)
                  )
                )
              ;
            )
          )
          (if (= (cdr (assoc 0 ed)) "LWPOLYLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "SPLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ELLIPSE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "CIRCLE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "TEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "MTEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ATTDEF")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (setq ent (entnext ent))
        )
        (reverse target)
      )
      (defun TA:Aassembly_all_nest_block (blkName / blkEnt ent elist result)
        (setq blkEnt (tblobjname "BLOCK" blkName))

        (while (setq blkEnt (entnext blkEnt))
          (setq elist (entget blkEnt))

          (if (= (cdr (assoc 0 elist)) "ENDBLK")
            (setq blkEnt nil)
            (progn
              (if (= (cdr (assoc 0 elist)) "INSERT")
                (progn
                  (setq result
                    (cons (cdr (assoc 2 elist)) result)
                  )
                  ;; recurse หา block ซ้อน
                  (setq result
                    (append result
                      (TA:Aassembly_all_nest_block (cdr (assoc 2 elist)))
                    )
                  )
                )
              )
            )
          )
        )
        result
      )
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (TA:interface_text_ T)
      (textscr)
      (getstring "\nHit [ENTER] to continue...")
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_Efname_ (LM:Effectivename ss_pre_filter_set_xx_obj_))
          (vla-put-color ss_pre_filter_set_xx_obj_  line_color)
          (vla-put-layer ss_pre_filter_set_xx_obj_  layer_name)
          ; (setq ss_pre_filter_set_xx_obj_lv1 (TA:Assembly_block_ ss_pre_filter_set_xx_obj_ ))
          (setq blk-count_list_ (TA:Count_item_in_list_ (TA:Aassembly_all_nest_block ss_pre_filter_set_xx_obj_Efname_)))
          (TA:all-editblock_ ss_pre_filter_set_xx_obj_Efname_ line_color layer_name)
          ;preloop_and_while
            (setq blk-count_list_i 0)
            (while (< blk-count_list_i (length blk-count_list_))
              (setq blk-count_list_efname_ (car (nth  blk-count_list_i blk-count_list_)))
              (TA:all-editblock_ blk-count_list_efname_ line_color layer_name)
              (TA:textscr_process_V2 "\nupdate dynamic" blk-count_list_i blk-count_list_)

                
              (setq blk-count_list_i (+ blk-count_list_i 1))
            )
          ;
          (setq ss_pre_filter_set_xx_i (+ ss_pre_filter_set_xx_i 1))
        )
      ;
      
    )
    (defun c:Dyeing_layer_object_dyeobj ()
      (setq line_color 256)
      (defun TA:all-editblock_ (blockname line_color layer_name)
        ; (setq blockname "PZG35")
        ; (setq line_color 256)
        ; (setq layer_name "008 - E&M_ACESSORIES_MAIN_COLOR_1")
        (setq target_ '())
        (setq blkdef (tblobjname "BLOCK" blockname))
        (setq ent (entnext blkdef))
        (while ent
          (setq ed (entget ent))
          (if (= (cdr (assoc 0 ed)) "HATCH")
            (progn
              (setq target_ (cons ent target_))
              ;main idea of code keep or delete don't affect with core code
                (setq target_obj_ (vlax-ename->vla-object (cdr (assoc -1 ed))))
                (vla-put-color target_obj_  line_color)
                (vla-put-layer target_obj_  layer_name)
                ; (vla-put-EntityTransparency target_obj_ 80 )
              ;
            )
          )
          (if (= (cdr (assoc 0 ed)) "ARC")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "LINE")
            (progn
              ; (setq target_ (cons ent target_))
              ;main idea of code keep or delete don't affect with core code
                (setq target_obj_ (vlax-ename->vla-object (cdr (assoc -1 ed))))
                (if (/= (vla-get-layer target_obj_ ) "A-ANNO-SYMB")
                  (progn
                    (vla-put-color target_obj_  line_color)
                    (vla-put-layer target_obj_  layer_name)
                  )
                )
              ;
            )
          )
          (if (= (cdr (assoc 0 ed)) "LWPOLYLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "SPLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ELLIPSE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "CIRCLE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "TEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "MTEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ATTDEF")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (setq ent (entnext ent))
        )
        (reverse target)
      )
      (defun TA:Aassembly_all_nest_block (blkName / blkEnt ent elist result)
        (setq blkEnt (tblobjname "BLOCK" blkName))

        (while (setq blkEnt (entnext blkEnt))
          (setq elist (entget blkEnt))

          (if (= (cdr (assoc 0 elist)) "ENDBLK")
            (setq blkEnt nil)
            (progn
              (if (= (cdr (assoc 0 elist)) "INSERT")
                (progn
                  (setq result
                    (cons (cdr (assoc 2 elist)) result)
                  )
                  ;; recurse หา block ซ้อน
                  (setq result
                    (append result
                      (TA:Aassembly_all_nest_block (cdr (assoc 2 elist)))
                    )
                  )
                )
              )
            )
          )
        )
        result
      )
      (setq ERR_
        (vl-catch-all-apply
          (function
            (lambda ()
              (setq layer_ename_ (car (entsel "specify Object")))
              (setq layer_obj_ (vlax-ename->vla-object layer_ename_))
              (setq layer_obj_name_ (vla-get-layer layer_obj_))
              
            )
          )
        )
      )
      (if (/= (vl-catch-all-error-p ERR_) T) 
        (progn 
                      ;selection_set_for_fillter_blk_name
              (if  ;pre_select_ssget_or_post_select_ssget
                (=
                  (setq ss_pre_filter_set_xx_ (ssget "i"
                                                    (list
                                                      (cons 0 "INSERT") ;type of object
                                                      ; (cons 8 "000 - GRID")   ;kind of layer
                                                      ; (cons 2 "000-GRID_LINE_DYN")       ;kind of nameblock
                                                      ; (cons 62 1)           ;kind of color call sign with color code index
                                                    )
                                              )
                  )
                  nil
                )
                (progn
                  (setq ss_pre_filter_set_xx_ (ssget
                                                    (list
                                                      ; (cons 0 "INSERT") ;type of object
                                                      ; (cons 8 "000 - GRID")   ;kind of layer
                                                      ; (cons 2 "000-GRID_LINE_DYN")       ;kind of nameblock
                                                      ; (cons 62 1)           ;kind of color call sign with color code index
                                                    )
                                              )
                  )
                )
                (sslength ss_pre_filter_set_xx_)
              )
            ;
            (TA:interface_text_ T)
            (textscr)
            (getstring "\nHit [ENTER] to continue...")
            ;preloop_and_while
              (setq ss_pre_filter_set_xx_i 0)
              (while (< ss_pre_filter_set_xx_i (sslength ss_pre_filter_set_xx_))
                (setq ss_pre_filter_set_xx_ename_ (ssname ss_pre_filter_set_xx_ ss_pre_filter_set_xx_i))
                (setq ss_pre_filter_set_xx_obj_ (vlax-ename->vla-object  ss_pre_filter_set_xx_ename_))
                
                (vla-put-color ss_pre_filter_set_xx_obj_  line_color)
                (vla-put-layer ss_pre_filter_set_xx_obj_  layer_obj_name_)
                (setq ss_pre_filter_set_xx_obj_Efname_ (LM:Effectivename ss_pre_filter_set_xx_obj_))
                ; (setq ss_pre_filter_set_xx_obj_lv1 (TA:Assembly_block_ ss_pre_filter_set_xx_obj_ ))
                (setq blk-count_list_ (TA:Count_item_in_list_ (TA:Aassembly_all_nest_block ss_pre_filter_set_xx_obj_Efname_)))
                (TA:all-editblock_ ss_pre_filter_set_xx_obj_Efname_ line_color layer_obj_name_)
                ;preloop_and_while
                  (setq blk-count_list_i 0)
                  (while (< blk-count_list_i (length blk-count_list_))
                    (setq blk-count_list_efname_ (car (nth  blk-count_list_i blk-count_list_)))
                    (TA:all-editblock_ blk-count_list_efname_ line_color layer_obj_name_)
                    (TA:textscr_process_V2 "\nupdate dynamic" blk-count_list_i blk-count_list_)

                      
                    (setq blk-count_list_i (+ blk-count_list_i 1))
                  )
                ;
                (setq ss_pre_filter_set_xx_i (+ ss_pre_filter_set_xx_i 1))
              )
            ;
        )
      )
    )
    (defun c:Dyeing_layer_object_dyeLIST ()
      (setq line_color 256)
      (setq layer_list_ (list 
                              "USER INPUT LAYER"
                              "000 - 0_HIDE_OBJ_FRAMING_DEF_SUB" 
                              "000 - 0_HIDE_OBJ_FRAMING_DEF_SUB_1"
                              "000 - CONCRETE_PRECAST_MAIN_COLOR_1" 
                              "010 - ASPG_FLASHING_MAIN_COLOR_1"
                              "010 - C10_PANEL_ACCESSORIES_MAIN_COLOR_2"
                        )
      )
      (defun TA:all-editblock_ (blockname line_color layer_name)
        ; (setq blockname "PZG35")
        ; (setq line_color 256)
        ; (setq layer_name "008 - E&M_ACESSORIES_MAIN_COLOR_1")
        (setq target_ '())
        (setq blkdef (tblobjname "BLOCK" blockname))
        (setq ent (entnext blkdef))
        (while ent
          (setq ed (entget ent))
          (if (= (cdr (assoc 0 ed)) "HATCH")
            (progn
              (setq target_ (cons ent target_))
              ;main idea of code keep or delete don't affect with core code
                (setq target_obj_ (vlax-ename->vla-object (cdr (assoc -1 ed))))
                (vla-put-color target_obj_  line_color)
                (vla-put-layer target_obj_  layer_name)
                ; (vla-put-EntityTransparency target_obj_ 80 )
              ;
            )
          )
          (if (= (cdr (assoc 0 ed)) "ARC")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "LINE")
            (progn
              ; (setq target_ (cons ent target_))
              ;main idea of code keep or delete don't affect with core code
                (setq target_obj_ (vlax-ename->vla-object (cdr (assoc -1 ed))))
                (if (/= (vla-get-layer target_obj_ ) "A-ANNO-SYMB")
                  (progn
                    (vla-put-color target_obj_  line_color)
                    (vla-put-layer target_obj_  layer_name)
                  )
                )
              ;
            )
          )
          (if (= (cdr (assoc 0 ed)) "LWPOLYLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "SPLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ELLIPSE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "CIRCLE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "TEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "MTEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ATTDEF")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (setq ent (entnext ent))
        )
        (reverse target)
      )
      (defun TA:Aassembly_all_nest_block (blkName / blkEnt ent elist result)
        (setq blkEnt (tblobjname "BLOCK" blkName))

        (while (setq blkEnt (entnext blkEnt))
          (setq elist (entget blkEnt))

          (if (= (cdr (assoc 0 elist)) "ENDBLK")
            (setq blkEnt nil)
            (progn
              (if (= (cdr (assoc 0 elist)) "INSERT")
                (progn
                  (setq result
                    (cons (cdr (assoc 2 elist)) result)
                  )
                  ;; recurse หา block ซ้อน
                  (setq result
                    (append result
                      (TA:Aassembly_all_nest_block (cdr (assoc 2 elist)))
                    )
                  )
                )
              )
            )
          )
        )
        result
      )
      (setq ERR_
        (vl-catch-all-apply
          (function
            (lambda ()
              (setq layer_obj_name_ (TA:choose_list_v4 
                                      layer_list_
                                      "select block"
                                      layer_obj_name_
                                    )
              )
            )
          )
        )
      )
      (if (= layer_obj_name_ "USER INPUT LAYER")
        (progn
          (setq layer_obj_name__ename_ (car (nentsel "specify layer Object")))
          (setq layer_obj_name__obj_ (vlax-ename->vla-object layer_obj_name__ename_))
          (setq layer_obj_name_val_ (vla-get-layer layer_obj_name__obj_  ))
        )
        (setq layer_obj_name_val_ layer_obj_name_ )
      )
      (if (/= (vl-catch-all-error-p ERR_) T) 
        (progn 
            ;selection_set_for_fillter_blk_name
              (if  ;pre_select_ssget_or_post_select_ssget
                (=
                  (setq ss_pre_filter_set_xx_ (ssget "i"
                                                    (list
                                                      ; (cons 0 "INSERT") ;type of object
                                                      ; (cons 8 "000 - GRID")   ;kind of layer
                                                      ; (cons 2 "000-GRID_LINE_DYN")       ;kind of nameblock
                                                      ; (cons 62 1)           ;kind of color call sign with color code index
                                                    )
                                              )
                  )
                  nil
                )
                (progn
                  (setq ss_pre_filter_set_xx_ (ssget
                                                    (list
                                                      ; (cons 0 "INSERT") ;type of object
                                                      ; (cons 8 "000 - GRID")   ;kind of layer
                                                      ; (cons 2 "000-GRID_LINE_DYN")       ;kind of nameblock
                                                      ; (cons 62 1)           ;kind of color call sign with color code index
                                                    )
                                              )
                  )
                )
                (sslength ss_pre_filter_set_xx_)
              )
            ;
            (TA:interface_text_ T)
            (textscr)
            (getstring "\nHit [ENTER] to continue...")
            ;preloop_and_while
              (setq ss_pre_filter_set_xx_i 0)
              (while (< ss_pre_filter_set_xx_i (sslength ss_pre_filter_set_xx_))
                (setq ss_pre_filter_set_xx_ename_ (ssname ss_pre_filter_set_xx_ ss_pre_filter_set_xx_i)) 
                (setq ss_pre_filter_set_xx_obj_ (vlax-ename->vla-object  ss_pre_filter_set_xx_ename_))
                
                (vla-put-color ss_pre_filter_set_xx_obj_  line_color)
                (vla-put-layer ss_pre_filter_set_xx_obj_  layer_obj_name_val_)
                (if (= (vla-get-objectname ss_pre_filter_set_xx_obj_ ) "AcDbBlockReference")
                  (progn
                    (setq ss_pre_filter_set_xx_obj_Efname_ (LM:Effectivename ss_pre_filter_set_xx_obj_))
                    (setq blk-count_list_ (TA:Count_item_in_list_ (TA:Aassembly_all_nest_block ss_pre_filter_set_xx_obj_Efname_)))
                    (TA:all-editblock_ ss_pre_filter_set_xx_obj_Efname_ line_color layer_obj_name_val_)
                    ;preloop_and_while
                      (setq blk-count_list_i 0)
                      (while (< blk-count_list_i (length blk-count_list_))
                        (setq blk-count_list_efname_ (car (nth  blk-count_list_i blk-count_list_)))
                        (TA:all-editblock_ blk-count_list_efname_ line_color layer_obj_name_val_)
                        (TA:textscr_process_V2 "\nupdate dynamic" blk-count_list_i blk-count_list_)

                          
                        (setq blk-count_list_i (+ blk-count_list_i 1))
                      )
                    ;
                  )
                )
                ; (setq ss_pre_filter_set_xx_obj_lv1 (TA:Assembly_block_ ss_pre_filter_set_xx_obj_ ))
                (setq ss_pre_filter_set_xx_i (+ ss_pre_filter_set_xx_i 1))
              )
            ;
        )
      )
    )
    (defun c:Dyeing_layer_object_dyeLIST_TEDY2_TEMP_DWGCMD ()
      (setq line_color 256)
      (setq layer_list_ (list 
                              "010 - C10_PANEL_FASTERN_MAIN_COLOR_1" 
                              "010 - C10_PANEL_FASTERN_MAIN_COLOR_2" 
                              "010 - C10_PANEL_FASTERN_MAIN_COLOR_3" 
                              "010 - C10_PANEL_FASTERN_MAIN_COLOR_4" 
                              "010 - C10_PANEL_FASTERN_MAIN_COLOR_251" 
                              "010 - C10_PANEL_FASTERN_DEF_SUB" 
                              
                              "010 - C10_PANEL_FRAMING_MAIN_COLOR_1"
                              "010 - C10_PANEL_FRAMING_MAIN_COLOR_2"
                              "010 - C10_PANEL_FRAMING_MAIN_COLOR_3"
                              "010 - C10_PANEL_FRAMING_MAIN_COLOR_4"
                              "010 - C10_PANEL_FRAMING_MAIN_COLOR_251"
                        )
      )
      (defun TA:all-editblock_ (blockname line_color layer_name)
        ; (setq blockname "PZG35")
        ; (setq line_color 256)
        ; (setq layer_name "008 - E&M_ACESSORIES_MAIN_COLOR_1")
        (setq target_ '())
        (setq blkdef (tblobjname "BLOCK" blockname))
        (setq ent (entnext blkdef))
        (while ent
          (setq ed (entget ent))
          (if (= (cdr (assoc 0 ed)) "HATCH")
            (progn
              (setq target_ (cons ent target_))
              ;main idea of code keep or delete don't affect with core code
                (setq target_obj_ (vlax-ename->vla-object (cdr (assoc -1 ed))))
                (vla-put-color target_obj_  line_color)
                (vla-put-layer target_obj_  layer_name)
                ; (vla-put-EntityTransparency target_obj_ 80 )
              ;
            )
          )
          (if (= (cdr (assoc 0 ed)) "ARC")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "LINE")
            (progn
              ; (setq target_ (cons ent target_))
              ;main idea of code keep or delete don't affect with core code
                (setq target_obj_ (vlax-ename->vla-object (cdr (assoc -1 ed))))
                (if (/= (vla-get-layer target_obj_ ) "A-ANNO-SYMB")
                  (progn
                    (vla-put-color target_obj_  line_color)
                    (vla-put-layer target_obj_  layer_name)
                  )
                )
              ;
            )
          )
          (if (= (cdr (assoc 0 ed)) "LWPOLYLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "SPLINE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ELLIPSE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "CIRCLE")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "TEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "MTEXT")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (if (= (cdr (assoc 0 ed)) "ATTDEF")
            (progn
              ; (setq target_ (cons ent target_))
              ;main idea of code keep or delete don't affect with core code
                (setq target_obj_ (vlax-ename->vla-object (cdr (assoc -1 ed))))
                (vla-put-color target_obj_  line_color)
                (vla-put-layer target_obj_  layer_name)
                
              ;
            )
          )
          (setq ent (entnext ent))
        )
        (reverse target)
      )
      (defun TA:Aassembly_all_nest_block (blkName / blkEnt ent elist result)
        (setq blkEnt (tblobjname "BLOCK" blkName))

        (while (setq blkEnt (entnext blkEnt))
          (setq elist (entget blkEnt))

          (if (= (cdr (assoc 0 elist)) "ENDBLK")
            (setq blkEnt nil)
            (progn
              (if (= (cdr (assoc 0 elist)) "INSERT")
                (progn
                  (setq result
                    (cons (cdr (assoc 2 elist)) result)
                  )
                  ;; recurse หา block ซ้อน
                  (setq result
                    (append result
                      (TA:Aassembly_all_nest_block (cdr (assoc 2 elist)))
                    )
                  )
                )
              )
            )
          )
        )
        result
      )
      (setq ERR_
        (vl-catch-all-apply
          (function
            (lambda ()
              (setq layer_obj_name_ (TA:choose_list_v3 
                                      layer_list_
                                      "select block"
                                      (if (or
                                            (= layer_obj_name_exval nil)
                                            (= layer_obj_name_ nil)
                                          ) 
                                        (progn 
                                          (setq layer_obj_name_exval 1)
                                        )
                                        (setq layer_obj_name_exval (+ 
                                                                     (vl-position layer_obj_name_ 
                                                                                  layer_list_
                                                                     )
                                                                     1
                                                                   )
                                        )
                                      )
                                    )
              )
            )
          )
        )
      )
      (if (/= (vl-catch-all-error-p ERR_) T) 
        (progn 
            ;selection_set_for_fillter_blk_name
              (if  ;pre_select_ssget_or_post_select_ssget
                (=
                  (setq ss_pre_filter_set_xx_ (ssget "i"
                                                    (list
                                                      ; (cons 0 "INSERT") ;type of object
                                                      ; (cons 8 "000 - GRID")   ;kind of layer
                                                      ; (cons 2 "000-GRID_LINE_DYN")       ;kind of nameblock
                                                      ; (cons 62 1)           ;kind of color call sign with color code index
                                                    )
                                              )
                  )
                  nil
                )
                (progn
                  (setq ss_pre_filter_set_xx_ (ssget
                                                    (list
                                                      ; (cons 0 "INSERT") ;type of object
                                                      ; (cons 8 "000 - GRID")   ;kind of layer
                                                      ; (cons 2 "000-GRID_LINE_DYN")       ;kind of nameblock
                                                      ; (cons 62 1)           ;kind of color call sign with color code index
                                                    )
                                              )
                  )
                )
                (sslength ss_pre_filter_set_xx_)
              )
            ;
            (TA:interface_text_ T)
            (textscr)
            (getstring "\nHit [ENTER] to continue...")
            ;preloop_and_while
              (setq ss_pre_filter_set_xx_i 0)
              (while (< ss_pre_filter_set_xx_i (sslength ss_pre_filter_set_xx_))
                (setq ss_pre_filter_set_xx_ename_ (ssname ss_pre_filter_set_xx_ ss_pre_filter_set_xx_i)) 
                (setq ss_pre_filter_set_xx_obj_ (vlax-ename->vla-object  ss_pre_filter_set_xx_ename_))
                
                (vla-put-color ss_pre_filter_set_xx_obj_  line_color)
                (vla-put-layer ss_pre_filter_set_xx_obj_  layer_obj_name_)
                (if (= (vla-get-objectname ss_pre_filter_set_xx_obj_ ) "AcDbBlockReference")
                  (progn
                    (setq ss_pre_filter_set_xx_obj_Efname_ (LM:Effectivename ss_pre_filter_set_xx_obj_))
                    (setq blk-count_list_ (TA:Count_item_in_list_ (TA:Aassembly_all_nest_block ss_pre_filter_set_xx_obj_Efname_)))
                    (TA:all-editblock_ ss_pre_filter_set_xx_obj_Efname_ line_color layer_obj_name_)
                    ;preloop_and_while
                      (setq blk-count_list_i 0)
                      (while (< blk-count_list_i (length blk-count_list_))
                        (setq blk-count_list_efname_ (car (nth  blk-count_list_i blk-count_list_)))
                        (TA:all-editblock_ blk-count_list_efname_ line_color layer_obj_name_)
                        (TA:textscr_process_V2 "\nupdate dynamic" blk-count_list_i blk-count_list_)

                          
                        (setq blk-count_list_i (+ blk-count_list_i 1))
                      )
                    ;
                  )
                )
                ; (setq ss_pre_filter_set_xx_obj_lv1 (TA:Assembly_block_ ss_pre_filter_set_xx_obj_ ))
                (setq ss_pre_filter_set_xx_i (+ ss_pre_filter_set_xx_i 1))
              )
            ;
        )
      )
    )
    (defun c:Dyeing_layer_object_dyevpLIST ()
      (setq layer_list_ (list 
                          (list 
                            (list "000 - 0_HIDE_OBJ_FRAMING_DEF_SUB" 251)
                            (list "000 - 0_HIDE_OBJ_FRAMING_DEF_SUB" 251)
                            (list "000 - 0_HIDE_OBJ_FRAMING_DEF_SUB" 251)
                          )
                          (list 
                            (list "010 - ASPG_ACCESSORIES_MAIN_COLOR_1" 251)
                            (list "010 - ASPG_EXTR_MAIN_COLOR_2" 251)
                            (list "010 - ASPG_FRAMING_HATCH_" 251)
                          )
                        )
      )
      (setq ERR_
        (vl-catch-all-apply
          (function
            (lambda ()
              (setq layer_list_val (cond ( (getint (strcat "\nspecify layer_list_\n<" (rtos (setq layer_list_val (cond (layer_list_val) (1.0) ) ) ) "> : " ) ) ) (layer_list_val) ) )
              (setq layer_list_target_ (nth (fix (- layer_list_val 1)) layer_list_) )
              ;preloop_and_while
                (setq layer_list_target_i 0)
                (setq finder_true_val_ T)
                (while (and 
                         (< layer_list_target_i (length layer_list_target_))
                         (= finder_true_val_ T)
                       )
                  (setq layer_list_target_ename_ (nth  layer_list_target_i layer_list_target_))
                  (setq finder_true_val_ (TA:if_found_layer_ (car layer_list_target_ename_) ))
                  (setq layer_list_target_i (+ layer_list_target_i 1))
                )
              ;
            )
          )
        )
      )
      (if (and 
            (/= (vl-catch-all-error-p ERR_) T)
            (= finder_true_val_ T)
            (> (getvar "CVPORT") 1)
          ) 
        (progn 
            (TA:interface_text_ T)
            (textscr)
            (getstring "\nHit [ENTER] to continue...")
            ;preloop_and_while
              
              (setq layer_list_i 0)
              (while (< layer_list_i (length layer_list_))
                (setq layer_list_target_name (car (nth  layer_list_i layer_list_target_)))
                (setq layer_list_target_color (cadr (nth  layer_list_i layer_list_target_)))
                
                (command "vplayer" "c" layer_list_target_color layer_list_target_name "c" "")
            
                (setq layer_list_i (+ layer_list_i 1))
              )
            ;
        )
      )
    )
    
  ;
  ;USER-INPUT_FUNC
    (defun TA:choose_list_ (choose_data-list_)
      ; (setq choose_data-list_ (list 
      ;                           "000 - CONCRETE_PRECAST_MAIN_COLOR_1"
      ;                           "000 - CONCRETE_WALL_MAIN_COLOR_1"
      ;                         )
      ; )
      (if (= ( type choose_data-list_ ) 'LIST)
        (progn
          (setq choose_data-list_sima (TA:list-to-Text choose_data-list_))
        )
      )
      (setq n 0)
        
        
        
      (if (= choose_block_di nil)
        (progn
          (setq choose_block_di 1)
        )
        (setq choose_block_di keepVAL_choose_block_di)
      )
      (setq choose_block_di (cond 
                              ((getint 
                                (strcat 
                                  "\nSpecify block"
                                  (apply 'strcat (mapcar '(lambda (x) (strcat "\n" (itoa (setq n (1+ n))) " = " x ) ) choose_data-list_sima ) )
                                  "\n<"
                                  (itoa 
                                    (setq choose_block_di (cond 
                                                            (choose_block_di)
                                                            (1)
                                                          )
                                    )
                                  )
                                  "> : "
                                )
                              )
                              )
                              (choose_block_di)
                            )
      )
      (setq keepVAL_choose_block_di choose_block_di)
      (nth (- choose_block_di 1)  choose_data-list_)
    )
    (defun TA:choose_list_v2 (choose_data-list_ txt_promt_ )
      ; (setq txt_promt_ "sadasdadasdasd")
      ; (setq choose_data-list_ (list 
      ;                           "000 - CONCRETE_PRECAST_MAIN_COLOR_1"
      ;                           "000 - CONCRETE_WALL_MAIN_COLOR_1"
      ;                         )
      ; )
      (if (= ( type choose_data-list_ ) 'LIST)
        (progn
          (setq choose_data-list_sima (TA:list-to-Text choose_data-list_))
        )
      )
      (setq n 0)
        
        
        
      (if (= choose_block_di nil)
        (progn
          (setq choose_block_di 1)
        )
        (setq choose_block_di keepVAL_choose_block_di)
      )
      (setq choose_block_di (cond 
                              ((getstring 
                                (strcat 
                                  "\n" txt_promt_
                                  (apply 'strcat (mapcar '(lambda (x) (strcat "\n" (itoa (setq n (1+ n))) " = " x ) ) choose_data-list_sima ) )
                                  "\n<"
                                  (itoa 
                                    (setq choose_block_di (cond 
                                                            (choose_block_di)
                                                            (1)
                                                          )
                                    )
                                  )
                                  "> : "
                                )
                              )
                              )
                              (choose_block_di)
                            )
      )
      (setq keepVAL_choose_block_di choose_block_di)
      (nth (- choose_block_di 1)  choose_data-list_)
    )
    (defun TA:choose_list_v3 (choose_data-list_ txt_promt_ existing_choose_block_di_ )
      ; (setq choose_data-list_val (TA:choose_list_v3 choose_data-list_ "Specify block" (setq choose_data-list_exval (+ (vl-position choose_data-list_val choose_data-list_ ) 1)) )) ;example of call func with existing value
      ; (setq choose_data-list_ (list 
      ;                           "000 - CONCRETE_PRECAST_MAIN_COLOR_1"
      ;                           "000 - CONCRETE_WALL_MAIN_COLOR_1"
      ;                         )
      ; )
      (if (= ( type choose_data-list_ ) 'LIST)
        (progn
          (setq choose_data-list_sima (TA:list-to-Text choose_data-list_))
        )
      )
      (setq n 0)
        
        
      
      (if (= existing_choose_block_di_ nil)
        (progn
          (setq existing_choose_block_di_ 1)
        )
      )
      (if (= choose_block_di nil)
        (progn
          (setq choose_block_di 1)
        )
        (setq choose_block_di existing_choose_block_di_)
      )
      (setq choose_block_di (cond 
                              ((getint 
                                (strcat 
                                  "\n" txt_promt_
                                  (apply 'strcat (mapcar '(lambda (x) (strcat "\n" (itoa (setq n (1+ n))) " = " x ) ) choose_data-list_sima ) )
                                  "\n<"
                                  (itoa 
                                    (setq choose_block_di (cond 
                                                            (choose_block_di)
                                                            (1)
                                                          )
                                    )
                                  )
                                  "> : "
                                )
                              )
                              )
                              (choose_block_di)
                            )
      )
      (setq keepVAL_choose_block_di choose_block_di)
      (nth (- choose_block_di 1)  choose_data-list_)
    )
    (defun TA:choose_list_v4 (choose_data-list_ txt_promt_ existing_value_
                              / choose_data-list_sima n existing_position_
                                default_index_ input_index_ prompt_text_)
      ; V4 accepts the previous string value directly.
      ; Each calling variable therefore keeps a separate selection.
      (if (and (= (type choose_data-list_) 'LIST)
               (> (length choose_data-list_) 0)
          )
        (progn
          (setq choose_data-list_sima (TA:list-to-Text choose_data-list_)
                existing_position_   (vl-position existing_value_
                                                  choose_data-list_
                                     )
                default_index_       (if existing_position_
                                       (1+ existing_position_)
                                       1
                                     )
                n                    0
                prompt_text_         (strcat
                                       "\n" txt_promt_
                                       (apply
                                         'strcat
                                         (mapcar
                                           '(lambda (x)
                                             (strcat
                                               "\n"
                                               (itoa (setq n (1+ n)))
                                               " = "
                                               x
                                             )
                                           )
                                           choose_data-list_sima
                                         )
                                       )
                                       "\n<"
                                       (itoa default_index_)
                                       "> : "
                                     )
          )
          (setq input_index_ nil)
          (while (null input_index_)
            (initget 6)
            (setq input_index_ (getint prompt_text_))
            (cond
              ((null input_index_)
               (setq input_index_ default_index_)
              )
              ((> input_index_ (length choose_data-list_))
               (prompt
                 (strcat
                   "\nPlease enter a number from 1 to "
                   (itoa (length choose_data-list_))
                   "."
                 )
               )
               (setq input_index_ nil)
              )
            )
          )
          (nth (1- input_index_) choose_data-list_)
        )
        nil
      )
    )
    (defun TA:getkword ( getkword_text_ initget_text1_ initget_text2_ value-true1 value-false1 ) ; for if true-false by keyword
      ; (setq getkword_text_ "keep input offset value ?")
      ; (setq initget_text1_ "Yes")
      ; (setq initget_text2_ "No")
      ; (setq value-true1 22)
      ; (setq value-false1 23)
      (setq initget_text_ovl_ (strcat initget_text1_ " " initget_text2_))
      (initget 2)
      (initget initget_text_ovl_)
      (setq condition_object_case_detect_ ;Detect the variable's result in case of a function error
        (vl-catch-all-apply 
          (function 
            (lambda () 
              (setq condition_object_case_val_type1_ (not (eq "No" (getkword (strcat getkword_text_ " [" (LM:StringSubst "/" " " initget_text_ovl_ ) "] " "<Y>:" ) ) ) ) ) 
            )
          )
        )
      )
      (if (= condition_object_case_val_type1_ T)
        (progn
          value-true1
        )
        value-false1
      )
    )
  ;
  ;CUTING-LENGTH_FUNC
    ;color byblock ก้่อน
    ;pairing length
    ;indicate color 
    ;lineup
    (defun c:EXTR-from-Pline () 
      ;selection_set_for_fillter_blk_name
        (if  ;pre_select_ssget_or_post_select_ssget
          (= 
            (setq ss_pre_filter_set_xx_ (ssget "i" 
                                              (list 
                                                (cons 0 "lwpolyline") ;type of object
                                                ; (cons 8 "000 - GRID")   ;kind of layer
                                                ; (cons 2 "000-GRID_LINE_DYN")       ;kind of nameblock
                                                ; (cons 62 1)           ;kind of color call sign with color code index
                                              )
                                        )
            )
            nil
          )
          (progn 
            (setq ss_pre_filter_set_xx_ (ssget 
                                          (list 
                                            (cons 0 "lwpolyline") ;type of object
                                            ; (cons 8 "000 - GRID")   ;kind of layer
                                            ; (cons 2 "000-GRID_LINE_DYN")       ;kind of nameblock
                                            ; (cons 62 1)           ;kind of color call sign with color code index
                                          )
                                        )
            )
          )
          (sslength ss_pre_filter_set_xx_)
        )
      ;
      ;preloop_and_while
      (setq ss_pre_filter_set_xx_i 0)
      (while (< ss_pre_filter_set_xx_i (sslength ss_pre_filter_set_xx_)) 
        (setq ss_pre_filter_set_xx_ename_ (ssname ss_pre_filter_set_xx_ ss_pre_filter_set_xx_i ) )
        (setq ss_pre_filter_set_xx_obj_ (vlax-ename->vla-object ss_pre_filter_set_xx_ename_))
        (setq ss_pre_filter_set_xx_obj_getboundingbox (vla-getboundingbox ss_pre_filter_set_xx_obj_ 'min_ 'max_ ) )
        (setq ss_pre_filter_set_xx_min_ (vlax-safearray->list min_))
        (setq ss_pre_filter_set_xx_max_ (vlax-safearray->list max_))
        (setq ss_pre_filter_set_xx_obj_xylist_ (TA:assembly_coordinate_coner (list ss_pre_filter_set_xx_min_ ss_pre_filter_set_xx_max_) ) )

        (TA:vla-insertblock 
          "DANAI EXTR H VAL" 
          (TA:midpoint (nth 0 ss_pre_filter_set_xx_obj_xylist_) (nth 1 ss_pre_filter_set_xx_obj_xylist_)) 
          1 
          0
        )
        ;new_blk_entlast object
        (setq sssss_ename (entlast))
        (setq sssss_obj (vlax-ename->vla-object sssss_ename))
        (LM:setdynpropvalue 
          sssss_obj
          "H"
          (distance  (nth 0 ss_pre_filter_set_xx_obj_xylist_) (nth 3 ss_pre_filter_set_xx_obj_xylist_))
        )
        (vla-delete ss_pre_filter_set_xx_obj_)
        ;


        (setq ss_pre_filter_set_xx_i (+ ss_pre_filter_set_xx_i 1))
      )
      ;
    )
    (defun c:EXTR-tag-sort-attribute ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:standard_list_croodinate_sorting ss_pre_filter_set_xx_ "X" ) )
      ;
      (setq danai-att-val_ ;Get-string by keep previous value
          (if
            (or
              (/= (setq danai-att-val_val (getstring (strcat "\nSpecify prefix name 1 <" (if danai-att-val_ danai-att-val_ "") ">: ") ) ) "" )
            )
              (progn
                (setq danai-att-val_ danai-att-val_val)
                (setq danai-att-val_keep_val_ danai-att-val_val)
              )
            (setq danai-att-val_val danai-att-val_keep_val_)
          )
      )
      (setq danai-att-val_LV2 ;Get-string by keep previous value
          (if
            (or
              (/= (setq danai-att-val_LV2val (getstring (strcat "\nSpecify prefix name 2 " (strcat danai-att-val_ )  "<" (if danai-att-val_LV2 danai-att-val_LV2 "") ">: ") ) ) "" )
            )
              (progn
                (setq danai-att-val_LV2 danai-att-val_LV2val)
                (setq danai-att-val_LV2keep_val_ danai-att-val_LV2val)
              )
            (setq danai-att-val_LV2val danai-att-val_LV2keep_val_)
          )
      )
      ;prloop_and_while
        (setq ss_pre_filter_set_xx_i 0)
        (while (< ss_pre_filter_set_xx_i (length ss_pre_filter_set_xx_))
          (setq ss_pre_filter_set_xx_ename_ (car (nth  ss_pre_filter_set_xx_i ss_pre_filter_set_xx_)))
          (setq ss_pre_filter_set_xx_obj_ (vlax-ename->vla-object  ss_pre_filter_set_xx_ename_))
          (setq ss_pre_filter_set_xx_obj_att-val (LM:vl-setattributevalue ss_pre_filter_set_xx_obj_ "DANAI_EXTR_NAME" (strcat danai-att-val_val "-" danai-att-val_LV2 "-" (TA:prefix_value_000 (+ ss_pre_filter_set_xx_i 1)))) )
          (setq ss_pre_filter_set_xx_i (+ ss_pre_filter_set_xx_i 1))
        )
      ;
    )
    (defun c:EXTR-indicate-color ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:standard_list_croodinate_sorting ss_pre_filter_set_xx_ "X" ) )
      ;
      ;prloop_and_while
        (setq ss_pre_filter_set_xx_i 0)
        (while (< ss_pre_filter_set_xx_i (length ss_pre_filter_set_xx_))
          (setq ss_pre_filter_set_xx_ename_ (car (nth  ss_pre_filter_set_xx_i ss_pre_filter_set_xx_)))
          (setq ss_pre_filter_set_xx_obj_ (vlax-ename->vla-object  ss_pre_filter_set_xx_ename_))
          (setq ss_pre_filter_set_xx_obj_att-val (LM:vl-setattributevalue 
                                                  ss_pre_filter_set_xx_obj_
                                                  "DANAI_EXTR_COLOR_FOR_SET"
                                                  (if 
                                                    (= (vla-get-color ss_pre_filter_set_xx_obj_) 0 )
                                                    (progn 
                                                      "000"
                                                    )
                                                    (TA:prefix_value_000 (vla-get-color ss_pre_filter_set_xx_obj_) )
                                                  )
                                                )
          )
          (setq ss_pre_filter_set_xx_i (+ ss_pre_filter_set_xx_i 1))
        )
      ;
    )
    (defun c:EXTR-sum_selection-length ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq sum 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq sum (+ sum (LM:getdynpropvalue ss_pre_filter_set_xx_obj_ "H")))
          (setq ss_pre_filter_set_xx_i (+ ss_pre_filter_set_xx_i 1))
        )
      ;\
      (alert (rtos sum 2 2))
    )
    (defun c:EXTR-pairing-length ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:EF_Filter_ss_set_V2_ ss_pre_filter_set_xx_ (list "DANAI EXTR H VAL")))
      ;
      ;preloop_and_while
        (setq color_i 0)
        (setq ss_pre_filter_set_xx_i 0)
        (setq ss_pre_filter_set_xx_ii 0)
        (setq ss_pre_filter_set_xx_list-ename_ ())
        (while (< ss_pre_filter_set_xx_i (sslength ss_pre_filter_set_xx_))
          (setq color_i (+ color_i 1))
          (setq ss_pre_filter_set_xx_ename_ (ssname ss_pre_filter_set_xx_ ss_pre_filter_set_xx_i))
          (setq ss_pre_filter_set_xx_list-ename_ (cons ss_pre_filter_set_xx_ename_  ss_pre_filter_set_xx_list-ename_ ))
          (setq ss_pre_filter_set_xx_obj_ (vlax-ename->vla-object  ss_pre_filter_set_xx_ename_))
          (setq ss_pre_filter_set_xx_obj_cur-L (LM:getdynpropvalue ss_pre_filter_set_xx_obj_ "H"))
          ; (vla-put-color ss_pre_filter_set_xx_obj_ color_i)
          ;preloop_and_while
            (setq ss_pre_filter_set_xx_ii 0)
            (while (< ss_pre_filter_set_xx_ii (sslength ss_pre_filter_set_xx_))
              (if (and 
                    (/= (vl-princ-to-string (setq target-match (ssname ss_pre_filter_set_xx_ ss_pre_filter_set_xx_ii))) (vl-princ-to-string ss_pre_filter_set_xx_ename_))
                    (/= (vl-princ-to-string (setq target-match_obj_ (vlax-ename->vla-object  target-match))) (vl-princ-to-string ss_pre_filter_set_xx_obj_))
                    (= (vla-get-color target-match_obj_) 0)
                    (= (vla-get-color target-match_obj_) 0)
                    (= (member target-match ss_pre_filter_set_xx_list-ename_) nil)
                    (or 
                      (< (+ (LM:getdynpropvalue target-match_obj_ "H") ss_pre_filter_set_xx_obj_cur-L) 6050)
                    )
                  )
                (progn
                  (setq ss_pre_filter_set_xx_obj_cur-L (+ (LM:getdynpropvalue target-match_obj_ "H") ss_pre_filter_set_xx_obj_cur-L))
                  (setq ss_pre_filter_set_xx_list-ename_ (cons target-match  ss_pre_filter_set_xx_list-ename_ ))
                  (vla-put-color target-match_obj_ color_i)
                  (vla-put-color ss_pre_filter_set_xx_obj_ color_i)
                  T
                )
              )
              (setq ss_pre_filter_set_xx_ii (+ ss_pre_filter_set_xx_ii 1))
            )
          ;
          ;preloop_and_while
            (setq ss_pre_filter_set_xx_list-ename_i 0)
            (while (< ss_pre_filter_set_xx_list-ename_i (length ss_pre_filter_set_xx_list-ename_))
              (setq ss_pre_filter_set_xx_list-ename_ename_ (nth  ss_pre_filter_set_xx_list-ename_i ss_pre_filter_set_xx_list-ename_))
              (ssdel ss_pre_filter_set_xx_list-ename_ename_ ss_pre_filter_set_xx_)
              (sslength ss_pre_filter_set_xx_)
              (setq ss_pre_filter_set_xx_i 0)
              (setq ss_pre_filter_set_xx_list-ename_i (+ ss_pre_filter_set_xx_list-ename_i 1))
            )
          ;
          (setq ss_pre_filter_set_xx_i (+ ss_pre_filter_set_xx_i 1))
        )
      ;
    )
    (defun c:EXTR-runing_color_tag1 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:standard_list_croodinate_sorting ss_pre_filter_set_xx_ "X" ) )
      ;
      
      (setq run_no (cond ( (getint (strcat "\nspecify get rotation\n<" (rtos (setq run_no (cond (run_no) (1.0) ) ) ) "> : " ) ) ) (run_no) ) )
      ;prloop_and_while
        (setq ss_pre_filter_set_xx_i 0)
        (while (< ss_pre_filter_set_xx_i (length ss_pre_filter_set_xx_))
          (setq ss_pre_filter_set_xx_ename_ (car (nth  ss_pre_filter_set_xx_i ss_pre_filter_set_xx_)))
          (setq ss_pre_filter_set_xx_obj_ (vlax-ename->vla-object  ss_pre_filter_set_xx_ename_))
          (if ( = (LM:vl-getattributevalue ss_pre_filter_set_xx_obj_ "DANAI_EXTR_COLOR_FOR_SET") "000")
            (progn
              
              (LM:vl-setattributevalue ss_pre_filter_set_xx_obj_ "DANAI_EXTR_COLOR_FOR_SET" (TA:prefix_value_000 run_no))
              (setq run_no (+ run_no 1))
            )
          )
          (setq ss_pre_filter_set_xx_i (+ ss_pre_filter_set_xx_i 1))
        )
      ;
    )
    (defun c:EXTR-lineup ()
      ;user-input-
        ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        ;preloop_and_while
          (setq ss_pre_filter_set_xx_i 0)
          (setq extr-tag-len_ ())
          (setq extr-tag-ename_ ())
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (setq ss_pre_filter_set_xx_obj_length (LM:getdynpropvalue ss_pre_filter_set_xx_obj_ "distance1"))
            (setq color_tag (LM:vl-getattributevalue ss_pre_filter_set_xx_obj_ "DANAI_EXTR_COLOR_FOR_SET" ))
            (setq tempforsum (list 
                                  color_tag
                                  ss_pre_filter_set_xx_obj_length
                                )
            )
            (setq tempforename (list 
                                  color_tag
                                  ss_pre_filter_set_xx_ename_
                                  ss_pre_filter_set_xx_obj_length
                                )
            )
            (setq extr-tag-ename_ (cons tempforename extr-tag-ename_ ))
            (setq extr-tag-len_ (cons tempforsum extr-tag-len_ ))
            (setq ss_pre_filter_set_xx_i (+ ss_pre_filter_set_xx_i 1))
          )
        ;\
      ;
      ;result text summary
        (setq result '())

        (foreach item extr-tag-len_
          (setq key (car item))
          (setq val (cadr item))

          (if (assoc key result)
            (setq result
              (subst
                (cons key (+ val (cdr (assoc key result))))
                (assoc key result)
                result
              )
            )
            (setq result (cons (cons key val) result))
          )
        )
        (setq txt "")
        (foreach r (vl-sort result '(lambda (a b) (< (car a) (car b))))
          (setq txt
            (strcat txt
              (car r)
              " = "
              (rtos (cdr r) 2 3)
              "\n"
            )
          )
        )
        (TA:copytext->clipboard txt )
      ;
      ;summary ename for set
        (setq result_ename-lst_ '())
        (foreach pair extr-tag-ename_
          (setq key (car pair))
          (setq ent (cadr pair))

          (if (assoc key result_ename-lst_)
            (setq result_ename-lst_
              (subst
                (cons key (cons ent (cdr (assoc key result_ename-lst_))))
                (assoc key result_ename-lst_)
                result_ename-lst_
              )
            )
            (setq result_ename-lst_ (cons (cons key (list ent)) result_ename-lst_))
          )
        )

        ;; print result_ename-lst_
        (foreach r result_ename-lst_
          (princ (strcat "\nTAG " (car r) " = " (itoa (length (cdr r)))))
        )

        (princ)
      ;
      ;TA:stanndard_lambda_sorting
        (setq result_ename-lst_sorted_ (vl-sort result_ename-lst_  ;bigest open indent list
                                                (function 
                                                  (lambda (a b) 
                                                    (< 
                                                      (atoi (car a)) 
                                                      (atoi (car b))
                                                    )
                                                  )
                                                )
                                      ) ;bigest close indent list
        )
      ;
      (setq new_pt_ (getpoint "xxxx"))
      ;preloop_and_while
        (setq result_ename-lst_i 0)
        (while (< result_ename-lst_i (length result_ename-lst_))
          (setq H-val 0)
          (setq result_ename-lst_main-set_ (nth  result_ename-lst_i result_ename-lst_sorted_))
          ;preloop_and_while for 
            (setq result_ename-lst_main-set_i 1)
            (while (< result_ename-lst_main-set_i (length result_ename-lst_main-set_))
              (setq temp-ss- (TA:list-to-ss result_ename-lst_main-set_ result_ename-lst_main-set_))
              (setq result_ename-lst_main-set_ename_ (nth  result_ename-lst_main-set_i result_ename-lst_main-set_)) 
              
              (setq result_ename-lst_main-set_obj_ (vlax-ename->vla-object  result_ename-lst_main-set_ename_))
              (setq result_ename-lst_main-set_obj_ins_ (vlax-safearray->list (vlax-variant-value (vla-get-insertionpoint result_ename-lst_main-set_obj_))))
              
              (vla-put-insertionpoint
                result_ename-lst_main-set_obj_
                (vlax-3d-point new_pt_ )
              )
              (if (/= result_ename-lst_main-set_i 1)
                (progn
                  (setq H-val (+ (+ H-val (LM:getdynpropvalue 
                                (vlax-ename->vla-object (nth  (- result_ename-lst_main-set_i 1)  result_ename-lst_main-set_)) 
                                "distance1"
                              )) 1.5 )
                  )
                  (TA:move_axis_insertionpoint result_ename-lst_main-set_obj_ "Y" H-val)
                )
              )

              (setq result_ename-lst_main-set_i (+ result_ename-lst_main-set_i 1))
            )
          ;
          (setq new_pt_ (list 
                          (+ (car new_pt_) 500)
                          (+ (cadr new_pt_) 0)
                          0
                        )
          )
          (setq result_ename-lst_i (+ result_ename-lst_i 1))
        )
      ;
      
    )
  ;
  ;repair_FUNC
    (defun c:repair-PL-LENGTH_S23_ ()
      (setq pline-target_ename_ (car (entsel "specify Object")))
      (setq pline-target_obj_ (vlax-ename->vla-object pline-target_ename_))
      (setq pline-target_obj_vtx-list_ (TA:Get_Pline_vertext_angle_case1 pline-target_ename_))
      ;preloop_and_while
        (setq pline-target_obj_vtx-list_i 0)
        (setq setset ())
        (setq setset (cons (car (nth  pline-target_obj_vtx-list_i pline-target_obj_vtx-list_)) setset))
        
        (while (< pline-target_obj_vtx-list_i (- (length pline-target_obj_vtx-list_) 1))
          (setq pline-target_obj_vtx-list_xy1 (car (nth  pline-target_obj_vtx-list_i pline-target_obj_vtx-list_)))
          (setq pline-target_obj_vtx-list_xy2 (car (nth  (+ 1  pline-target_obj_vtx-list_i) pline-target_obj_vtx-list_)))
          (setq pline-target_obj_vtx-list_ang1 (cadr (nth  pline-target_obj_vtx-list_i pline-target_obj_vtx-list_)))
          (setq pline-target_obj_vtx-list_ang2 (cadr (nth  (+ 1  pline-target_obj_vtx-list_i) pline-target_obj_vtx-list_)))
          
          (setq tolerance_ang_ 2.0)
          (setq nearest_angle_ (* 90.0 (LM:round (/ pline-target_obj_vtx-list_ang1 90.0)) ) )
          
          (setq pline-target_obj_vtx-list_result 
                (polar (car setset) 
                        (setq ang (* (/ pi 2.0) 
                                    (LM:round (/ (deg-to-rad pline-target_obj_vtx-list_ang1) (/ pi 2.0)))
                                  )
                        ) 
                        (fix (distance pline-target_obj_vtx-list_xy1 pline-target_obj_vtx-list_xy2))
                )
          )

          (if (<= (abs (- pline-target_obj_vtx-list_ang1 nearest_angle_)) tolerance_)
            (progn
              ; อยู่ใน tolerance ให้ปัดเข้ามุมมาตรฐาน
              (setq pline-target_obj_vtx-list_result 
                (polar (car setset) 
                        (setq ang (* (/ pi 2.0) 
                                    (LM:round (/ (deg-to-rad pline-target_obj_vtx-list_ang1) (/ pi 2.0)))
                                  )
                        ) 
                        (fix (distance pline-target_obj_vtx-list_xy1 pline-target_obj_vtx-list_xy2))
                )
              )
            )
            (progn
              (setq pline-target_obj_vtx-list_result 
                (polar (car setset) 
                        (deg-to-rad pline-target_obj_vtx-list_ang1) 
                        (fix (distance pline-target_obj_vtx-list_xy1 pline-target_obj_vtx-list_xy2))
                )
              )
            )
          )
          (setq setset (cons pline-target_obj_vtx-list_result  setset))
          (distance (car setset) (cadr setset))
          (setq pline-target_obj_vtx-list_i (+ pline-target_obj_vtx-list_i 1))
        )
      ;
      (setvar "osmode" 0)
      (create-pline (reverse setset) )
      (vla-delete pline-target_obj_)
      (setvar "osmode" 1215)
    )
    (defun c:s90_reangline-to-90 ()
      (setq pline-target_ename_ (car (entsel "specify Object")))
      (setq pline-target_obj_ (vlax-ename->vla-object pline-target_ename_))
      (setq pline-target_obj_vtx-list_ (TA:Get_Pline_vertext_angle_case1 pline-target_ename_))
      ;preloop_and_while
        (setq pline-target_obj_vtx-list_i 0)
        (setq setset ())
        (setq setset (cons (car (nth  pline-target_obj_vtx-list_i pline-target_obj_vtx-list_)) setset))
        
        (while (< pline-target_obj_vtx-list_i (- (length pline-target_obj_vtx-list_) 1))
          (setq pline-target_obj_vtx-list_xy1 (car (nth  pline-target_obj_vtx-list_i pline-target_obj_vtx-list_)))
          (setq pline-target_obj_vtx-list_xy2 (car (nth  (+ 1  pline-target_obj_vtx-list_i) pline-target_obj_vtx-list_)))
          (setq pline-target_obj_vtx-list_ang1 (cadr (nth  pline-target_obj_vtx-list_i pline-target_obj_vtx-list_)))
          (setq pline-target_obj_vtx-list_ang2 (cadr (nth  (+ 1  pline-target_obj_vtx-list_i) pline-target_obj_vtx-list_)))
          
          (setq tolerance_ang_ 2.0)
          (setq nearest_angle_ (* 90.0 (LM:round (/ pline-target_obj_vtx-list_ang1 90.0)) ) )
          
          (setq pline-target_obj_vtx-list_result 
                (polar (car setset) 
                        (deg-to-rad 90) 
                        (fix (distance pline-target_obj_vtx-list_xy1 pline-target_obj_vtx-list_xy2))
                )
          )

          (if (<= (abs (- pline-target_obj_vtx-list_ang1 nearest_angle_)) tolerance_)
            (progn
              ; อยู่ใน tolerance ให้ปัดเข้ามุมมาตรฐาน
              (setq pline-target_obj_vtx-list_result 
                (polar (car setset) 
                        (deg-to-rad 90) 
                        (fix (distance pline-target_obj_vtx-list_xy1 pline-target_obj_vtx-list_xy2))
                )
              )
            )
            (progn
              (setq pline-target_obj_vtx-list_result 
                (polar (car setset) 
                        (deg-to-rad 90) 
                        (fix (distance pline-target_obj_vtx-list_xy1 pline-target_obj_vtx-list_xy2))
                )
              )
            )
          )
          (setq setset (cons pline-target_obj_vtx-list_result  setset))
          (distance (car setset) (cadr setset))
          (setq pline-target_obj_vtx-list_i (+ pline-target_obj_vtx-list_i 1))
        )
      ;
      (setvar "osmode" 0)
      
      
      (if (= (getvar "worlducs") 0) 
        (progn 
          (setq trans_point_list_
            (mapcar
              '(lambda (point_)
                (trans point_ 0 1)
              )
              setset
            )
          )
        )
        (progn 
          (setq trans_point_list_ setset)
        )
        
      )
      (create-pline (reverse trans_point_list_) )
      (vla-delete pline-target_obj_)
      (setvar "osmode" 1215)
    )
  ;
  ;Layer_FUNC
    (defun c:rename_layer_bycase
      (
        /
        target_change_
        next_change_
        all_layer_indwg_
        all_layer_indwg_i
        all_layer_indwg_val_
        layer_data_
        newcut_
        new_layer_name_
        layers_
        layer_obj_
        error_result_
        rename_count_
      )

      (vl-load-com)

      ;; Pattern ของ Layer เดิม
      (setq target_change_ "*C10_PANEL_*")

      ;; ข้อความใหม่ที่ใช้แทน "300-PANEL_"
      (setq next_change_ "300-PANEL_")

      ;; ดึง Layer ทั้งหมดจาก Drawing
      (setq all_layer_indwg_ '())
      (setq layer_data_ (tblnext "LAYER" T))

      (while layer_data_
        (setq all_layer_indwg_ (cons (cdr (assoc 2 layer_data_)) all_layer_indwg_))
        (setq layer_data_ (tblnext "LAYER"))
      )

      (setq all_layer_indwg_ (reverse all_layer_indwg_))
      (setq layers_ (vla-get-Layers (vla-get-ActiveDocument (vlax-get-acad-object))))
      (setq all_layer_indwg_i 0)
      (setq rename_count_ 0)

      ;; เอา * ออกจาก Pattern เพื่อใช้เป็นข้อความค้นหา
      (setq newcut_ (LM:StringSubst "" "*" target_change_))

      ;; วน Rename Layer
      (while (< all_layer_indwg_i (length all_layer_indwg_))
        (setq all_layer_indwg_val_ (nth all_layer_indwg_i all_layer_indwg_))

        (if (wcmatch all_layer_indwg_val_ target_change_)
          (progn
            ;; ตัวอย่าง: AAA300-PANEL_BBB -> AAAC10_PANEL_BBB
            (setq new_layer_name_ (LM:StringSubst next_change_ newcut_ all_layer_indwg_val_))

            ;; ไม่ Rename ถ้าชื่อใหม่มีอยู่แล้ว
            (if
              (tblsearch "LAYER" new_layer_name_)
              (prompt
                (strcat
                  "\nSkip: Layer already exists: "
                  new_layer_name_
                )
              )

              (progn
                (setq error_result_
                  (vl-catch-all-apply
                    'vla-Item
                    (list layers_ all_layer_indwg_val_)
                  )
                )

                (if (not (vl-catch-all-error-p error_result_))
                  (progn
                    (setq layer_obj_ error_result_)

                    (setq error_result_
                      (vl-catch-all-apply
                        'vla-put-Name
                        (list layer_obj_ new_layer_name_)
                      )
                    )

                    (if (vl-catch-all-error-p error_result_)
                      (prompt
                        (strcat
                          "\nUnable to rename: "
                          all_layer_indwg_val_
                          " | "
                          (vl-catch-all-error-message error_result_)
                        )
                      )

                      (progn
                        (setq rename_count_ (+ rename_count_ 1))

                        (prompt
                          (strcat
                            "\nRenamed: "
                            all_layer_indwg_val_
                            " -> "
                            new_layer_name_
                          )
                        )
                      )
                    )
                  )
                )
              )
            )
          )
        )

        (setq all_layer_indwg_i (+ all_layer_indwg_i 1))
      )

      (prompt
        (strcat
          "\nCompleted. Renamed "
          (itoa rename_count_)
          " layer(s)."
        )
      )

      (princ)
    )
  ;
;                                   
  (defun c:expl-p () 
    (vl-load-com)
    (vlax-for b 
      (vla-get-Blocks 
        (vla-get-ActiveDocument (vlax-get-acad-object))
      )
      (or (wcmatch (vla-get-Name b) "`**_Space*") 
          (vla-put-explodable b :vlax-false)
      )
    )
    (princ)
  ) 
  (defun c:2d_blank_size ()
    ;user_input_
      (setq 2dblank_ename_ (car (entsel "specify Object")))
      (setq inserttion_point_ (getpoint "specify Point"))
      (setq user_input_height_ (cond ( (getreal (strcat "\nspecify_height blank size\n<" (rtos (setq user_input_height_ (cond (user_input_height_) (1.0) ) ) ) "> : " ) ) ) (user_input_height_) ) )
    ;
    ;get_data_
      (setq r2dblank_obj_ (vlax-ename->vla-object 2dblank_ename_))
      (setq 2dblank_objname_  (vla-get-objectname r2dblank_obj_))
    
      (setq vertex_list_  (TA:Get_Pline_vertext_ins_point_ 2dblank_ename_))
      (setq 2dblank_len_val_ (TA:get_vertex_len_ 2dblank_ename_))
    
    ;
    ;preloop_and_while for main_idea for insertion_dynamicblock_data_
      (setq 2dblank_len_val_i 0)
      (while (< 2dblank_len_val_i (length 2dblank_len_val_))
        (setq 2dblank_len_val_width_ (nth  2dblank_len_val_i 2dblank_len_val_))
        
        ;main_idea_
          (command "insert" "001 - DYNAMIC REC&SSQ SHAPE BLANKSIZE_startpoint" inserttion_point_ 1 0 )
          (setq new_dynamic_block_ (entlast))
          (setq new_dynamic_block_obj_ (vlax-ename->vla-object new_dynamic_block_))
          (LM:setdynpropvalue new_dynamic_block_obj_ "H" user_input_height_)
          (LM:setdynpropvalue new_dynamic_block_obj_ "W" 2dblank_len_val_width_)
          (LM:setdynpropvalue new_dynamic_block_obj_ "visibility1" "3.FOLDING_LINE")
        ;
        ;incaseloop_coordinate_x_axis
          (setq inserttion_point_ (list
                                      (+ (car inserttion_point_ ) 2dblank_len_val_width_ )
                                      (cadr inserttion_point_ )
                                    )
          )
        ;
        (setq 2dblank_len_val_i (+ 2dblank_len_val_i 1))
      )
    ;
      
    ;
    
  )
  (defun c:insert_folding_sheet_insFL ()
    (setq pt (getpoint "spoecify insertion point"))
    (setq pt2 (getpoint pt "specify length "))
    (TA:vla-insertblock "001 - DYNAMIC REC&SSQ SHAPE SOLID_midpoint" pt 1 (angle pt pt2) )
    ;new_blk_entlast object
      (setq newfold_ename (entlast))
      (setq newfold_obj (vlax-ename->vla-object newfold_ename))
      (LM:setdynpropvalue newfold_obj "H" 17)
      (LM:setdynpropvalue newfold_obj "W" (* 2 (distance pt pt2) ))
      (LM:setdynpropvalue newfold_obj "visibility1" "2.non wipeout")
      
    ;
    ; (setq getRO_RO_ (cond ( (getint (strcat "\nspecify get rotation\n<" (rtos (setq getRO_RO_ (cond (getRO_RO_) (1.0) ) ) ) "> : " ) ) ) (getRO_RO_) ) )
    ; (vla-put-rotation newfold_obj (angle pt pt2))
    (vla-put-color newfold_obj 1 ) 
  )
  
  (defun c:DAFT_insert_to_mid_pline_ins1_ ()
    (setq pline_ename_ (car (entsel "specify Object")))
    (setq pline_obj_ (vlax-ename->vla-object pline_ename_))
    (setq vt_point_ (cadr (TA:Get_Pline_vertext_ins_point_ pline_ename_)))
    
    ; (setq H_VAL (cond ( (getreal (strcat "\nSpecify Dim Scale Overall <" (rtos (setq H_VAL (cond (H_VAL) (1.0) ) ) ) "> : " ) ) ) (H_VAL) ) )
    (setq H_VAL_MAX 112.5 )
    (setq H_VAL_MIN 50 )
    
    ;preloop_and_while
      (setq vt_point_i 0)
      (setq vt_point_ii 1)
      (while (< vt_point_i (length vt_point_))
        (setq vt_point_ename_pt1 (nth  vt_point_i vt_point_))
        (if (= vt_point_ii (length vt_point_))
          (progn
            (setq vt_point_ename_pt2 (nth  0 vt_point_))
          )
          (setq vt_point_ename_pt2 (nth  vt_point_ii vt_point_))
        )
        
    
        (setq vt_point_ename_mid_ (TA:midpoint vt_point_ename_pt1 vt_point_ename_pt2))
        (setq vt_distance_ (distance vt_point_ename_pt1 vt_point_ename_pt2))
        
        (setq vt_angle_ (rad-to-deg (angle vt_point_ename_pt1 vt_point_ename_pt2)))
        
        (command "insert" "001 - DYNAMIC REC&SSQ SHAPE SOLID_midpoint" vt_point_ename_mid_ 1 vt_angle_ )
        (setq new_insert_blk_ (entlast))
        (setq new_insert_blk_obj_ (vlax-ename->vla-object new_insert_blk_))
        ; (LM:setdynpropvalue new_insert_blk_obj_ "H" H_VAL )
        
        (if (or (= vt_point_i 0) (= vt_point_i 2) )
          (progn
            (LM:setdynpropvalue new_insert_blk_obj_ "W" (- (- vt_distance_ (* 50 2) ) 50))
            (LM:setdynpropvalue new_insert_blk_obj_ "H" 50 )
          )
          
          (LM:setdynpropvalue new_insert_blk_obj_ "H" 75 )
        )
        (if (or (= vt_point_i 0) (= vt_point_i 2) )
          (progn
            (LM:setdynpropvalue new_insert_blk_obj_ "W" (- (- vt_distance_ (* 50 2) ) 50))
            (LM:setdynpropvalue new_insert_blk_obj_ "H" 50 )
          )
          (LM:setdynpropvalue new_insert_blk_obj_ "W" vt_distance_)
          
        )
        
        
        (setq vt_point_i (+ vt_point_i 1))
        (setq vt_point_ii (+ vt_point_ii 1))
      )
    ;
  )
  (defun c:ztest_ztt ()
    ;this_code_only_work_with_"A$Cc9a77f15"
    (setq pline_ename_ (car (entsel "specify Object")))
    (setq insertion_point_ (getpoint ))
    (command "insert" "A$Cc9a77f15" insertion_point_ 1 0)
    (TA:Get_Pline_vertext_angle_case1 pline_ename_)
    (setq tt_len_ (TA:get_vertex_len_ pline_ename_))
    (setq tt_len_total_ (length tt_len_))
    (setq dynamic_ename_ (entlast))
    (setq dynamic_obj_ (vlax-ename->vla-object dynamic_ename_))
    (LM:setdynpropvalue dynamic_obj_ "Visibility1" tt_len_total_)

    ;preloop_and_while
      (setq tt_len_i 0)
      (setq tt_len_ii 1) 
      (while (< tt_len_i (length tt_len_))
        (setq tt_len_num_ (nth  tt_len_i tt_len_))
        (setq tt_len_parametername_ (strcat "LINE" (rtos tt_len_ii 2 0)))
        (LM:setdynpropvalue dynamic_obj_ tt_len_parametername_ tt_len_num_)
        (setq tt_len_i (+ tt_len_i 1))
        (setq tt_len_ii (+ tt_len_ii 1))
      )
    ;
    
  )
  (defun c:increment_rotation_to_block_inc1_ ()
    ;DES from dev
    ;this is code work with Block only by process of code was design by selection set and filter name , sorting corrdinate axis block from SUB-FUNC TA:EF_Filter_ss_set_ 
    ;TA:standard_list_croodinate_sorting 
    ;selection_set
      (if  ;pre_select_ssget_or_post_select_ssget
        (= 
          (setq ss_pre_filter_set_xx_ (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "INSERT,line,lwpolyline") ;type of object
                                          ; (cons 8 "000 - GRID")   ;kind of layer
                                          ; (cons 2 "000-GRIDLINE_DYN")       ;kind of nameblock
                                          (cons 62 1)           ;kind of color call sign with color code index
                                        )
                                      )
          )
        )
        (sslength ss_pre_filter_set_xx_)
      )
    ;
    ;filter and sorting axis selection set
      (setq ssget_efname_filter_ (TA:EF_Filter_ss_set_ ss_pre_filter_set_xx_ "001 - AF100 VIEW 1"))
      (setq ssget_efname_filter_sorted_X_ (TA:standard_list_croodinate_sorting ssget_efname_filter_ "X"))
    ;
    ;user_input for increment rotation angle of block 
      (setq user_num_i (getreal "increment rotation angle of block "))
      (setq time_i 1)  
    ;
    ;preloop_and_while
      (setq ssget_efname_filter_sorted_X_i 0)
      (while (< ssget_efname_filter_sorted_X_i (length ssget_efname_filter_sorted_X_))
        (setq ssget_efname_filter_sorted_X_ename_ (car (nth  ssget_efname_filter_sorted_X_i ssget_efname_filter_sorted_X_)))
        (setq ssget_efname_filter_sorted_X_obj_ (vlax-ename->vla-object ssget_efname_filter_sorted_X_ename_))
        

          (setq get-rotation_angle (rad-to-deg (vla-get-rotation ssget_efname_filter_sorted_X_obj_ )))
          (if (< user_num_i 0)
            (progn
              (setq put-rotation (- get-rotation_angle  (* (* user_num_i time_i) -1)))
            )
              (setq put-rotation (+ get-rotation_angle  (* (* user_num_i time_i) -1)))
          )
          
          (vla-put-rotation ssget_efname_filter_sorted_X_obj_ (deg-to-rad put-rotation))

        
        
        (setq time_i (+ time_i 1))
        (setq ssget_efname_filter_sorted_X_i (+ ssget_efname_filter_sorted_X_i 1))
      )
    ;
    
    
    
  )
  (defun c:ccc1_ ()
    (setq cc_ename_ (car (entsel "specify Object")))
    (setq cc_obj_ (vlax-ename->vla-object cc_ename_))
    (setq cc_obj_get_rotation_ (vla-get-rotation cc_obj_))
    (setq name_block_ (strcat "000CUS - AF-100_END_CAP_" (rtos (rad-to-deg cc_obj_get_rotation_) 2 2) "_DEG"))

    (setq ss_set_ (ssget))
    (setq blk_get_pt_ (getpoint ))
    (command "_block"  name_block_ blk_get_pt_ ss_set_ "" )
    (command "insert" name_block_ blk_get_pt_ 1 1 0)
  )
;
;



(defun format-list (data)
  (print "(") ; พิมพ์เปิดวงเล็บ
  (foreach point data
    (princ " ") ; เพิ่มช่องว่างก่อนแต่ละรายการ
    (print point) ; แสดงแต่ละจุด
  )
  (print ")") ; พิมพ์ปิดวงเล็บ
)
(defun format-entity-list (data)
  (print "(") ; พิมพ์เปิดวงเล็บ
  (foreach entry data
    (cond
      ((listp entry) ; ตรวจสอบว่าเป็น list ย่อยหรือไม่
      (princ " ")   ; เพิ่มช่องว่าง
      (print entry) ; แสดง list
      )
      (T ; อื่น ๆ เช่น entity name
      (princ " ")   ; เพิ่มช่องว่าง
      (princ entry) ; แสดง entity
      )
    )
  )
  (print ")") ; พิมพ์ปิดวงเล็บ
)

;RASTER MACHNE FUNC
  (defun c:Foldline_ ()
    ;Foldline_process_
    (setq input_PT (Getpoint "specify point"))
    (setvar "osmode" 0)
    (setq PL_ename_ (car (entsel "specify Object")))
    (setq PL_L_ (TA:get_vertex_len_ PL_ename_ )) 
    ;preloop_and_while
      (setq PL_L_i 0)
      (while (< PL_L_i (length PL_L_))
        (setq PL_x (nth  PL_L_i PL_L_))
        (setq PL_xyz (list 
                      (+ PL_x (car input_PT)) 
                      (cadr input_PT) 
                      0
                    )
        )
        (command "line"
                input_PT
                PL_xyz
                ""
        )
        (if 
          (or
            (= PL_L_i 0)
            (= PL_L_i 2)
            (= PL_L_i 4)
            (= PL_L_i 6)
            (= PL_L_i 8)
            (= PL_L_i 10)
            (= PL_L_i 12)
            (= PL_L_i 14)
            (= PL_L_i 16)
            )
          (progn
            (vla-put-color (vlax-ename->vla-object (entlast)) 3)
          )
          (vla-put-color (vlax-ename->vla-object (entlast)) 1)
        )
        
        (setq input_PT PL_xyz )
        (setq PL_L_i (+ PL_L_i 1))
      )
    ;
    (setvar "osmode" 1215)
  )
  (defun c:F0 () ;คำสั่งหมุนแบบง่าย
    ;selection_set
      (if  ;pre_select_ssget_or_post_select_ssget
        (= 
          (setq ss_pre_filter_set_xx_ (ssget "I" 
                                            (list 
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "LINE") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
    ;

    (initget "Yes No")
    (setq ss_ ;Detect the variable's result in case of a function error
      (vl-catch-all-apply 
        (function 
          (lambda () 
            (setq DELETE_OBJ_ (not (eq "No" (getkword "\nKeep Existing point with object? [Yes/No] <Y>: "))))
          )
        )
      )
    )
    (if (and (= ss_ nil)  )
      (progn
        
        (setq input_RO_PT_ (car (entsel "Specify block "))
            input_RO_PT_ins (vlax-safearray->list (vlax-variant-value(vla-get-insertionpoint (vlax-ename->vla-object input_RO_PT_ ))))
        )
      )
      (setq input_RO_PT_ins (vlax-safearray->list (vlax-variant-value(vla-get-insertionpoint (vlax-ename->vla-object input_RO_PT_ )))))
      
    )
    
    
    (command "rotate" ss_pre_filter_set_xx_ "" input_RO_PT_ins 90)
  )
  (defun c:F90 () ;คำสั่งหมุนแบบง่าย
    ;selection_set
      (if  ;pre_select_ssget_or_post_select_ssget
        (= 
          (setq ss_pre_filter_set_xx_ (ssget "I" 
                                            (list 
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "LINE") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
    ;

    (initget "Yes No")
    (setq ss_ ;Detect the variable's result in case of a function error
      (vl-catch-all-apply 
        (function 
          (lambda () 
            (setq DELETE_OBJ_ (not (eq "No" (getkword "\nKeep Existing point with object? [Yes/No] <Y>: "))))
          )
        )
      )
    )
    (if (and (= ss_ nil)  )
      (progn
        
        (setq input_RO_PT_ (car (entsel "Specify block "))
            input_RO_PT_ins (vlax-safearray->list (vlax-variant-value(vla-get-insertionpoint (vlax-ename->vla-object input_RO_PT_ ))))
        )
      )
      (setq input_RO_PT_ins (vlax-safearray->list (vlax-variant-value(vla-get-insertionpoint (vlax-ename->vla-object input_RO_PT_ )))))
      
    )
    
    
    (command "rotate" ss_pre_filter_set_xx_ "" input_RO_PT_ins 270)
  )
  (defun c:QMM () ;คำสั่งหมุนแบบง่าย
    ;selection_set
      (if  ;pre_select_ssget_or_post_select_ssget
        (= 
          (setq ss_pre_filter_set_xx_ (ssget "I" 
                                            (list 
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "LINE") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
    ;

    (initget "Yes No")
    (setq ss_ ;Detect the variable's result in case of a function error
      (vl-catch-all-apply 
        (function 
          (lambda () 
            (setq DELETE_OBJ_ (not (eq "No" (getkword "\nKeep Existing point with object? [Yes/No] <Y>: "))))
          )
        )
      )
    )
    (if (and (= ss_ nil)  )
      (progn
        
        (setq input_RO_PT_ (car (entsel "Specify block "))
            input_RO_PT_ins (vlax-safearray->list (vlax-variant-value(vla-get-insertionpoint (vlax-ename->vla-object input_RO_PT_ ))))
        )
      )
      (setq input_RO_PT_ins (vlax-safearray->list (vlax-variant-value(vla-get-insertionpoint (vlax-ename->vla-object input_RO_PT_ )))))
      
    )
    (setq input_RO_PT_ins_end (list (+ 250 (car input_RO_PT_ins)) (cadr input_RO_PT_ins) 0) )
    
    (command "mirror" ss_pre_filter_set_xx_ "" input_RO_PT_ins input_RO_PT_ins_end "Y"  )
    
    
    
  )
  (defun c:STAMP_START_CIRCLE_AT_LINE_CCL ()
    ;selection_set
      (if  ;pre_select_ssget_or_post_select_ssget
        (= 
          (setq ss_pre_filter_set_xx_ (ssget "I" 
                                            (list 
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "LINE") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq new_pt_line_ (TA:Get_line_ins_point_ ss_pre_filter_set_xx_ename_ ))
        (command "circle" (car new_pt_line_ ) 3  )
        
    
        (if (= ss_pre_filter_set_xx_i 0)
          (progn
            (command "circle" (cadr new_pt_line_ ) 3  )
          )
        )
        
        (setq ss_pre_filter_set_xx_i (+ ss_pre_filter_set_xx_i 1))
        
      )
    ;  
    
    
  )
  (defun TAS:MAKE_AREA_SELECTION (test_point_)
    ;example_user_input_
      ; (setq test_point_ (getpoint))
      (setvar "osmode" 0)
    ;
    ;existing_area_list_
      (setq selection_area_list_ (list (list 40.5877 50.9799) 
                                      (list 77.3102 106.0)
                                      (list 167.31 12.0)
                                      (list 128.925 37.0)
                                      (list 90.0 13.7238)
                                      (list 180.0 215.348)
                                      (list 270.0 312.079)
                                      (list 3.42803e-14 380.03)
                                      (list 90.0 127.355)
                                      (list 180.0 191.728)
                                      (list 90.0 3.0)
                                )
      )
    ;
    ;preloop_and_while
      (setq sumpoint_ ())
      (setq selection_area_list_i 0)
      (while (< selection_area_list_i (length selection_area_list_))
        (setq selection_area_list_ang_ (car (nth  selection_area_list_i selection_area_list_)))
        (setq selection_area_list_length_ (cadr (nth  selection_area_list_i selection_area_list_)))
        (setq test_point_in_ test_point_)
        (setq test_point_out_ (polar 
                                test_point_in_
                                (deg-to-rad selection_area_list_ang_)
                                selection_area_list_length_
                              )
        )
        (setq test_point_ test_point_out_)
        ; (command "point" test_point_ )
        (setq sumpoint_ (cons test_point_ sumpoint_))
        (setq selection_area_list_i (+ selection_area_list_i 1))
      )
      (setvar "osmode" 1215)
      (princ (setq sumpoint_ (reverse sumpoint_)))
    ;
  )
  (defun c:E1TEST ()
    
    ;preset_user_input_
      (setq method_1                                  "1 = fold up 90") 
      (setq method_2                                  "2 = fold up 0") 
      (setq method_3                                  "3 = move ") 
      (setq method_4                                  "4 = mirror ") 
      (setq method_5                                  "5 = copy step ") 
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (and (= ss_ nil)  )
        (progn
          (setq input_RO_PT_    (car (entsel "Specify block "))
                input_RO_PT_ins (vlax-safearray->list (vlax-variant-value (vla-get-insertionpoint (vlax-ename->vla-object input_RO_PT_)) ) )
                input_RO_BOL_ (TA:ename+vla-getboundingbox (vlax-ename->vla-object input_RO_PT_))
                
          )
          (setq distance1_ (LM:getdynpropvalue (vlax-ename->vla-object input_RO_PT_ ) "distance1" ))
          (setq distance1x_ distance1_)
          (setq offset_pt_ 100)
          (setq ii-i 1)
        )
        (setq input_RO_PT_ins (vlax-safearray->list (vlax-variant-value(vla-get-insertionpoint (vlax-ename->vla-object input_RO_PT_ ))))
              input_RO_BOL_ (TA:ename+vla-getboundingbox (vlax-ename->vla-object input_RO_PT_))
              
        )
      )
    ;
    ;ss area
      (setq ssset_boundary_ (ssget "WP" 
                                  (setq input_RO_PT_ins_PT_LIST (TAS:MAKE_AREA_SELECTION (list 
                                                                                          (+ 0.01 (car input_RO_PT_ins))
                                                                                          (cadr input_RO_PT_ins)
                                                                                          (caddr input_RO_PT_ins)
                                                                                        ) 
                                                                ) 
                                  )
                                  (list 
                                    (cons 0 "line")
                                  )
                            )
      )
    
    ;
    ;preloop_and_while_
      (setq LV_1_ans_ nil)
      (while (/= (vl-catch-all-error-p LV_1_ans_ ) T)
        ;error_detect_
        (setq LV_1_ans_ ;Detect the variable's result in case of a function error
          (vl-catch-all-apply 
            (function 
              (lambda () 
                (setq LV_1_ans_int_ (cond ( (getint (strcat method_1 "\n" method_2 "\n" method_3 "\n" method_4 "\n" method_5 "\n<" (rtos (setq LV_1_ans_int_ (cond (LV_1_ans_int_) (1.0) ) ) ) "> : " ) ) ) (LV_1_ans_int_) ) )
                
              )
            )
          )
        )
        (if (= (vl-catch-all-error-p LV_1_ans_ ) T)
          (progn
            (vl-catch-all-error-message LV_1_ans_ )
          )
        )
        ;
        
        ;condition_for_folding_control
          (cond
            (;raster_case_1
              (and
                (= LV_1_ans_int_ 1)
                (/= (vl-catch-all-error-p LV_1_ans_ ) T)
              )
              (progn
                
                (command "rotate" ssset_boundary_ "" input_RO_PT_ins 270)
                (princ "raster_case_1")
              )
            )
            (;raster_case_2
              (and
                (= LV_1_ans_int_ 2)
                (/= (vl-catch-all-error-p LV_1_ans_ ) T)
              )
              (progn
                
                (command "rotate" ssset_boundary_ "" input_RO_PT_ins 90)
                (princ "raster_case_2")
              )
            )
            (;raster_case_3
              (and
                (= LV_1_ans_int_ 3)
                (/= (vl-catch-all-error-p LV_1_ans_ ) T)
              )
              (progn
                (setq ss_L_ (ssget "C" 
                                (list (+ (car input_RO_PT_ins) -500) 
                                      (+ (cadr input_RO_PT_ins) -5)
                                      0
                                )
                                (list (+ (car input_RO_PT_ins) 500) 
                                      (+ (cadr input_RO_PT_ins) 5)
                                      0
                                )
                                (list (cons 0 "line") )
                        )
                )
                ; (command "rectangle" (list (+ (car input_RO_PT_ins) -500) (+ (cadr input_RO_PT_ins) -5) 0 ) (list (+ (car input_RO_PT_ins) 500) (+ (cadr input_RO_PT_ins) 5) 0 ) )
                ;preloop_and_while
                  (setq ss_L_i 0)
                  (setq startpt_sum_list_ ())
                  (while (< ss_L_i (sslength ss_L_))
                    (setq ss_L_ename_ (ssname ss_L_ ss_L_i))
                    (setq ss_L_obj_ (vlax-ename->vla-object ss_L_ename_))
                    (if 
                      (or 
                        (= (rad-to-deg (vla-get-angle ss_L_obj_)) 0)
                        (= (rad-to-deg (vla-get-angle ss_L_obj_)) 180)
                      )
                      (progn
                        (setq ss_L_ename_obj_start_end_pt_ (list 
                                                            (setq ss_L_ename_obj_startpt_ ( vlax-safearray->list ( vlax-variant-value ( vla-get-startpoint ss_L_obj_ ) ) ) )
                                                            (setq ss_L_ename_obj_endpt_ ( vlax-safearray->list ( vlax-variant-value ( vla-get-endpoint ss_L_obj_ ) ) ) )
                                                          )
                        )
                        (setq startpt_sum_list_ (cons ss_L_ename_obj_startpt_ startpt_sum_list_))
                      )
                    )
                    (setq ss_L_i (+ ss_L_i 1))
                  )
                  ;TA:stanndard_lambda_sorting
                    (setq startpt_sum_list_sorted_ (vl-sort startpt_sum_list_  ;bigest open indent list
                                                            (function 
                                                              (lambda (a b) 
                                                                (< (car a) (car b))
                                                              )
                                                            )
                                                  ) ;bigest close indent listLV_2_
                    )
                  ;
                ;
                ;preloop_and_while
                  (setq LV_3_ans_ nil)
                  (setq move_i 0)
                  (while (/= (vl-catch-all-error-p LV_3_ans_ ) T)
                    ;error_detect_
                    (setq LV_3_ans_ ;Detect the variable's result in case of a function error
                      (vl-catch-all-apply 
                        (function 
                          (lambda () 
                            (setq LV_3_ans_int_ (cond ( (getint (strcat "\nspecify get move to point\n<" (rtos (setq LV_3_ans_int_ (cond (LV_3_ans_int_) (1.0) ) ) ) "> : " ) ) ) (LV_3_ans_int_) ) )
                          )
                        )
                      )
                    )
                    (if (= (vl-catch-all-error-p LV_3_ans_ ) T)
                      (progn
                        (vl-catch-all-error-message LV_3_ans_ )
                      )
                    )
                    ;
                    ;
                    (if 
                      (and 
                        (= LV_3_ans_ 1)
                        (< move_i (- (length startpt_sum_list_sorted_ ) 1) )
                      )
                      (progn
                        (setq move_i (+ move_i LV_3_ans_))
                          (vla-move 
                            (vlax-ename->vla-object input_RO_PT_)
                            (vlax-3d-point (setq aa_obj_ins_ (vlax-safearray->list (vlax-variant-value (vla-get-insertionpoint (vlax-ename->vla-object input_RO_PT_))))))
                            (vlax-3d-point (nth (atoi (rtos move_i 2 0)) startpt_sum_list_sorted_ ))
                          )
                      )
                    )
                    (if (or 
                          (= move_i (- (length startpt_sum_list_sorted_ ) 1) )
                        )
                      (progn
                        (setq move_i -1)
                      )
                    )
                    ;
                  )
                  (setq input_RO_PT_ins (vlax-safearray->list 
                                          (vlax-variant-value (vla-get-insertionpoint (vlax-ename->vla-object input_RO_PT_) ) )
                                        )
                        input_RO_BOL_   (TA:ename+vla-getboundingbox (vlax-ename->vla-object input_RO_PT_) )
                  )
                  (setq ssset_boundary_ (ssget "WP" 
                                              (setq input_RO_PT_ins_PT_LIST (TAS:MAKE_AREA_SELECTION 
                                                                              (list 
                                                                                (+ 0.01 (car input_RO_PT_ins ) ) 
                                                                                (cadr input_RO_PT_ins) 
                                                                                (caddr input_RO_PT_ins) 
                                                                              )
                                                                            )
                                              )
                                              (list 
                                                (cons 0 "line")
                                              )
                                        )
                  )
                  
                ;
                (princ "raster_case_3")
              )
            )
            (;raster_case_4
              (and
                (= LV_1_ans_int_ 4)
                (/= (vl-catch-all-error-p LV_1_ans_ ) T)
              )
              (progn
                (setq input_RO_PT_ins (vlax-safearray->list (vlax-variant-value (vla-get-insertionpoint (vlax-ename->vla-object input_RO_PT_)))))
                (setq input_RO_BOL_ (TA:ename+vla-getboundingbox (vlax-ename->vla-object input_RO_PT_)))   
                (setq ss_L_minror_ (ssget "C" 
                                (cadr input_RO_BOL_)
                                (caddr input_RO_BOL_)
                                
                                (list (cons 0 "line") )
                        )
                )
                ;preloop_and_while
                  (setq LV_4_ans_ nil)
                  (setq mirror_i 0)
                  (while (/= (vl-catch-all-error-p LV_4_ans_ ) T)
                    ;error_detect_
                    (setq LV_4_ans_ ;Detect the variable's result in case of a function error
                      (vl-catch-all-apply 
                        (function 
                          (lambda () 
                            (setq LV_4_ans_int_ (cond ( (getint (strcat "\nspecify get miror to point \n0 = Ver 1 = Hon\n<" (rtos (setq LV_4_ans_int_ (cond (LV_4_ans_int_) (1.0) ) ) ) "> : " ) ) ) (LV_4_ans_int_) ) )
                          )
                        )
                      )
                    )
                    (if (= (vl-catch-all-error-p LV_4_ans_ ) T)
                      (progn
                        (vl-catch-all-error-message LV_4_ans_ )
                      )
                    )
                    ;
                    (cond
                      (;mirror_case_1
                        (and
                            (= LV_4_ans_ 0)
                            (/= (vl-catch-all-error-p LV_4_ans_ ) T)
                        )
                        (progn
                          (setq input_RO_PT_ins_end (list (+ 0 (car input_RO_PT_ins)) (+ 500 (cadr input_RO_PT_ins)) 0) )
                          (command "mirror" ss_L_minror_ "" input_RO_PT_ins input_RO_PT_ins_end "Y"  )
                          (princ "mirror_case_1")
                        )
                      )
                      (;mirror_case_2
                        (and
                            (= LV_4_ans_ 1)
                            (/= (vl-catch-all-error-p LV_4_ans_ ) T)
                        )
                        (progn
                          (setq input_RO_PT_ins_end (list (+ 500 (car input_RO_PT_ins)) (+ 0 (cadr input_RO_PT_ins)) 0) )
                          (command "mirror" ss_L_minror_ "" input_RO_PT_ins input_RO_PT_ins_end "Y"  )
                          (princ "mirror_case_2")
                        )
                      )
                      
                      
                    )
                    
                    
                    ;
                  )
                ;
                (setq ssset_boundary_ (ssget "WP" 
                                  (setq input_RO_PT_ins_PT_LIST (TAS:MAKE_AREA_SELECTION (list 
                                                                                          (+ 0.01 (car input_RO_PT_ins))
                                                                                          (cadr input_RO_PT_ins)
                                                                                          (caddr input_RO_PT_ins)
                                                                                        ) 
                                                                ) 
                                  )
                                  (list 
                                    (cons 0 "line")
                                  )
                            )
                )
                (princ "raster_case_4")
              )
            )
            (;raster_case_5
              (and
                (= LV_1_ans_int_ 5)
                (/= (vl-catch-all-error-p LV_1_ans_ ) T)
              )
              (progn
                (setq ss_copy_ (ssget "C" 
                                (cadr input_RO_BOL_)
                                (caddr input_RO_BOL_)
                                
                                (list (cons 0 "line,insert") )
                        )
                )
                (sslength ss_copy_)
                
                ;copy_process
                  (setq new_copy_insertion_point_ (list 
                                                    (nth 0 (cadr input_RO_BOL_))
                                                    (- (- (nth 1 (cadr input_RO_BOL_)) distance1x_  ) offset_pt_)
                                                    0
                                                  )
                  )
                  (setq sssssssss (LM:vl-setattributevalue (vlax-ename->vla-object input_RO_PT_ ) "step_no." ii-i )  )
                  (command "copy" ss_copy_ "" ( cadr input_RO_BOL_) new_copy_insertion_point_ )
                  
                  (setq distance1x_ (+ distance1x_ distance1_))  
                  (setq offset_pt_ (+ offset_pt_ 100))  
                  (setq ii-i (+ ii-i 1))  
                ;
                (princ "raster_case_5")
              )
            )
            (;raster_case_5
              (and
                (vl-catch-all-error-p LV_1_ans_ )
                  
              )
              (progn
                
                (princ "raster_case_6")
              )
            )
          )
        ;
      )
    ;
  )
;
;dynamic temp for create ACP line and cut
  (defun c:was1 ()
    (setvar "osmode" 0)

    ;user_input_and_get-data_
      (setq acp_main_1_ename_ (car (entsel)))
      (setq acp_main_1_obj_ (vlax-ename->vla-object acp_main_1_ename_))
      (setq acp_main_1_as10_list_ (TA:Get_Pline_vertext_angle_case1 acp_main_1_ename_ ))

    ;
    ;offset_2-2_groove_angle_tri-C__
      (TA:Offset_Pline_multi_vertex_ acp_main_1_ename_ 0.50 "min")
      (setq 2-2_groove_angle_tri-C__ename_ (entlast)) 
      (setq 2-2_groove_angle_tri-C__obj_ (vlax-ename->vla-object 2-2_groove_angle_tri-C__ename_))
      (setq 2-2_groove_angle_tri-C__as10_list_ (TA:Get_Pline_vertext_angle_case1 2-2_groove_angle_tri-C__ename_ )) 
    ;
    ;preloop_and_while
      (setq acp_main_1_as10_i 1)
      (while (< acp_main_1_as10_i (- (length acp_main_1_as10_list_ ) 1))
        (setq acp_main_1_as10_list_val (nth  acp_main_1_as10_i  acp_main_1_as10_list_))
        (setq 2-2_groove_angle_tri-C__as10_list_val (nth  acp_main_1_as10_i  2-2_groove_angle_tri-C__as10_list_))
        (setq groove_angle_90V (rad-to-deg (angle (car 2-2_groove_angle_tri-C__as10_list_val) (car acp_main_1_as10_list_val))))
        (setq groove_angle_90H (- groove_angle_90V  90))
        (setq groove_angle_tri-A_ (- groove_angle_90H (cadr 2-2_groove_angle_tri-C__as10_list_val)))
        (setq groove_angle_tri-B_ 90)
        (setq groove_angle_tri-C_ (- groove_angle_tri-B_ groove_angle_tri-A_ ))
        ;TRIGONMETRY-PROCESS
          (setq point_1 
                  (polar 
                    (polar (car 2-2_groove_angle_tri-C__as10_list_val) (deg-to-rad groove_angle_90H) 0.1 )
                    (deg-to-rad (+ groove_angle_90V 180))
                    (/ (* 0.10000 (sin (deg-to-rad groove_angle_tri-A_))) (sin (deg-to-rad groove_angle_tri-C_)) )
                  )
          )
          ; (command "point" point_1 )
          
          (setq point_2
                  (polar 
                    point_1
                      (deg-to-rad groove_angle_90V)
                      0.2
                  )
          )
          ; (command "point" point_2 )
          (setq point_3
                  (polar 
                    point_2
                    (deg-to-rad (+ 90 groove_angle_90V))
                    0.2
                  )
          )
          ; (command "point" point_3 )
          (setq point_4
                  (polar 
                    point_3
                    (deg-to-rad (+ 180 groove_angle_90V))
                    0.2
                  )
          )
          ; (command "point" point_4 )
          ; (command "_line" point_1 point_2 ""   )
          ; (command "_line" point_2    "")
          ; (command "_line" point_3    "")
          ; (command "_line" point_4    "")
          (setq new_ssset_(ssadd))
          (setq new_ssset_ (ssadd 2-2_groove_angle_tri-C__ename_ new_ssset_  )  )
          (command "pline" point_1 point_2 point_3 point_4 "")    
          (setq new_groove_ename (entlast))
          (setq new_ssset_ (ssadd new_groove_ename new_ssset_  )  )
          (command "breakatpoint" 2-2_groove_angle_tri-C__ename_ point_1)
          (setq new_groove_ex1 (entlast))
          (setq new_ssset_ (ssadd new_groove_ex1 new_ssset_  )  )
          (command "breakatpoint" 2-2_groove_angle_tri-C__ename_ point_4)
          (setq new_groove_ex2 (entlast))
          (vla-delete (vlax-ename->vla-object new_groove_ex2))
          
          
          (command "pedit" "m" new_ssset_ "" "J" "" "")
        ;
      

        (setq acp_main_1_as10_i (+ acp_main_1_as10_i 1))
      )
    ;

    (setvar "osmode" 1215)
  )
  (defun c:was3 ()
    (setvar "osmode" 0)

    ;user_input_and_get-data_
      (setq acp_main_1_ename_ (car (entsel)))
      (setq acp_main_1_obj_ (vlax-ename->vla-object acp_main_1_ename_))
      (setq acp_main_1_as10_list_ (TA:Get_Pline_vertext_angle_case1 acp_main_1_ename_ ))

    ;
    ;offset_2-2_groove_angle_tri-C__
      (TA:Offset_Pline_multi_vertex_ acp_main_1_ename_ 3.5 "min")
      (setq 2-2_groove_angle_tri-C__ename_ (entlast)) 
      (setq 2-2_groove_angle_tri-C__obj_ (vlax-ename->vla-object 2-2_groove_angle_tri-C__ename_))
      (setq 2-2_groove_angle_tri-C__as10_list_ (TA:Get_Pline_vertext_angle_case1 2-2_groove_angle_tri-C__ename_ )) 
    ;
    ;preloop_and_while
      (setq acp_main_1_as10_i 1)
      (while (< acp_main_1_as10_i (- (length acp_main_1_as10_list_ ) 1))
        (setq acp_main_1_as10_list_val (nth  acp_main_1_as10_i  acp_main_1_as10_list_))
        (setq 2-2_groove_angle_tri-C__as10_list_val (nth  acp_main_1_as10_i  2-2_groove_angle_tri-C__as10_list_))
        (setq groove_angle_90V (rad-to-deg (angle (car 2-2_groove_angle_tri-C__as10_list_val) (car acp_main_1_as10_list_val))))
        (setq groove_angle_90H (- groove_angle_90V  90))
        (setq groove_angle_tri-A_ (- groove_angle_90H (cadr 2-2_groove_angle_tri-C__as10_list_val)))
        (setq groove_angle_tri-B_ 90)
        (setq groove_angle_tri-C_ (- groove_angle_tri-B_ groove_angle_tri-A_ ))
        ;TRIGONMETRY-PROCESS
          (setq point_1 
                  (polar 
                    (polar (car 2-2_groove_angle_tri-C__as10_list_val) (deg-to-rad groove_angle_90H) 0.1 )
                    (deg-to-rad (+ groove_angle_90V 180))
                    (/ (* 0.10000 (sin (deg-to-rad groove_angle_tri-A_))) (sin (deg-to-rad groove_angle_tri-C_)) )
                  )
          )
          ; (command "point" point_1 )
          
          (setq point_2
                  (polar 
                    point_1
                      (deg-to-rad groove_angle_90V)
                      0.2
                  )
          )
          ; (command "point" point_2 )
          (setq point_3
                  (polar 
                    point_2
                    (deg-to-rad (+ 90 groove_angle_90V))
                    0.2
                  )
          )
          ; (command "point" point_3 )
          (setq point_4
                  (polar 
                    point_3
                    (deg-to-rad (+ 180 groove_angle_90V))
                    0.2
                  )
          )
          ; (command "point" point_4 )
          ; (command "_line" point_1 point_2 ""   )
          ; (command "_line" point_2    "")
          ; (command "_line" point_3    "")
          ; (command "_line" point_4    "")
          (setq new_ssset_(ssadd))
          (setq new_ssset_ (ssadd 2-2_groove_angle_tri-C__ename_ new_ssset_  )  )
          (command "pline" point_1 point_2 point_3 point_4 "")    
          (setq new_groove_ename (entlast))
          (setq new_ssset_ (ssadd new_groove_ename new_ssset_  )  )
          (command "breakatpoint" 2-2_groove_angle_tri-C__ename_ point_1)
          (setq new_groove_ex1 (entlast))
          (setq new_ssset_ (ssadd new_groove_ex1 new_ssset_  )  )
          (command "breakatpoint" 2-2_groove_angle_tri-C__ename_ point_4)
          (setq new_groove_ex2 (entlast))
          (vla-delete (vlax-ename->vla-object new_groove_ex2))
          
          
          (command "pedit" "m" new_ssset_ "" "J" "" "")
        ;
      

        (setq acp_main_1_as10_i (+ acp_main_1_as10_i 1))
      )
    ;

    (setvar "osmode" 1215)
  )
  (defun c:was4 ()
    (setvar "osmode" 0)

    ;user_input_and_get-data_
      (setq acp_main_1_ename_ (car (entsel)))
      (setq acp_main_1_obj_ (vlax-ename->vla-object acp_main_1_ename_))
      (setq acp_main_1_as10_list_ (TA:Get_Pline_vertext_angle_case1 acp_main_1_ename_ ))

    ;
    ;offset_2-2_groove_angle_tri-C__
      (TA:Offset_Pline_multi_vertex_ acp_main_1_ename_ 4 "min")
      (setq 2-2_groove_angle_tri-C__ename_ (entlast)) 
      (setq 2-2_groove_angle_tri-C__obj_ (vlax-ename->vla-object 2-2_groove_angle_tri-C__ename_))
      (setq 2-2_groove_angle_tri-C__as10_list_ (TA:Get_Pline_vertext_angle_case1 2-2_groove_angle_tri-C__ename_ )) 
    ;
    ;preloop_and_while
      (setq acp_main_1_as10_i 1)
      (while (< acp_main_1_as10_i (- (length acp_main_1_as10_list_ ) 1))
        (setq acp_main_1_as10_list_val (nth  acp_main_1_as10_i  acp_main_1_as10_list_))
        (setq 2-2_groove_angle_tri-C__as10_list_val (nth  acp_main_1_as10_i  2-2_groove_angle_tri-C__as10_list_))
        (setq groove_angle_90V (rad-to-deg (angle (car 2-2_groove_angle_tri-C__as10_list_val) (car acp_main_1_as10_list_val))))
        (setq groove_angle_90H (- groove_angle_90V  90))
        (setq groove_angle_tri-A_ (- groove_angle_90H (cadr 2-2_groove_angle_tri-C__as10_list_val)))
        (setq groove_angle_tri-B_ 90)
        (setq groove_angle_tri-C_ (- groove_angle_tri-B_ groove_angle_tri-A_ ))
        ;TRIGONMETRY-PROCESS
          (command "point" (car 2-2_groove_angle_tri-C__as10_list_val))
          (setq point_1 
                  (polar 
                    (polar (car 2-2_groove_angle_tri-C__as10_list_val) (deg-to-rad groove_angle_90H) 0.1 )
                    (deg-to-rad (+ groove_angle_90V 180))
                    (/ (* 0.10000 (sin (deg-to-rad groove_angle_tri-A_))) (sin (deg-to-rad groove_angle_tri-C_)) )
                  )
          )
          (command "point" point_1 )       
          (setq point_2
                  (polar 
                    point_1
                      (deg-to-rad groove_angle_90V)
                      0.2
                  )
          )
          (command "point" point_2 )
          (setq point_3
                  (polar 
                    point_2
                    (deg-to-rad (+ 90 groove_angle_90V))
                    0.2
                  )
          )
          (command "point" point_3 )
          (setq point_4
                  (polar 
                    point_3
                    (deg-to-rad (+ 180 groove_angle_90V))
                    0.2
                  )
          )
          (command "point" point_4 )
          ; (command "_line" point_1 point_2 ""   )
          ; (command "_line" point_2    "")
          ; (command "_line" point_3    "")
          ; (command "_line" point_4    "")
          (setq new_ssset_(ssadd))
          (setq new_ssset_ (ssadd 2-2_groove_angle_tri-C__ename_ new_ssset_  )  )
          (command "pline" point_1 point_2 point_3 point_4 "")    
          (setq new_groove_ename (entlast))
          (setq new_ssset_ (ssadd new_groove_ename new_ssset_  )  )
          (command "breakatpoint" 2-2_groove_angle_tri-C__ename_ point_1)
          (setq new_groove_ex1 (entlast))
          (setq new_ssset_ (ssadd new_groove_ex1 new_ssset_  )  )
          (command "breakatpoint" 2-2_groove_angle_tri-C__ename_ point_4)
          (setq new_groove_ex2 (entlast))
          (vla-delete (vlax-ename->vla-object new_groove_ex2))
          
          
          (command "pedit" "m" new_ssset_ "" "J" "" "")
        ;
      

        (setq acp_main_1_as10_i (+ acp_main_1_as10_i 1))
      )
    ;

    (setvar "osmode" 1215)
  )
  (defun c:was41 ()
    (setvar "osmode" 0)

    ;user_input_and_get-data_
      (setq acp_main_1_ename_ (car (entsel)))
      (setq acp_main_1_obj_ (vlax-ename->vla-object acp_main_1_ename_))
      (setq acp_main_1_as10_list_ (TA:Get_Pline_vertext_angle_case1 acp_main_1_ename_ ))
      ; (if 
      ;   (and
      ;     (> (car (car (nth 0 (reverse acp_main_1_as10_list_)))) (car (car (nth 0 acp_main_1_as10_list_))) )
          
      ;   )
      ;   (progn
      ;     (command "reverse" acp_main_1_ename_ "" )
      ;     (setq acp_main_1_as10_list_ (TA:Get_Pline_vertext_angle_case1 acp_main_1_ename_ ))
      ;   )
      ; )
    ;
    ;offset_2-2_groove_angle_tri-C__
      (TA:Offset_Pline_multi_vertex_ acp_main_1_ename_ 0.50 "min")
      (setq 2-2_groove_angle_tri-C__ename_ (entlast)) 
      (setq 2-2_groove_angle_tri-C__obj_ (vlax-ename->vla-object 2-2_groove_angle_tri-C__ename_))
      (setq 2-2_groove_angle_tri-C__as10_list_ (TA:Get_Pline_vertext_angle_case1 2-2_groove_angle_tri-C__ename_ )) 
    ;
    ;offset_2-3_groove_angle_tri-C__
      (TA:Offset_Pline_multi_vertex_ acp_main_1_ename_ 3.50 "min")
      (setq 2-3_groove_angle_tri-C__ename_ (entlast)) 
      (setq 2-3_groove_angle_tri-C__obj_ (vlax-ename->vla-object 2-3_groove_angle_tri-C__ename_))
      (setq 2-3_groove_angle_tri-C__as10_list_ (TA:Get_Pline_vertext_angle_case1 2-3_groove_angle_tri-C__ename_ )) 
    ;
    ;offset_2-4_groove_angle_tri-C__
      (TA:Offset_Pline_multi_vertex_ acp_main_1_ename_ 4 "min")
      (setq 2-4_groove_angle_tri-C__ename_ (entlast)) 
      (setq 2-4_groove_angle_tri-C__obj_ (vlax-ename->vla-object 2-4_groove_angle_tri-C__ename_))
      (setq 2-4_groove_angle_tri-C__as10_list_ (TA:Get_Pline_vertext_angle_case1 2-4_groove_angle_tri-C__ename_ )) 
    ;

    ;preloop_and_while
      (setq acp_main_1_as10_i 1)
      (while (< acp_main_1_as10_i (- (length acp_main_1_as10_list_ ) 1))
        
          ;2-2process
            (setq acp_main_1_as10_list_val (nth  acp_main_1_as10_i  acp_main_1_as10_list_))
            (setq 2-2_groove_angle_tri-C__as10_list_val (nth  acp_main_1_as10_i  2-2_groove_angle_tri-C__as10_list_))
            (setq 2-2_groove_angle_90V (rad-to-deg (angle (car 2-2_groove_angle_tri-C__as10_list_val) (car acp_main_1_as10_list_val))))
            (setq 2-2_groove_angle_90H (- 2-2_groove_angle_90V  90))
            (setq 2-2_groove_angle_tri-A_ (- 2-2_groove_angle_90H (cadr 2-2_groove_angle_tri-C__as10_list_val)))
            (setq 2-2_groove_angle_tri-B_ 90)
            (setq 2-2_groove_angle_tri-C_ (- 2-2_groove_angle_tri-B_ 2-2_groove_angle_tri-A_ ))
            ;TRIGONMETRY-PROCESS
              (setq 2-2point_1 
                      (polar 
                        (polar (car 2-2_groove_angle_tri-C__as10_list_val) (deg-to-rad 2-2_groove_angle_90H) 0.1 )
                        (deg-to-rad (+ 2-2_groove_angle_90V 180))
                        (/ (* 0.10000 (sin (deg-to-rad 2-2_groove_angle_tri-A_))) (sin (deg-to-rad 2-2_groove_angle_tri-C_)) )
                      )
              )
              ;(command "point" 2-2point_1 )
              (setq 2-2point_2
                      (polar 
                        2-2point_1
                          (deg-to-rad 2-2_groove_angle_90V)
                          0.2
                      )
              )
              ;(command "point" 2-2point_2 )
              (setq 2-2point_3
                      (polar 
                        2-2point_2
                        (deg-to-rad (+ 90 2-2_groove_angle_90V))
                        0.2
                      )
              )
              ;(command "point" 2-2point_3 )
              (setq 2-2point_4
                      (polar 
                        2-2point_3
                        (deg-to-rad (+ 180 2-2_groove_angle_90V))
                        0.2
                      )
              )
              ; (command "point" 2-2point_4 )
        
              ; (command "point" 2-2point_1 )
              ; (command "point" 2-2point_2 )
              ; (command "point" 2-2point_3 )
              ; (command "point" 2-2point_4 )
              
    
              (setq new_ssset_(ssadd))
              (sslength new_ssset_)
              (setq new_ssset_ (ssadd 2-2_groove_angle_tri-C__ename_ new_ssset_  )  )
              (command "pline" 2-2point_1 2-2point_2 2-2point_3 2-2point_4 "")    
              (setq new_groove_ename (entlast)) 
              (setq new_ssset_ (ssadd new_groove_ename new_ssset_  )  )
              (command "breakatpoint" 2-2_groove_angle_tri-C__ename_ 2-2point_1)
              
              (setq new_groove_ex1 (entlast))
              (setq new_ssset_ (ssadd new_groove_ex1 new_ssset_  )  )
              (command "breakatpoint" 2-2_groove_angle_tri-C__ename_ 2-2point_4)
              (setq new_groove_ex2 (entlast))
              (if (/= (vl-prin1-to-string new_groove_ename) (vl-prin1-to-string new_groove_ex2))
                (progn
                  (vla-delete (vlax-ename->vla-object new_groove_ex2))
                )
              )
              
              
              
              (command "pedit" "m" new_ssset_ "" "J" "" "")
            ;
          ;
          ;2-3process
              (setq acp_main_1_as10_list_val (nth  acp_main_1_as10_i  acp_main_1_as10_list_))
              (setq 2-3_groove_angle_tri-C__as10_list_val (nth  acp_main_1_as10_i  2-3_groove_angle_tri-C__as10_list_))
              (setq 2-3_groove_angle_90V (rad-to-deg (angle (car 2-3_groove_angle_tri-C__as10_list_val) (car acp_main_1_as10_list_val))))
              (setq 2-3_groove_angle_90H (- 2-3_groove_angle_90V  90))
              (setq 2-3_groove_angle_tri-A_ (- 2-3_groove_angle_90H (cadr 2-3_groove_angle_tri-C__as10_list_val)))
              (setq 2-3_groove_angle_tri-B_ 90)
              (setq 2-3_groove_angle_tri-C_ (- 2-3_groove_angle_tri-B_ 2-3_groove_angle_tri-A_ ))
            ;TRIGONMETRY-PROCESS
              (setq 2-3point_1 
                      (polar 
                        (polar (car 2-3_groove_angle_tri-C__as10_list_val) (deg-to-rad 2-3_groove_angle_90H) 0.1 )
                        (deg-to-rad (+ 2-3_groove_angle_90V 180))
                        (/ (* 0.10000 (sin (deg-to-rad 2-3_groove_angle_tri-A_))) (sin (deg-to-rad 2-3_groove_angle_tri-C_)) )
                      )
              )
              ;(command "point" 2-3point_1 )
              
              (setq 2-3point_2
                      (polar 
                        2-3point_1
                          (deg-to-rad 2-3_groove_angle_90V)
                          0.2
                      )
              )
              ;(command "point" 2-3point_2 )
              (setq 2-3point_3
                      (polar 
                        2-3point_2
                        (deg-to-rad (+ 90 2-3_groove_angle_90V))
                        0.2
                      )
              )
              ; (command "point" 2-3point_3 )
              (setq 2-3point_4
                      (polar 
                        2-3point_3
                        (deg-to-rad (+ 180 2-3_groove_angle_90V))
                        0.2
                      )
              )
              ; (command "point" 2-3point_4 )
              (setq new_ssset_2(ssadd))
              (setq new_ssset_2 (ssadd 2-3_groove_angle_tri-C__ename_ new_ssset_2  )  )
              ; (command "pline" 2-3point_1 2-3point_2 2-3point_3 2-3point_4 "")    
              (command "pline" 2-3point_1 2-2point_2 2-2point_3 2-3point_4 "")
              (setq new_groove_ename (entlast))
              (setq new_ssset_2 (ssadd new_groove_ename new_ssset_2  )  )
              (command "breakatpoint" 2-3_groove_angle_tri-C__ename_ 2-3point_1)
              (setq new_groove_ex1 (entlast))
              (setq new_ssset_2 (ssadd new_groove_ex1 new_ssset_2  )  )
              (command "breakatpoint" 2-3_groove_angle_tri-C__ename_ 2-3point_4)
              (setq new_groove_ex2 (entlast))
              (if (/= (vl-prin1-to-string new_groove_ename) (vl-prin1-to-string new_groove_ex2))
                (progn
                  (vla-delete (vlax-ename->vla-object new_groove_ex2))
                )
              )
              
              
              (command "pedit" "m" new_ssset_2 "" "J" "" "")
            ;
          ;
          ;2-4process
              (setq acp_main_1_as10_list_val (nth  acp_main_1_as10_i  acp_main_1_as10_list_))
              (setq 2-4_groove_angle_tri-C__as10_list_val (nth  acp_main_1_as10_i  2-4_groove_angle_tri-C__as10_list_))
              (setq 2-4_groove_angle_90V (rad-to-deg (angle (car 2-4_groove_angle_tri-C__as10_list_val) (car acp_main_1_as10_list_val))))
              (setq 2-4_groove_angle_90H (- 2-4_groove_angle_90V  90))
              (setq 2-4_groove_angle_tri-A_ (- 2-4_groove_angle_90H (cadr 2-4_groove_angle_tri-C__as10_list_val)))
              (setq 2-4_groove_angle_tri-B_ 90)
              (setq 2-4_groove_angle_tri-C_ (- 2-4_groove_angle_tri-B_ 2-4_groove_angle_tri-A_ ))
            ;TRIGONMETRY-PROCESS
              (setq 2-4point_1 
                      (polar 
                        (polar (car 2-4_groove_angle_tri-C__as10_list_val) (deg-to-rad 2-4_groove_angle_90H) 0.1 )
                        (deg-to-rad (+ 2-4_groove_angle_90V 180))
                        (/ (* 0.10000 (sin (deg-to-rad 2-4_groove_angle_tri-A_))) (sin (deg-to-rad 2-4_groove_angle_tri-C_)) )
                      )
              )
              ; (command "point" 2-4point_1 )    
              (setq 2-4point_2
                      (polar 
                        2-4point_1
                          (deg-to-rad 2-4_groove_angle_90V)
                          0.2
                      )
              )
              ; (command "point" 2-4point_2 )
              (setq 2-4point_3
                      (polar 
                        2-4point_2
                        (deg-to-rad (+ 90 2-4_groove_angle_90V))
                        0.2
                      )
              )
              ;(command "point" 2-4point_3 )
              (setq 2-4point_4
                      (polar 
                        2-4point_3
                        (deg-to-rad (+ 180 2-4_groove_angle_90V))
                        0.2
                      )
              )
              ;(command "point" 2-4point_4 )
              (setq new_ssset_3(ssadd))
              (setq new_ssset_3 (ssadd 2-4_groove_angle_tri-C__ename_ new_ssset_3  )  )
              ; (command "pline" 2-4point_1 2-4point_2 2-4point_3 2-4point_4 "")    
              (command "pline" 2-4point_1 2-2point_2 2-2point_3 2-4point_4 "")
              (setq new_groove_ename (entlast))
              (setq new_ssset_3 (ssadd new_groove_ename new_ssset_3  )  )
              (command "breakatpoint" 2-4_groove_angle_tri-C__ename_ 2-4point_1)
              (setq new_groove_ex1 (entlast))
              (setq new_ssset_3 (ssadd new_groove_ex1 new_ssset_3  )  )
              (command "breakatpoint" 2-4_groove_angle_tri-C__ename_ 2-4point_4)
              (setq new_groove_ex2 (entlast))
              (if (/= (vl-prin1-to-string new_groove_ename) (vl-prin1-to-string new_groove_ex2))
                (progn
                  (vla-delete (vlax-ename->vla-object new_groove_ex2))
                )
              )
              
              
              (command "pedit" "m" new_ssset_3 "" "J" "" "")
            ;
            
            

          ;


          (setq acp_main_1_as10_i (+ acp_main_1_as10_i 1))
        
      )
    ;

    (setvar "osmode" 1215)
  )
  (defun c:was5 ()
    (setvar "osmode" 0)

    ;user_input_and_get-data_
      (setq acp_main_1_ename_ (car (entsel)))
      (setq acp_main_1_obj_ (vlax-ename->vla-object acp_main_1_ename_))
      (setq acp_main_1_as10_list_ (TA:Get_Pline_vertext_angle_case1 acp_main_1_ename_ ))

    ;
    ;offset_2-2_groove_angle_tri-C__
      (TA:Offset_Pline_multi_vertex_ acp_main_1_ename_ 0.50 "min")
      (setq 2-2_groove_angle_tri-C__ename_ (entlast)) 
      (setq 2-2_groove_angle_tri-C__obj_ (vlax-ename->vla-object 2-2_groove_angle_tri-C__ename_))
      (setq 2-2_groove_angle_tri-C__as10_list_ (TA:Get_Pline_vertext_angle_case1 2-2_groove_angle_tri-C__ename_ )) 
    ;
    ;offset_2-3_groove_angle_tri-C__
      (TA:Offset_Pline_multi_vertex_ acp_main_1_ename_ 3.50 "min")
      (setq 2-3_groove_angle_tri-C__ename_ (entlast)) 
      (setq 2-3_groove_angle_tri-C__obj_ (vlax-ename->vla-object 2-3_groove_angle_tri-C__ename_))
      (setq 2-3_groove_angle_tri-C__as10_list_ (TA:Get_Pline_vertext_angle_case1 2-3_groove_angle_tri-C__ename_ )) 
    ;
    ;offset_2-4_groove_angle_tri-C__
      (TA:Offset_Pline_multi_vertex_ acp_main_1_ename_ 4 "min")
      (setq 2-4_groove_angle_tri-C__ename_ (entlast)) 
      (setq 2-4_groove_angle_tri-C__obj_ (vlax-ename->vla-object 2-4_groove_angle_tri-C__ename_))
      (setq 2-4_groove_angle_tri-C__as10_list_ (TA:Get_Pline_vertext_angle_case1 2-4_groove_angle_tri-C__ename_ )) 
    ;
    ; ;offset_2-5_groove_angle_tri-C__
    ;   (TA:Offset_Pline_multi_vertex_ acp_main_1_ename_ 20 "min")
    ;   (setq 2-5_groove_angle_tri-C__ename_ (entlast)) 
    ;   (setq 2-5_groove_angle_tri-C__obj_ (vlax-ename->vla-object 2-5_groove_angle_tri-C__ename_))
    ;   (setq 2-5_groove_angle_tri-C__as10_list_ (TA:Get_Pline_vertext_angle_case1 2-5_groove_angle_tri-C__ename_ )) 
    ; ;
    ;preloop_and_while
      (setq acp_main_1_as10_i 1)
      (while (< acp_main_1_as10_i (- (length acp_main_1_as10_list_ ) 1))
        
          ;2-2process
            (setq acp_main_1_as10_list_val (nth  acp_main_1_as10_i  acp_main_1_as10_list_))
            (setq 2-2_groove_angle_tri-C__as10_list_val (nth  acp_main_1_as10_i  2-2_groove_angle_tri-C__as10_list_))
            (setq 2-2_groove_angle_90V (rad-to-deg (angle (car 2-2_groove_angle_tri-C__as10_list_val) (car acp_main_1_as10_list_val))))
            (setq 2-2_groove_angle_90H (- 2-2_groove_angle_90V  90))
            (setq 2-2_groove_angle_tri-A_ (- 2-2_groove_angle_90H (cadr 2-2_groove_angle_tri-C__as10_list_val)))
            (setq 2-2_groove_angle_tri-B_ 90)
            (setq 2-2_groove_angle_tri-C_ (- 2-2_groove_angle_tri-B_ 2-2_groove_angle_tri-A_ ))
            ;TRIGONMETRY-PROCESS
              (setq 2-2point_1 
                      (polar 
                        (polar (car 2-2_groove_angle_tri-C__as10_list_val) (deg-to-rad 2-2_groove_angle_90H) 0.1 )
                        (deg-to-rad (+ 2-2_groove_angle_90V 180))
                        (/ (* 0.10000 (sin (deg-to-rad 2-2_groove_angle_tri-A_))) (sin (deg-to-rad 2-2_groove_angle_tri-C_)) )
                      )
              )
              ;(command "point" 2-2point_1 )
              (setq 2-2point_2
                      (polar 
                        2-2point_1
                          (deg-to-rad 2-2_groove_angle_90V)
                          0.2
                      )
              )
              ;(command "point" 2-2point_2 )
              (setq 2-2point_3
                      (polar 
                        2-2point_2
                        (deg-to-rad (+ 90 2-2_groove_angle_90V))
                        0.2
                      )
              )
              ;(command "point" 2-2point_3 )
              (setq 2-2point_4
                      (polar 
                        2-2point_3
                        (deg-to-rad (+ 180 2-2_groove_angle_90V))
                        0.2
                      )
              )
              ;(command "point" 2-2point_4 )
              ; (command "_line" point_1 point_2 ""   )
              ; (command "_line" point_2    "")
              ; (command "_line" point_3    "")
              ; (command "_line" point_4    "")
              (setq new_ssset_(ssadd))
              (sslength new_ssset_)
              (setq new_ssset_ (ssadd 2-2_groove_angle_tri-C__ename_ new_ssset_  )  )
              (command "pline" 2-2point_1 2-2point_2 2-2point_3 2-2point_4 "")    
              (setq new_groove_ename (entlast))
              (setq new_ssset_ (ssadd new_groove_ename new_ssset_  )  )
              (command "breakatpoint" 2-2_groove_angle_tri-C__ename_ 2-2point_1)
              
              (setq new_groove_ex1 (entlast))
              (setq new_ssset_ (ssadd new_groove_ex1 new_ssset_  )  )
              (command "breakatpoint" 2-2_groove_angle_tri-C__ename_ 2-2point_4)
              (setq new_groove_ex2 (entlast))
              (vla-delete (vlax-ename->vla-object new_groove_ex2))
              
              
              (command "pedit" "m" new_ssset_ "" "J" "" "")
            ;
          ;
          ;2-3process
              (setq acp_main_1_as10_list_val (nth  acp_main_1_as10_i  acp_main_1_as10_list_))
              (setq 2-3_groove_angle_tri-C__as10_list_val (nth  acp_main_1_as10_i  2-3_groove_angle_tri-C__as10_list_))
              (setq 2-3_groove_angle_90V (rad-to-deg (angle (car 2-3_groove_angle_tri-C__as10_list_val) (car acp_main_1_as10_list_val))))
              (setq 2-3_groove_angle_90H (- 2-3_groove_angle_90V  90))
              (setq 2-3_groove_angle_tri-A_ (- 2-3_groove_angle_90H (cadr 2-3_groove_angle_tri-C__as10_list_val)))
              (setq 2-3_groove_angle_tri-B_ 90)
              (setq 2-3_groove_angle_tri-C_ (- 2-3_groove_angle_tri-B_ 2-3_groove_angle_tri-A_ ))
            ;TRIGONMETRY-PROCESS
              (setq 2-3point_1 
                      (polar 
                        (polar (car 2-3_groove_angle_tri-C__as10_list_val) (deg-to-rad 2-3_groove_angle_90H) 0.1 )
                        (deg-to-rad (+ 2-3_groove_angle_90V 180))
                        (/ (* 0.10000 (sin (deg-to-rad 2-3_groove_angle_tri-A_))) (sin (deg-to-rad 2-3_groove_angle_tri-C_)) )
                      )
              )
              ;(command "point" 2-3point_1 )
              
              (setq 2-3point_2
                      (polar 
                        2-3point_1
                          (deg-to-rad 2-3_groove_angle_90V)
                          0.2
                      )
              )
              ;(command "point" 2-3point_2 )
              (setq 2-3point_3
                      (polar 
                        2-3point_2
                        (deg-to-rad (+ 90 2-3_groove_angle_90V))
                        0.2
                      )
              )
              ; (command "point" 2-3point_3 )
              (setq 2-3point_4
                      (polar 
                        2-3point_3
                        (deg-to-rad (+ 180 2-3_groove_angle_90V))
                        0.2
                      )
              )
              ; (command "point" 2-3point_4 )
              (setq new_ssset_2(ssadd))
              (setq new_ssset_2 (ssadd 2-3_groove_angle_tri-C__ename_ new_ssset_2  )  )
              ; (command "pline" 2-3point_1 2-3point_2 2-3point_3 2-3point_4 "")    
              (command "pline" 2-3point_1 2-2point_2 2-2point_3 2-3point_4 "")
              (setq new_groove_ename (entlast))
              (setq new_ssset_2 (ssadd new_groove_ename new_ssset_2  )  )
              (command "breakatpoint" 2-3_groove_angle_tri-C__ename_ 2-3point_1)
              (setq new_groove_ex1 (entlast))
              (setq new_ssset_2 (ssadd new_groove_ex1 new_ssset_2  )  )
              (command "breakatpoint" 2-3_groove_angle_tri-C__ename_ 2-3point_4)
              (setq new_groove_ex2 (entlast))
              (vla-delete (vlax-ename->vla-object new_groove_ex2))
              
              
              (command "pedit" "m" new_ssset_2 "" "J" "" "")
            ;
          ;
          ;2-4process
              (setq acp_main_1_as10_list_val (nth  acp_main_1_as10_i  acp_main_1_as10_list_))
              (setq 2-4_groove_angle_tri-C__as10_list_val (nth  acp_main_1_as10_i  2-4_groove_angle_tri-C__as10_list_))
              (setq 2-4_groove_angle_90V (rad-to-deg (angle (car 2-4_groove_angle_tri-C__as10_list_val) (car acp_main_1_as10_list_val))))
              (setq 2-4_groove_angle_90H (- 2-4_groove_angle_90V  90))
              (setq 2-4_groove_angle_tri-A_ (- 2-4_groove_angle_90H (cadr 2-4_groove_angle_tri-C__as10_list_val)))
              (setq 2-4_groove_angle_tri-B_ 90)
              (setq 2-4_groove_angle_tri-C_ (- 2-4_groove_angle_tri-B_ 2-4_groove_angle_tri-A_ ))
            ;TRIGONMETRY-PROCESS
              (setq 2-4point_1 
                      (polar 
                        (polar (car 2-4_groove_angle_tri-C__as10_list_val) (deg-to-rad 2-4_groove_angle_90H) 0.1 )
                        (deg-to-rad (+ 2-4_groove_angle_90V 180))
                        (/ (* 0.10000 (sin (deg-to-rad 2-4_groove_angle_tri-A_))) (sin (deg-to-rad 2-4_groove_angle_tri-C_)) )
                      )
              )
              ; (command "point" 2-4point_1 )    
              (setq 2-4point_2
                      (polar 
                        2-4point_1
                          (deg-to-rad 2-4_groove_angle_90V)
                          0.2
                      )
              )
              ; (command "point" 2-4point_2 )
              (setq 2-4point_3
                      (polar 
                        2-4point_2
                        (deg-to-rad (+ 90 2-4_groove_angle_90V))
                        0.2
                      )
              )
              ;(command "point" 2-4point_3 )
              (setq 2-4point_4
                      (polar 
                        2-4point_3
                        (deg-to-rad (+ 180 2-4_groove_angle_90V))
                        0.2
                      )
              )
              ;(command "point" 2-4point_4 )
              (setq new_ssset_3(ssadd))
              (setq new_ssset_3 (ssadd 2-4_groove_angle_tri-C__ename_ new_ssset_3  )  )
              ; (command "pline" 2-4point_1 2-4point_2 2-4point_3 2-4point_4 "")    
              (command "pline" 2-4point_1 2-2point_2 2-2point_3 2-4point_4 "")
              (setq new_groove_ename (entlast))
              (setq new_ssset_3 (ssadd new_groove_ename new_ssset_3  )  )
              (command "breakatpoint" 2-4_groove_angle_tri-C__ename_ 2-4point_1)
              (setq new_groove_ex1 (entlast))
              (setq new_ssset_3 (ssadd new_groove_ex1 new_ssset_3  )  )
              (command "breakatpoint" 2-4_groove_angle_tri-C__ename_ 2-4point_4)
              (setq new_groove_ex2 (entlast))
              (vla-delete (vlax-ename->vla-object new_groove_ex2))
              
              
              (command "pedit" "m" new_ssset_3 "" "J" "" "")
            ;
            
            

          ;
          ; ;2-5process
          ;   (setq acp_main_1_as10_list_val (nth  acp_main_1_as10_i  acp_main_1_as10_list_))
          ;   (if 
          ;     (and
          ;       (= acp_main_1_as10_i 1)
          ;       (<=
          ;         (distance
          ;           (car (nth  acp_main_1_as10_i  acp_main_1_as10_list_))
          ;           (car (nth  (-  acp_main_1_as10_i 1)  acp_main_1_as10_list_))
          ;         )
          ;         20
          ;       )
          ;     )
          ;     (progn
          ;       (setq 2-5_groove_angle_tri-C__as10_list_val (nth  (-  acp_main_1_as10_i 1)   2-5_groove_angle_tri-C__as10_list_))
          ;     )
          ;   )
          ;   (if 
          ;     (and
          ;       (/= acp_main_1_as10_i 1)
          ;       (/= acp_main_1_as10_i (- (length acp_main_1_as10_list_ ) 2 ) )
          ;       (>
          ;         (distance
          ;           (car (nth  acp_main_1_as10_i  acp_main_1_as10_list_))
          ;           (car (nth  (-  acp_main_1_as10_i 1)  acp_main_1_as10_list_))
          ;         )
          ;         20
          ;       )
          ;     )
          ;     (progn
          ;       (setq 2-5_groove_angle_tri-C__as10_list_val (nth  acp_main_1_as10_i  2-5_groove_angle_tri-C__as10_list_))
          ;     )                
          ;   )
          ;   (if 
          ;     (and
          ;       (= acp_main_1_as10_i (- (length acp_main_1_as10_list_ ) 2 ) )
          ;       (>
          ;         (distance
          ;           (car (nth  acp_main_1_as10_i  acp_main_1_as10_list_))
          ;           (car (nth  (-  acp_main_1_as10_i 1)  acp_main_1_as10_list_))
          ;         )
          ;         20
          ;       )
          ;     )
          ;     (progn
          ;       (setq 2-5_groove_angle_tri-C__as10_list_val (nth  (-  acp_main_1_as10_i 1)   2-5_groove_angle_tri-C__as10_list_))
          ;     )                
          ;   )
          ;   (setq 2-5_groove_angle_90V (rad-to-deg (angle (car 2-5_groove_angle_tri-C__as10_list_val) (car acp_main_1_as10_list_val))))
          ;   (setq 2-5_groove_angle_90H (- 2-5_groove_angle_90V  90))
          ;   (setq 2-5_groove_angle_tri-A_ (- 2-5_groove_angle_90H (cadr 2-5_groove_angle_tri-C__as10_list_val)))
          ;   (setq 2-5_groove_angle_tri-B_ 90)
          ;   (setq 2-5_groove_angle_tri-C_ (- 2-5_groove_angle_tri-B_ 2-5_groove_angle_tri-A_ ))
          ;   ;TRIGONMETRY-PROCESS
          ;     (setq 2-5point_1 
          ;             (polar 
          ;               (polar (car 2-5_groove_angle_tri-C__as10_list_val) (deg-to-rad 2-5_groove_angle_90H) 0.1 )
          ;               (deg-to-rad (+ 2-5_groove_angle_90V 180))
          ;               (/ (* 0.10000 (sin (deg-to-rad 2-5_groove_angle_tri-A_))) (sin (deg-to-rad 2-5_groove_angle_tri-C_)) )
          ;             )
          ;     )
          ;     ;(command "point" 2-5point_1 )    
          ;     (setq 2-5point_2
          ;             (polar 
          ;               2-5point_1
          ;                 (deg-to-rad 2-5_groove_angle_90V)
          ;                 0.2
          ;             )
          ;     )
          ;     ;(command "point" 2-5point_2 )
          ;     (setq 2-5point_3
          ;             (polar 
          ;               2-5point_2
          ;               (deg-to-rad (+ 90 2-5_groove_angle_90V))
          ;               0.2
          ;             )
          ;     )
          ;     ;(command "point" 2-5point_3 )
          ;     (setq 2-5point_4
          ;             (polar 
          ;               2-5point_3
          ;               (deg-to-rad (+ 180 2-5_groove_angle_90V))
          ;               0.2
          ;             )
          ;     )
          ;     ;(command "point" 2-5point_4 )
          ;   ;
          ;   ;create process
          ;     (setq new_ssset_3 (ssadd))
          ;     (setq new_ssset_3 (ssadd 2-5_groove_angle_tri-C__ename_ new_ssset_3  )  )
          ;     ; (command "pline" 2-5point_1 2-5point_2 2-5point_3 2-5point_4 "") 
          ;     (cond
          ;       (;start
          ;         (and
          ;           (=  (- acp_main_1_as10_i 1) 0)
                    
          ;         )
          ;         (progn
          ;           (command "pline" 2-5point_1 2-4point_1 2-2point_2 2-2point_3 2-4point_4  "")
          ;         )
                  
          ;       )      
          ;       (;end
          ;         (and
          ;           (= acp_main_1_as10_i (- (length acp_main_1_as10_list_ ) 2 ) )
                    
          ;         )
          ;         (progn
          ;           (command "pline" 2-4point_1 2-2point_2 2-2point_3 2-4point_4 2-5point_4 "")
          ;         )
                  
          ;       )      
          ;       (;middle
          ;         (and
          ;           (/= acp_main_1_as10_i (- (length acp_main_1_as10_list_ ) 2 ) )
          ;           (/=  (- acp_main_1_as10_i 1) 0)
          ;         )
          ;         (progn
          ;           (command "pline" 2-5point_1 2-4point_1 2-2point_2 2-2point_3 2-4point_4 2-5point_4 "")
          ;         )
          ;       )      
          ;     )
              
          ;     (setq new_groove_ename (entlast))
              
          ;     (setq new_ssset_3 (ssadd new_groove_ename new_ssset_3  )  )
          ;     (cond
          ;       (;first_wave_case_1
          ;         (and
          ;             (= 0 (- acp_main_1_as10_i 1))
                      
          ;         )
          ;         (progn
          ;             (command "breakatpoint" 2-5_groove_angle_tri-C__ename_ 2-5point_1)
          ;             (setq new_groove_ex1 (entlast))
                      
          ;             (setq new_ssset_3 (ssadd new_groove_ex1 new_ssset_3  )  )
          ;             (vla-delete 2-5_groove_angle_tri-C__obj_)
          ;             (command "pedit" "m" new_ssset_3 "" "J" "" "")
          ;             (setq new_man_ (entlast))
                    
                      
          ;             (princ "first_wave_case_1")
          ;         )
          ;       )
          ;       (;first_wave_case_2
          ;         (and
          ;             (/= 0 (- acp_main_1_as10_i 1))
          ;             (/= acp_main_1_as10_i (- (length acp_main_1_as10_list_ ) 2 ) )
          ;         )
          ;         (progn
                      
          ;             (command "breakatpoint" new_man_ 2-5point_1)
                      
          ;             (setq new_groove_ex1 (entlast))
          ;             (command "breakatpoint" new_groove_ex1 2-5point_4)
          ;             (setq new_groove_ex2 (entlast))
                    
          ;             (setq new_ssset_3 (ssadd new_man_ new_ssset_3  )  )
          ;             (setq new_ssset_3 (ssadd new_groove_ex2 new_ssset_3  )  )
              

          ;             (vla-delete (vlax-ename->vla-object new_groove_ex1))
                      
                      
          ;             (command "pedit" "m" new_ssset_3 "" "J" "" "")
          ;             (setq new_man_ (entlast))
          ;             (princ "first_wave_case_2")
          ;         )
          ;       )
          ;       (;first_wave_case_3
          ;         (and
          ;           (= acp_main_1_as10_i (- (length acp_main_1_as10_list_ ) 2 ) )
          ;           (<=
          ;             (distance 
          ;               (car (nth acp_main_1_as10_i acp_main_1_as10_list_))
          ;               (car (nth (- (length acp_main_1_as10_list_ ) 1 ) acp_main_1_as10_list_))
          ;             )
          ;             20
          ;           )
          ;         )
          ;         (progn
          ;           (setq newline_ename_ (entlast))
          ;           (setq newline_obj_ (vlax-ename->vla-object newline_ename_))
          ;           (setq new_man_obj_ (vlax-ename->vla-object new_man_))
          ;           (command "pselect"  new_man_ "" )
          ;           (command "extend" new_man_  "" newline_ename_ "")
          ;           (command "breakatpoint" new_man_ (car (LM:intersections+0 newline_obj_ new_man_obj_ acextendnone )) )
          ;           (vla-delete (vlax-ename->vla-object new_man_))
          ;           (setq new_cut (entlast))
          ;           (setq new_ssset_4 (ssadd))
          ;           (setq new_ssset_4 (ssadd new_cut new_ssset_4 ))
          ;           (setq new_ssset_4 (ssadd newline_ename_ new_ssset_4 ))
          ;           (command "pedit" "m" new_ssset_4 "" "J" "" "")
                    
                    
                    
                    
                    
          ;         )
          ;       )
          ;       (;first_wave_case_4
          ;         (and
          ;           (= acp_main_1_as10_i (- (length acp_main_1_as10_list_ ) 2 ) )
          ;           (> 
          ;             (distance 
          ;               (car (nth acp_main_1_as10_i acp_main_1_as10_list_))
          ;               (car (nth (- (length acp_main_1_as10_list_ ) 1 ) acp_main_1_as10_list_))
          ;             )
          ;             20
          ;           )
          ;         )
          ;         (progn
          ;           (setq newline_ename_ (entlast))
          ;           (setq newline_obj_ (vlax-ename->vla-object newline_ename_))
          ;           (setq new_man_obj_ (vlax-ename->vla-object new_man_))
          ;           (command "pselect"  new_man_ "" )
          ;           (command "breakatpoint" new_man_ (car (LM:intersections+0 newline_obj_ new_man_obj_ acextendnone )) )
          ;           (command "extend" new_man_  "" newline_ename_ "")
                    
          ;           (vla-delete (vlax-ename->vla-object new_man_))
          ;           (setq new_cut (entlast))
          ;           (setq new_ssset_4 (ssadd))
          ;           (setq new_ssset_4 (ssadd new_cut new_ssset_4 ))
          ;           (setq new_ssset_4 (ssadd newline_ename_ new_ssset_4 ))
          ;           (command "pedit" "m" new_ssset_4 "" "J" "" "")
                    
                    
                    
                    
                    
          ;         )
          ;       )
          ;     )
          ;   ;
          ; ;
          (setq acp_main_1_as10_i (+ acp_main_1_as10_i 1))
        
      )
    ;

    (setvar "osmode" 1215)
  )
  (defun c:wash ()
  ;selection_set_for_fillter_blk_name
    (if  ;pre_select_ssget_or_post_select_ssget
      (=
        (setq ss_pre_filter_set_xx_ (ssget "i"
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq acp_level_ ())
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (setq ss_pre_filter_set_xx_obj_area_ (vla-get-area ss_pre_filter_set_xx_obj_))
      
        (setq acp_level_ (cons  (list ss_pre_filter_set_xx_ename_ ss_pre_filter_set_xx_obj_area_ ) acp_level_ ) )
      
      (setq ss_pre_filter_set_xx_i (+ ss_pre_filter_set_xx_i 1))
    )
  ;
  ;TA:stanndard_lambda_sorting
    (setq acp_level_sorted_ (vl-sort acp_level_  ;bigest open indent list
                                              (function 
                                                (lambda (a b) 
                                                  (> (cadr a) (cadr b))
                                                )
                                              )
                          ) ;bigest close indent list
    )
  ;
  ;new copy acp plastic line
    (setq acp_plastic_ssset (ssadd))
      (setq acp_level_sorted_lv2_obj_ (vlax-ename->vla-object (car (nth 1 acp_level_sorted_))))
      (vla-copy acp_level_sorted_lv2_obj_)
    (setq acp_plastic_line_lv1 (entlast))
    (setq acp_plastic_ssset (ssadd  acp_plastic_line_lv1 acp_plastic_ssset))
      (setq acp_level_sorted_lv3_obj_ (vlax-ename->vla-object (car (nth 2 acp_level_sorted_))))
      (vla-copy acp_level_sorted_lv3_obj_)
    (setq acp_plastic_line_lv2 (entlast))
    (setq acp_plastic_ssset (ssadd  acp_plastic_line_lv2 acp_plastic_ssset))
    
  ;
  ;plastic_joint
    (setq acp_plastic_line_lv1_pt (cadr (TA:Get_Pline_vertext_ins_point_ acp_plastic_line_lv1 )))
    (setq acp_plastic_line_lv2_pt (cadr (TA:Get_Pline_vertext_ins_point_ acp_plastic_line_lv2 )))
    (command "pline" (car acp_plastic_line_lv1_pt)  (car acp_plastic_line_lv2_pt) "")
    (setq acp_plastic_ssset (ssadd  (entlast) acp_plastic_ssset))

    (setq acp_plastic_line_lv1_pt (reverse (cadr (TA:Get_Pline_vertext_ins_point_ acp_plastic_line_lv1 ))))
    (setq acp_plastic_line_lv2_pt (reverse (cadr (TA:Get_Pline_vertext_ins_point_ acp_plastic_line_lv2 ))))
    (command "pline" (car acp_plastic_line_lv1_pt)  (car acp_plastic_line_lv2_pt) "")
    (setq acp_plastic_ssset (ssadd  (entlast) acp_plastic_ssset))

    (command "_.pedit" "_m" acp_plastic_ssset "" "_j" "" "")
    (setq ename_for_hatch_ (entlast))
    (TA:CREATE_HATCH_ANSI37 ename_for_hatch_ 1 1)
    (vla-put-color (setq ename_for_hatch_obj_ (vlax-ename->vla-object ename_for_hatch_)) 1)
    (command "draworder" ename_for_hatch_ "" "F")
  ;

  ;front_sheet_process_
    (setq acp_front_sheet_ssset_ (ssadd))
    (setq acp_front_sheet_line_lv1_pt_Head (cadr (TA:Get_Pline_vertext_ins_point_ (car (nth 0 acp_level_sorted_ )) )))
    (setq acp_front_sheet_line_lv2_pt_Head (cadr (TA:Get_Pline_vertext_ins_point_ (car (nth 1 acp_level_sorted_ )) )))
    (command "pline"  (car acp_front_sheet_line_lv1_pt_Head ) (car acp_front_sheet_line_lv2_pt_Head) "")
    (setq acp_front_sheet_ssset_ (ssadd (entlast) acp_front_sheet_ssset_))

    
    (setq acp_front_sheet_line_lv1_pt_bot (reverse (cadr (TA:Get_Pline_vertext_ins_point_ (car (nth 0 acp_level_sorted_ )) ))))
    (setq acp_front_sheet_line_lv2_pt_bot (reverse (cadr (TA:Get_Pline_vertext_ins_point_ (car (nth 1 acp_level_sorted_ )) ))))
    (command "pline"  (car acp_front_sheet_line_lv1_pt_bot ) (car acp_front_sheet_line_lv2_pt_bot) "")
    (setq acp_front_sheet_ssset_ (ssadd (entlast) acp_front_sheet_ssset_))
    
    (setq acp_front_sheet_ssset_ (ssadd (car (nth 0 acp_level_sorted_ )) acp_front_sheet_ssset_))
    (setq acp_front_sheet_ssset_ (ssadd (car (nth 1 acp_level_sorted_ )) acp_front_sheet_ssset_))
    
    (command "_.pedit" "_m" acp_front_sheet_ssset_ "" "_j" "" "")
    (setq acp_front_sheet_for_hatch_ (entlast))
    (TA:CREATE_HATCH_ acp_front_sheet_for_hatch_ 1 1)
    (vla-put-color (setq acp_front_sheet_for_hatch_obj_ (vlax-ename->vla-object acp_front_sheet_for_hatch_)) 3)
    (command "draworder" acp_front_sheet_for_hatch_ "" "F")
  ;
  ;back_sheet_process_
    (setq acp_back_sheet_ssset_ (ssadd))
    (setq acp_back_sheet_line_lv3_pt_Head (cadr (TA:Get_Pline_vertext_ins_point_ (car (nth 2 acp_level_sorted_ )) )))
    (setq acp_back_sheet_line_lv4_pt_Head (cadr (TA:Get_Pline_vertext_ins_point_ (car (nth 3 acp_level_sorted_ )) )))
    (command "pline"  (car acp_back_sheet_line_lv3_pt_Head ) (car acp_back_sheet_line_lv4_pt_Head) "")
    (setq acp_back_sheet_ssset_ (ssadd (entlast) acp_back_sheet_ssset_))

    
    (setq acp_back_sheet_line_lv3_pt_bot (reverse (cadr (TA:Get_Pline_vertext_ins_point_ (car (nth 2 acp_level_sorted_ )) ))))
    (setq acp_back_sheet_line_lv4_pt_bot (reverse (cadr (TA:Get_Pline_vertext_ins_point_ (car (nth 3 acp_level_sorted_ )) ))))
    (command "pline"  (car acp_back_sheet_line_lv3_pt_bot ) (car acp_back_sheet_line_lv4_pt_bot) "")
    (setq acp_back_sheet_ssset_ (ssadd (entlast) acp_back_sheet_ssset_))
    
    (setq acp_back_sheet_ssset_ (ssadd (car (nth 2 acp_level_sorted_ )) acp_back_sheet_ssset_))
    (setq acp_back_sheet_ssset_ (ssadd (car (nth 3 acp_level_sorted_ )) acp_back_sheet_ssset_))
    
    (command "_.pedit" "_m" acp_back_sheet_ssset_ "" "_j" "" "")
    (setq acp_back_sheet_for_hatch_ (entlast))
    (TA:CREATE_HATCH_ acp_back_sheet_for_hatch_ 1 1)
    (vla-put-color (setq acp_back_sheet_for_hatch_obj_ (vlax-ename->vla-object acp_back_sheet_for_hatch_)) 3)
    (command "draworder" acp_back_sheet_for_hatch_ "" "F")
  ;
  )

;




(defun c:unisc_ ()
  (setq uni_ename_ (car (entsel )))
  (setq uni_obj_ (vlax-ename->vla-object uni_ename_))
  (setq user_input_name_block (LM:effectivename uni_obj_))
  (TA:set-block-blockscaling user_input_name_block acUniform) 
)

(defun c:Matchangle_Mang_ ()
  ;selection_set_for_fillter_blk_name
    (if  ;pre_select_ssget_or_post_select_ssget
      (=
        (setq ss_pre_filter_set_xx_ (ssget "i"
                                          (list
                                            (cons 0 "insert") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "insert") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;user_input_
    (setq mathc_angle_ (car (entsel "specify angle Object")))
    (setq mathc_angle_obj_ (vlax-ename->vla-object mathc_angle_))
    (setq match_angle_obj_val (rad-to-deg (vla-get-angle mathc_angle_obj_)))
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (vla-put-rotation ss_pre_filter_set_xx_hon_obj_ (deg-to-rad match_angle_obj_val)   ) 
      (setq ss_pre_filter_set_xx_i (+ ss_pre_filter_set_xx_i 1))
    )
  ;
)







(defun c:TEMP_stamp_on_intersec_CT05_ ()
  (setvar "osmode" 0)
  ;selection_set_for_fillter_blk_name
    (if  ;pre_select_ssget_or_post_select_ssget
      (=
        (setq ss_pre_filter_set_xx_ (ssget "i"
                                          (list
                                            (cons 0 "line,lwpolyline,xline") ;type of object
                                            ; (cons 8 "000 - GRID")   ;kind of layer
                                            ; (cons 2 "000-GRID_LINE_DYN")       ;kind of nameblock
                                            (cons 62 1)           ;kind of color call sign with color code index
                                          )
                                    )
        )
        nil
      )
      (progn
        (setq ss_pre_filter_set_xx_ (ssget 
                                          (list
                                            (cons 0 "line,lwpolyline,xline") ;type of object
                                            ; (cons 8 "000 - GRID")   ;kind of layer
                                            ; (cons 2 "000-GRID_LINE_DYN")       ;kind of nameblock
                                            (cons 62 1)           ;kind of color call sign with color code index
                                          )
                                    )
        )
      )
      (sslength ss_pre_filter_set_xx_)
    )
  ;
  ;user_input_
    ;while_select_block_on_condition_
        (setq main_intersec_pline_ename_ nil)
        (while (= main_intersec_pline_ename_ nil)
          (setq main_intersec_pline_ename_ (car (entsel "specify main_intersec_pline_ename Object")))
          (if
            (and ;conditional_rule_for_select_object
              (/= main_intersec_pline_ename_ nil)
              (setq main_intersec_pline_ename_obj_ (vlax-ename->vla-object main_intersec_pline_ename_))
              (= (vla-get-objectname main_intersec_pline_ename_obj_ ) "AcDbPolyline")
              ; (= (vla-get-isdynamicblock main_intersec_pline_ename_obj_ ) :vlax-true)
              ; (/= (LM:getdynpropallowedvalues main_intersec_pline_ename_obj_ "view") nil)
            )
            (progn
              (setq main_intersec_pline_obj_ (vlax-ename->vla-object main_intersec_pline_ename_))
            )
            (setq main_intersec_pline_ename_ nil)
          )
        )
    ;
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (setq insertion_point_val_ (car (LM:intersections+0 ss_pre_filter_set_xx_hon_obj_ main_intersec_pline_obj_  acextendnone)))
      
      (command "insert" "xsa1" insertion_point_val_ 0.5 0)
  
      (setq ss_pre_filter_set_xx_i (+ ss_pre_filter_set_xx_i 1))
    )
  ;)
  (setvar "osmode" 1215)
)
(defun c:TEMP_stamp_on_intersec_CT1_ ()
  (setvar "osmode" 0)
  ;user_input_
    (initget "Yes No")
    (setq ss_ ;Detect the variable's result in case of a function error
      (vl-catch-all-apply 
        (function 
          (lambda () 
            (setq DELETE_OBJ_ (not (eq "No" (getkword "\nKeep Existing point with object? [Yes/No] <Y>: "))))
          )
        )
      )
    )
    (if (or (= ss_ nil) (= (vl-prin1-to-string ss_) "#<%catch-all-apply-error%>")  )
      (progn
        ;selection_set_for_fillter_blk_name
          (if  ;pre_select_ssget_or_post_select_ssget
            (=
              (setq ss_pre_filter_set_xx_ (ssget "i"
                                                (list
                                                  (cons 0 "line") ;type of object
                                                  ; (cons 8 "000 - GRID")   ;kind of layer
                                                  ; (cons 2 "000-GRID_LINE_DYN")       ;kind of nameblock
                                                  ; (cons 62 0)           ;kind of color call sign with color code index
                                                )
                                          )
              )
              nil
            )
            (progn
              (setq ss_pre_filter_set_xx_ (ssget 
                                                (list
                                                  (cons 0 "line") ;type of object
                                                  ; (cons 8 "000 - GRID")   ;kind of layer
                                                  ; (cons 2 "000-GRID_LINE_DYN")       ;kind of nameblock
                                                  ; (cons 62 0)           ;kind of color call sign with color code index
                                                )
                                          )
              )
            )
            (sslength ss_pre_filter_set_xx_)
          )
        ;
      )
      (setq ss_pre_filter_set_xx_ ss_pre_filter_set_xx_)
    )
  ;
 
  ;user_input_
    ;while_select_block_on_condition_
        (setq main_intersec_pline_ename_ nil)
        (while (= main_intersec_pline_ename_ nil)
          (setq main_intersec_pline_ename_ (car (entsel "specify main_intersec_pline_ename Object")))
          (if
            (and ;conditional_rule_for_select_object
              (/= main_intersec_pline_ename_ nil)
              (setq main_intersec_pline_ename_obj_ (vlax-ename->vla-object main_intersec_pline_ename_))
              (= (vla-get-objectname main_intersec_pline_ename_obj_ ) "AcDbPolyline")
              ; (= (vla-get-isdynamicblock main_intersec_pline_ename_obj_ ) :vlax-true)
              ; (/= (LM:getdynpropallowedvalues main_intersec_pline_ename_obj_ "view") nil)
            )
            (progn
              (setq main_intersec_pline_obj_ (vlax-ename->vla-object main_intersec_pline_ename_))
              
              
              
            )
            (setq main_intersec_pline_ename_ nil)
          )
        )
    ;
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (setq ss_pre_filter_set_xx_hon_obj_angle (rad-to-deg (vla-get-angle ss_pre_filter_set_xx_hon_obj_)))
      (setq insertion_point_val_ (car (LM:intersections+0 ss_pre_filter_set_xx_hon_obj_ main_intersec_pline_obj_  acextendnone)))
      
      (if ;lv1
        (and 
          (= 3 (vla-get-color ss_pre_filter_set_xx_hon_obj_))
          (= 1 (vla-get-color main_intersec_pline_obj_))
        )
        (progn
          (command "insert" "xsa1" insertion_point_val_ 1 ss_pre_filter_set_xx_hon_obj_angle)
        )
      )
      (if ;lv2
        (and 
          (= 1 (vla-get-color ss_pre_filter_set_xx_hon_obj_))
          (= 2 (vla-get-color main_intersec_pline_obj_))
        )
        (progn
          (command "insert" "xsa1" insertion_point_val_ 0.75 ss_pre_filter_set_xx_hon_obj_angle)
        )
      )
      (if ;lv2-1
        (and 
          (= 4 (vla-get-color ss_pre_filter_set_xx_hon_obj_))
          (= 2 (vla-get-color main_intersec_pline_obj_))
        )
        (progn
          (command "insert" "xsa1" insertion_point_val_ 1 ss_pre_filter_set_xx_hon_obj_angle)
        )
      )
      (if ;lv3
        (and 
          (= 3 (vla-get-color ss_pre_filter_set_xx_hon_obj_))
          (= 4 (vla-get-color main_intersec_pline_obj_))
        )
        (progn
          (command "insert" "xsa1" insertion_point_val_ 0.50 ss_pre_filter_set_xx_hon_obj_angle)
        )
      )
      (if ;lv4
        (and 
          (= 1 (vla-get-color ss_pre_filter_set_xx_hon_obj_))
          (= 5 (vla-get-color main_intersec_pline_obj_))
        )
        (progn
          (command "insert" "xsa1" insertion_point_val_ 0.50 ss_pre_filter_set_xx_hon_obj_angle)
        )
      )
      (if ;lv4-1
        (and 
          (= 4 (vla-get-color ss_pre_filter_set_xx_hon_obj_))
          (= 5 (vla-get-color main_intersec_pline_obj_))
        )
        (progn
          (command "insert" "xsa1" insertion_point_val_ 0.50 ss_pre_filter_set_xx_hon_obj_angle)
        )
      )
      (if 
        (and 
          (= 3 (vla-get-color ss_pre_filter_set_xx_hon_obj_))
          (= 6 (vla-get-color main_intersec_pline_obj_))
        )
        (progn
          (command "insert" "xsa1" insertion_point_val_ 0.50 ss_pre_filter_set_xx_hon_obj_angle)
        )
      )
      
  
      (setq ss_pre_filter_set_xx_i (+ ss_pre_filter_set_xx_i 1))
    )
  ;)
  (setvar "osmode" 1215)
)    
(defun c:TEMP_stamp_on_intersec_CT3_ ()
  (setvar "osmode" 0)
  ;user_input_
    (initget "Yes No")
    (setq ss_ ;Detect the variable's result in case of a function error
      (vl-catch-all-apply 
        (function 
          (lambda () 
            (setq DELETE_OBJ_ (not (eq "No" (getkword "\nKeep Existing point with object? [Yes/No] <Y>: "))))
          )
        )
      )
    )
    (if (or (= ss_ nil) (= (vl-prin1-to-string ss_) "#<%catch-all-apply-error%>")  )
      (progn
        ;selection_set_for_fillter_blk_name
          (if  ;pre_select_ssget_or_post_select_ssget
            (=
              (setq ss_pre_filter_set_xx_ (ssget "i"
                                                (list
                                                  (cons 0 "line") ;type of object
                                                  ; (cons 8 "000 - GRID")   ;kind of layer
                                                  ; (cons 2 "000-GRID_LINE_DYN")       ;kind of nameblock
                                                  ; (cons 62 0)           ;kind of color call sign with color code index
                                                )
                                          )
              )
              nil
            )
            (progn
              (setq ss_pre_filter_set_xx_ (ssget 
                                                (list
                                                  (cons 0 "line") ;type of object
                                                  ; (cons 8 "000 - GRID")   ;kind of layer
                                                  ; (cons 2 "000-GRID_LINE_DYN")       ;kind of nameblock
                                                  ; (cons 62 0)           ;kind of color call sign with color code index
                                                )
                                          )
              )
            )
            (sslength ss_pre_filter_set_xx_)
          )
        ;
      )
      (setq ss_pre_filter_set_xx_ ss_pre_filter_set_xx_)
    )
  ;
 
  ;user_input_
    ;while_select_block_on_condition_
        (setq main_intersec_pline_ename_ nil)
        (while (= main_intersec_pline_ename_ nil)
          (setq main_intersec_pline_ename_ (car (entsel "specify main_intersec_pline_ename Object")))
          (if
            (and ;conditional_rule_for_select_object
              (/= main_intersec_pline_ename_ nil)
              (setq main_intersec_pline_ename_obj_ (vlax-ename->vla-object main_intersec_pline_ename_))
              (= (vla-get-objectname main_intersec_pline_ename_obj_ ) "AcDbPolyline")
              ; (= (vla-get-isdynamicblock main_intersec_pline_ename_obj_ ) :vlax-true)
              ; (/= (LM:getdynpropallowedvalues main_intersec_pline_ename_obj_ "view") nil)
            )
            (progn
              (setq main_intersec_pline_obj_ (vlax-ename->vla-object main_intersec_pline_ename_))
              
              
              
            )
            (setq main_intersec_pline_ename_ nil)
          )
        )
    ;
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (setq ss_pre_filter_set_xx_hon_obj_angle (rad-to-deg (vla-get-angle ss_pre_filter_set_xx_hon_obj_)))
      (setq insertion_point_val_ (car (LM:intersections+0 ss_pre_filter_set_xx_hon_obj_ main_intersec_pline_obj_  acextendnone)))
      
      (cond
        ( ;lv1
          (and 
            (= 3 (vla-get-color ss_pre_filter_set_xx_hon_obj_))
            (= 1 (vla-get-color main_intersec_pline_obj_))
          )
          (progn
            (command "insert" "xsa1" insertion_point_val_ 1 ss_pre_filter_set_xx_hon_obj_angle)
          )
        )
        ( ;lv2
          (and 
            (= 1 (vla-get-color ss_pre_filter_set_xx_hon_obj_))
            (= 2 (vla-get-color main_intersec_pline_obj_))
          )
          (progn
            (command "insert" "xsa1" insertion_point_val_ 1 ss_pre_filter_set_xx_hon_obj_angle)
          )
        )
      )
      
  
      (setq ss_pre_filter_set_xx_i (+ ss_pre_filter_set_xx_i 1))
      (setq ss_pre_filter_set_xx_i (- ss_pre_filter_set_xx_i 1))
    )
  ;)
  (setvar "osmode" 1215)
)    
(defun c:TMEP_line_sorting_CT2 ()
  ;selection_set_for_fillter_blk_name
    (if  ;pre_select_ssget_or_post_select_ssget
      (=
        (setq ss_pre_filter_set_xx_ (ssget "i"
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq line_list_ ())
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (setq ss_pre_filter_set_xx_hon_obj_start_end_pt_ (list
                                      (setq ss_pre_filter_set_xx_hon_obj_startpt_ (vlax-safearray->list
                                                                 (vlax-variant-value ( vla-get-startpoint ss_pre_filter_set_xx_hon_obj_ ))
                                                               )
                                      )
                                      (setq ss_pre_filter_set_xx_hon_obj_endpt_ (vlax-safearray->list
                                                                (vlax-variant-value ( vla-get-endpoint ss_pre_filter_set_xx_hon_obj_ ))
                                                             )
                                      )
                                    )
      )
      (setq sumlist_ (list ss_pre_filter_set_xx_hon_obj_startpt_ ss_pre_filter_set_xx_ename_ ))
      (setq line_list_ (cons sumlist_  line_list_ ))
      
      
      
      (setq ss_pre_filter_set_xx_i (+ ss_pre_filter_set_xx_i 1))
    )
  ;
  ;TA:stanndard_lambda_sorting
    (setq line_list_sorted_ (vl-sort line_list_  ;bigest open indent list
                                    (function 
                                      (lambda (a b) 
                                        (< (nth 0 (car a)) (nth 0 (car b)))
                                      )
                                    )
                            ) ;bigest close indent list
    )
  ;
  ;preloop_and_while
    (setq line_list_sorted_i 0)
    (setq line_list_sorted_i-color_ 1)
    (while (< line_list_sorted_i (length line_list_sorted_))
      (setq line_list_sorted_ename_ (cadr (nth  line_list_sorted_i line_list_sorted_)))
      (setq line_list_sorted_obj_ (vlax-ename->vla-object line_list_sorted_ename_))
      
      (cond
        (;_case_1
           (and
              (= line_list_sorted_i-color_ 1)
           )
           (progn
             (vla-put-color line_list_sorted_obj_ 1)
             (princ "_case_1")
           )
        )
        (;_case_2
           (and
              (= line_list_sorted_i-color_ 2)
           )
           (progn
             (vla-put-color line_list_sorted_obj_ 3)
             (princ "_case_2")
           )
        )
        (;_case_3
           (and
              (= line_list_sorted_i-color_ 3)
           )
           (progn
             (vla-put-color line_list_sorted_obj_ 4)
             (princ "_case_3")
           )
        )
        (;_case_4
           (and
              (= line_list_sorted_i-color_ 4)
           )
           (progn
             (vla-put-color line_list_sorted_obj_ 3)
             (princ "_case_4")
           )
        )
        (;_case_5
           (and
              (= line_list_sorted_i-color_ 5)
           )
           (progn
             (vla-put-color line_list_sorted_obj_ 1)
             (setq line_list_sorted_i-color_ 1)
             (princ "_case_5")
           )
        )

      )
      
      
      (setq line_list_sorted_i-color_ (+ line_list_sorted_i-color_ 1))
      (setq line_list_sorted_i (+ line_list_sorted_i 1))
    )
  ;
  
)
(defun c:TMEP_line_sorting_CT4 ()
  ;selection_set_for_fillter_blk_name
    (if  ;pre_select_ssget_or_post_select_ssget
      (=
        (setq ss_pre_filter_set_xx_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq line_list_ ())
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (setq obj_type_ (vla-get-objectname ss_pre_filter_set_xx_hon_obj_))
      (cond
        (;obj_type_case_1
           (and
              (= obj_type_ "AcDbPolyline" )

           )
           (progn
             (setq sumlist_ (list   
                              (list 
                                (car (vlax-safearray->list (vlax-variant-value (vla-get-coordinates ss_pre_filter_set_xx_hon_obj_ ))))
                                (cadr (vlax-safearray->list (vlax-variant-value (vla-get-coordinates ss_pre_filter_set_xx_hon_obj_ ))))
                                0
                              )
                              ss_pre_filter_set_xx_ename_
                            )
             )
             (setq line_list_ (cons sumlist_  line_list_ ))
             (princ "obj_type_case_1")
           )
        )
        (;obj_type_case_2
           (and
              (= obj_type_ "AcDbLine" )

           )
           (progn
             (setq ss_pre_filter_set_xx_hon_obj_start_end_pt_ (list
                                      (setq ss_pre_filter_set_xx_hon_obj_startpt_ (vlax-safearray->list
                                                                 (vlax-variant-value ( vla-get-startpoint ss_pre_filter_set_xx_hon_obj_ ))
                                                               )
                                      )
                                      (setq ss_pre_filter_set_xx_hon_obj_endpt_ (vlax-safearray->list
                                                                (vlax-variant-value ( vla-get-endpoint ss_pre_filter_set_xx_hon_obj_ ))
                                                             )
                                      )
                                    )
              )
              (setq sumlist_ (list ss_pre_filter_set_xx_hon_obj_startpt_ ss_pre_filter_set_xx_ename_ ))
              (setq line_list_ (cons sumlist_  line_list_ ))
             (princ "obj_type_case_2")
           )
        )
      )
      
      (setq ss_pre_filter_set_xx_i (+ ss_pre_filter_set_xx_i 1))
    )
  ;
  ;TA:stanndard_lambda_sorting
    (setq line_list_sorted_ (vl-sort line_list_  ;bigest open indent list
                                    (function 
                                      (lambda (a b) 
                                        (< (nth 0 (car a)) (nth 0 (car b)))
                                      )
                                    )
                            ) ;bigest close indent list
    )
  ;
  ;preloop_and_while
    (setq line_list_sorted_i 0)
    (setq line_list_sorted_i-color_ 1)
    (while (< line_list_sorted_i (length line_list_sorted_))
      (setq line_list_sorted_ename_ (cadr (nth  line_list_sorted_i line_list_sorted_)))
      (setq line_list_sorted_obj_ (vlax-ename->vla-object line_list_sorted_ename_))
      
      (cond
        (;_case_1
           (and
              (= line_list_sorted_i-color_ 1)
           )
           (progn
             (vla-put-color line_list_sorted_obj_ 1)
             (princ "_case_1")
           )
        )
        (;_case_2
           (and
              (= line_list_sorted_i-color_ 2)
           )
           (progn
             (vla-put-color line_list_sorted_obj_ 2)
             (setq line_list_sorted_i-color_ 0)
             (princ "_case_2")
           )
        )
        ; (;_case_3
        ;    (and
        ;       (= line_list_sorted_i-color_ 3)
        ;    )
        ;    (progn
        ;      (vla-put-color line_list_sorted_obj_ 4)
        ;      (princ "_case_3")
        ;    )
        ; )
        ; (;_case_4
        ;    (and
        ;       (= line_list_sorted_i-color_ 4)
        ;    )
        ;    (progn
        ;      (vla-put-color line_list_sorted_obj_ 3)
        ;      (princ "_case_4")
        ;    )
        ; )
        ; (;_case_5
        ;    (and
        ;       (= line_list_sorted_i-color_ 5)
        ;    )
        ;    (progn
        ;      (vla-put-color line_list_sorted_obj_ 1)
        ;      (setq line_list_sorted_i-color_ 1)
        ;      (princ "_case_5")
        ;    )
        ; )

      )
      
      
      (setq line_list_sorted_i-color_ (+ line_list_sorted_i-color_ 1))
      (setq line_list_sorted_i (+ line_list_sorted_i 1))
    )
  ;
  
)
(defun c:TMEP_line_sorting_CT5 ()
  ;user_input_
    (setq input_sc_ (cond ( (getint (strcat "\nspecify get block scale \n<" (rtos (setq input_sc_ (cond (input_sc_) (1.0) ) ) ) "> : " ) ) ) (input_sc_) ) )
  ;
  ;selection_set_for_fillter_blk_name
    (if  ;pre_select_ssget_or_post_select_ssget
      (=
        (setq ss_pre_filter_set_xx_hon_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_hon_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_hon_)
    )
  ;
  ;preloop_and_while
    (setq ss_pre_filter_set_xx_hon_i 0)
    (setq line_list_hon ())
    (while (< ss_pre_filter_set_xx_hon_i (sslength ss_pre_filter_set_xx_hon_))
      (setq ss_pre_filter_set_xx_hon_ename_ (ssname ss_pre_filter_set_xx_hon_ ss_pre_filter_set_xx_hon_i))
      (setq ss_pre_filter_set_xx_hon_obj_ (vlax-ename->vla-object ss_pre_filter_set_xx_hon_ename_))
      (setq obj_type_ (vla-get-objectname (vlax-ename->vla-object ss_pre_filter_set_xx_hon_ename_)))
      (cond
        (;obj_type_case_1
           (and
              (= obj_type_ "AcDbPolyline" )

           )
           (progn
             (setq sumlist_ (list   
                              (list 
                                (car (vlax-safearray->list (vlax-variant-value (vla-get-coordinates ss_pre_filter_set_xx_hon_obj_ ))))
                                (cadr (vlax-safearray->list (vlax-variant-value (vla-get-coordinates ss_pre_filter_set_xx_hon_obj_ ))))
                                0
                              )
                              ss_pre_filter_set_xx_hon_ename_
                            )
             )
             (setq line_list_hon (cons sumlist_  line_list_hon ))
             (princ "obj_type_case_1")
           )
        )
        (;obj_type_case_2
           (and
              (= obj_type_ "AcDbLine" )

           )
           (progn
             (setq ss_pre_filter_set_xx_hon_obj_start_end_pt_ (list
                                      (setq ss_pre_filter_set_xx_hon_obj_startpt_ (vlax-safearray->list
                                                                 (vlax-variant-value ( vla-get-startpoint ss_pre_filter_set_xx_hon_obj_ ))
                                                               )
                                      )
                                      (setq ss_pre_filter_set_xx_hon_obj_endpt_ (vlax-safearray->list
                                                                (vlax-variant-value ( vla-get-endpoint ss_pre_filter_set_xx_hon_obj_ ))
                                                             )
                                      )
                                    )
              )
              (setq sumlist_ (list ss_pre_filter_set_xx_hon_obj_startpt_ ss_pre_filter_set_xx_hon_ename_ ))
              (setq line_list_hon (cons sumlist_  line_list_hon ))
             (princ "obj_type_case_2")
           )
        )
      )
      
      
      
      (setq ss_pre_filter_set_xx_hon_i (+ ss_pre_filter_set_xx_hon_i 1))
    )
  ;
  ;TA:stanndard_lambda_sorting
    (setq line_list_sorted_hon_ (vl-sort line_list_hon  ;bigest open indent list
                                    (function 
                                      (lambda (a b) 
                                        (< (nth 0 (car a)) (nth 0 (car b)))
                                      )
                                    )
                            ) ;bigest close indent list
    )
  ;

  ;selection_set_for_fillter_blk_name
    (if  ;pre_select_ssget_or_post_select_ssget
      (=
        (setq ss_pre_filter_set_xx_ver_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ver_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_ver_)
    )
  ;
  ;preloop_and_while
    (setq ss_pre_filter_set_xx_ver_i 0)
    (setq line_list_ver ())
    (while (< ss_pre_filter_set_xx_ver_i (sslength ss_pre_filter_set_xx_ver_))
      (setq ss_pre_filter_set_xx_ver_ename_ (ssname ss_pre_filter_set_xx_ver_ ss_pre_filter_set_xx_ver_i))
      (setq ss_pre_filter_set_xx_ver_obj_ (vlax-ename->vla-object ss_pre_filter_set_xx_ver_ename_))
      (setq obj_type_ (vla-get-objectname (vlax-ename->vla-object ss_pre_filter_set_xx_ver_ename_)))
      (cond
        (;obj_type_case_1
           (and
              (= obj_type_ "AcDbPolyline" )

           )
           (progn
             (setq sumlist_ (list   
                              (list 
                                (car (vlax-safearray->list (vlax-variant-value (vla-get-coordinates ss_pre_filter_set_xx_ver_obj_ ))))
                                (cadr (vlax-safearray->list (vlax-variant-value (vla-get-coordinates ss_pre_filter_set_xx_ver_obj_ ))))
                                0
                              )
                              ss_pre_filter_set_xx_ver_ename_
                            )
             )
             (setq line_list_ver (cons sumlist_  line_list_ver ))
             (princ "obj_type_case_1")
           )
        )
        (;obj_type_case_2
           (and
              (= obj_type_ "AcDbLine" )

           )
           (progn
             (setq ss_pre_filter_set_xx_ver_obj_start_end_pt_ (list
                                      (setq ss_pre_filter_set_xx_ver_obj_startpt_ (vlax-safearray->list
                                                                 (vlax-variant-value ( vla-get-startpoint ss_pre_filter_set_xx_ver_obj_ ))
                                                               )
                                      )
                                      (setq ss_pre_filter_set_xx_ver_obj_endpt_ (vlax-safearray->list
                                                                (vlax-variant-value ( vla-get-endpoint ss_pre_filter_set_xx_ver_obj_ ))
                                                             )
                                      )
                                    )
              )
              (setq sumlist_ (list ss_pre_filter_set_xx_ver_obj_startpt_ ss_pre_filter_set_xx_ver_ename_ ))
              (setq line_list_ver (cons sumlist_  line_list_ver ))
             (princ "obj_type_case_2")
           )
        )
      )
      
      
      
      (setq ss_pre_filter_set_xx_ver_i (+ ss_pre_filter_set_xx_ver_i 1))
    )
  ;
  ;TA:stanndard_lambda_sorting
    (setq line_list_sorted_ver_ (vl-sort line_list_ver  ;bigest open indent list
                                    (function 
                                      (lambda (a b) 
                                        (< (nth 1 (car a)) (nth 1 (car b)))
                                      )
                                    )
                            ) ;bigest close indent list
    )
  ;

  ;preloop_and_while
    (setq line_list_sorted_hon_i 0)
    (while (< line_list_sorted_hon_i (length line_list_sorted_hon_))
      (setq line_list_sorted_hon_ename_ (cadr (nth  line_list_sorted_hon_i line_list_sorted_hon_)))
      (setq line_list_sorted_hon_obj_ (vlax-ename->vla-object line_list_sorted_hon_ename_))
      (setq line_list_sorted_hon_obj_color_ (vla-get-color line_list_sorted_hon_obj_))
      
      
        ;preloop_and_while
          (setq line_list_sorted_ver_i 0)
          ; (setq blk_scale_i (* (length line_list_sorted_ver_) 0.20))
          
          (setq blk_scale_i input_sc_)
          (while (< line_list_sorted_ver_i (length line_list_sorted_ver_))
            (setq line_list_sorted_ver_ename_ (cadr (nth  line_list_sorted_ver_i line_list_sorted_ver_)))
            (setq line_list_sorted_ver_obj_ (vlax-ename->vla-object line_list_sorted_ver_ename_))
            (setq line_list_sorted_ver_obj_color_ (vla-get-color line_list_sorted_ver_obj_))
            
            
            
              (cond
                (;color_case_1
                   (and
                      (= line_list_sorted_hon_obj_color_ 1)
                      (= line_list_sorted_ver_obj_color_ 1)
                      
                   )
                   (progn
                     (setq insertion_point_val_ (car (LM:intersections+0 line_list_sorted_hon_obj_ line_list_sorted_ver_obj_  acextendnone)))
                     (command "insert" "xsa1" insertion_point_val_ blk_scale_i 90)
                     (princ "color_case_1")
                   )
                )
                (;color_case_2
                   (and
                      (= line_list_sorted_hon_obj_color_ 2)
                      (= line_list_sorted_ver_obj_color_ 2)
                      
                   )
                   (progn
                     (setq insertion_point_val_ (car (LM:intersections+0 line_list_sorted_hon_obj_ line_list_sorted_ver_obj_  acextendnone)))
                     (command "insert" "xsa1" insertion_point_val_ blk_scale_i 90)
                     (princ "color_case_2")
                   )
                )
              )
            
            (if (=  "0.2" (rtos blk_scale_i 2 1))
              (progn
                (princ "S")
              )
                (setq blk_scale_i (- blk_scale_i 0.2))
            )
            
            (setq line_list_sorted_ver_i (+ line_list_sorted_ver_i 1))
          )
        ;
      
      (setq line_list_sorted_hon_i (+ line_list_sorted_hon_i 1))
    )
  ;
)
(defun c:TMEP_line_sorting_CT6 ()
  ;user-input_name_block_
    (setq user_input_name_block "X10")
    (TA:set-block-blockscaling user_input_name_block acUniform)
  ;
  ;user_input_
    ; (setq input_sc_ (cond ( (getint (strcat "\nspecify get block scale \n<" (rtos (setq input_sc_ (cond (input_sc_) (1.0) ) ) ) "> : " ) ) ) (input_sc_) ) )
  ;
  ;selection_set_for_fillter_blk_name
    (if  ;pre_select_ssget_or_post_select_ssget
      (=
        (setq ss_pre_filter_set_xx_hon_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_hon_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_hon_)
    )
  ;
  ;preloop_and_while
    (setq ss_pre_filter_set_xx_hon_i 0)
    (setq line_list_hon ())
    (while (< ss_pre_filter_set_xx_hon_i (sslength ss_pre_filter_set_xx_hon_))
      (setq ss_pre_filter_set_xx_hon_ename_ (ssname ss_pre_filter_set_xx_hon_ ss_pre_filter_set_xx_hon_i))
      (setq ss_pre_filter_set_xx_hon_obj_ (vlax-ename->vla-object ss_pre_filter_set_xx_hon_ename_))
      (setq obj_type_ (vla-get-objectname (vlax-ename->vla-object ss_pre_filter_set_xx_hon_ename_)))
      (cond
        (;obj_type_case_1
           (and
              (= obj_type_ "AcDbPolyline" )

           )
           (progn
             (setq sumlist_ (list   
                              (list 
                                (car (vlax-safearray->list (vlax-variant-value (vla-get-coordinates ss_pre_filter_set_xx_hon_obj_ ))))
                                (cadr (vlax-safearray->list (vlax-variant-value (vla-get-coordinates ss_pre_filter_set_xx_hon_obj_ ))))
                                0
                              )
                              ss_pre_filter_set_xx_hon_ename_
                            )
             )
             (setq line_list_hon (cons sumlist_  line_list_hon ))
             (princ "obj_type_case_1")
           )
        )
        (;obj_type_case_2
           (and
              (= obj_type_ "AcDbLine" )

           )
           (progn
             (setq ss_pre_filter_set_xx_hon_obj_start_end_pt_ (list
                                      (setq ss_pre_filter_set_xx_hon_obj_startpt_ (vlax-safearray->list
                                                                 (vlax-variant-value ( vla-get-startpoint ss_pre_filter_set_xx_hon_obj_ ))
                                                               )
                                      )
                                      (setq ss_pre_filter_set_xx_hon_obj_endpt_ (vlax-safearray->list
                                                                (vlax-variant-value ( vla-get-endpoint ss_pre_filter_set_xx_hon_obj_ ))
                                                             )
                                      )
                                    )
              )
              (setq sumlist_ (list ss_pre_filter_set_xx_hon_obj_startpt_ ss_pre_filter_set_xx_hon_ename_ ))
              (setq line_list_hon (cons sumlist_  line_list_hon ))
             (princ "obj_type_case_2")
           )
        )
      )
      
      
      
      (setq ss_pre_filter_set_xx_hon_i (+ ss_pre_filter_set_xx_hon_i 1))
    )
  ;
  ;TA:stanndard_lambda_sorting
    (setq line_list_sorted_hon_ (vl-sort line_list_hon  ;bigest open indent list
                                    (function 
                                      (lambda (a b) 
                                        (> (nth 0 (car a)) (nth 0 (car b)))
                                      )
                                    )
                            ) ;bigest close indent list
    )
  ;

  ;selection_set_for_fillter_blk_name
    (if  ;pre_select_ssget_or_post_select_ssget
      (=
        (setq ss_pre_filter_set_xx_ver_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ver_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_ver_)
    )
  ;
  ;preloop_and_while
    (setq ss_pre_filter_set_xx_ver_i 0)
    (setq line_list_ver ())
    (while (< ss_pre_filter_set_xx_ver_i (sslength ss_pre_filter_set_xx_ver_))
      (setq ss_pre_filter_set_xx_ver_ename_ (ssname ss_pre_filter_set_xx_ver_ ss_pre_filter_set_xx_ver_i))
      (setq ss_pre_filter_set_xx_ver_obj_ (vlax-ename->vla-object ss_pre_filter_set_xx_ver_ename_))
      (setq obj_type_ (vla-get-objectname (vlax-ename->vla-object ss_pre_filter_set_xx_ver_ename_)))
      (cond
        (;obj_type_case_1
           (and
              (= obj_type_ "AcDbPolyline" )

           )
           (progn
             (setq sumlist_ (list   
                              (list 
                                (car (vlax-safearray->list (vlax-variant-value (vla-get-coordinates ss_pre_filter_set_xx_ver_obj_ ))))
                                (cadr (vlax-safearray->list (vlax-variant-value (vla-get-coordinates ss_pre_filter_set_xx_ver_obj_ ))))
                                0
                              )
                              ss_pre_filter_set_xx_ver_ename_
                            )
             )
             (setq line_list_ver (cons sumlist_  line_list_ver ))
             (princ "obj_type_case_1")
           )
        )
        (;obj_type_case_2
           (and
              (= obj_type_ "AcDbLine" )

           )
           (progn
             (setq ss_pre_filter_set_xx_ver_obj_start_end_pt_ (list
                                      (setq ss_pre_filter_set_xx_ver_obj_startpt_ (vlax-safearray->list
                                                                 (vlax-variant-value ( vla-get-startpoint ss_pre_filter_set_xx_ver_obj_ ))
                                                               )
                                      )
                                      (setq ss_pre_filter_set_xx_ver_obj_endpt_ (vlax-safearray->list
                                                                (vlax-variant-value ( vla-get-endpoint ss_pre_filter_set_xx_ver_obj_ ))
                                                             )
                                      )
                                    )
              )
              (setq sumlist_ (list ss_pre_filter_set_xx_ver_obj_startpt_ ss_pre_filter_set_xx_ver_ename_ ))
              (setq line_list_ver (cons sumlist_  line_list_ver ))
             (princ "obj_type_case_2")
           )
        )
      )
      
      
      
      (setq ss_pre_filter_set_xx_ver_i (+ ss_pre_filter_set_xx_ver_i 1))
    )
  ;
  ;TA:stanndard_lambda_sorting
    (setq line_list_sorted_ver_ (vl-sort line_list_ver  ;bigest open indent list
                                    (function 
                                      (lambda (a b) 
                                        (< (nth 1 (car a)) (nth 1 (car b)))
                                      )
                                    )
                            ) ;bigest close indent list
    )
  ;

  ;preloop_and_while
    (setq line_list_sorted_hon_i 0)
    (while (< line_list_sorted_hon_i (length line_list_sorted_hon_))
      (setq line_list_sorted_hon_ename_ (cadr (nth  line_list_sorted_hon_i line_list_sorted_hon_)))
      (setq line_list_sorted_hon_obj_ (vlax-ename->vla-object line_list_sorted_hon_ename_))
      (setq line_list_sorted_hon_obj_color_ (vla-get-color line_list_sorted_hon_obj_))
      
      
        ;preloop_and_while
          (setq line_list_sorted_ver_i 0)
          ; (setq blk_scale_i (* (length line_list_sorted_ver_) 0.20))
          (setq blk_scale_i 1)
      
          (while (< line_list_sorted_ver_i (length line_list_sorted_ver_))
            (setq line_list_sorted_ver_ename_ (cadr (nth  line_list_sorted_ver_i line_list_sorted_ver_)))
            (setq line_list_sorted_ver_obj_ (vlax-ename->vla-object line_list_sorted_ver_ename_))
            (setq line_list_sorted_ver_obj_color_ (vla-get-color line_list_sorted_ver_obj_))
            
            
            
              (cond
                (;color_case_1
                   (and
                      (= line_list_sorted_hon_obj_color_ 1)
                      (= line_list_sorted_ver_obj_color_ 1)
                      
                   )
                   (progn
                     (setq insertion_point_val_ (car (LM:intersections+0 line_list_sorted_hon_obj_ line_list_sorted_ver_obj_  acextendnone)))
                     (command "insert" user_input_name_block insertion_point_val_ blk_scale_i 0)
                     (princ "color_case_1")
                   )
                )
                (;color_case_2
                   (and
                      (= line_list_sorted_hon_obj_color_ 2)
                      (= line_list_sorted_ver_obj_color_ 2)
                      
                   )
                   (progn
                     (setq insertion_point_val_ (car (LM:intersections+0 line_list_sorted_hon_obj_ line_list_sorted_ver_obj_  acextendnone)))
                     (command "insert" user_input_name_block insertion_point_val_ blk_scale_i 0)
                     (princ "color_case_2")
                   )
                )
              )
            
            ; (if (=  "0.2" (rtos blk_scale_i 2 1))
            ;   (progn
            ;     (princ "S")
            ;   )
            ;     (setq blk_scale_i (- blk_scale_i 0.2))
            ; )
            
            (setq line_list_sorted_ver_i (+ line_list_sorted_ver_i 1))
          )
        ;
      
      (setq line_list_sorted_hon_i (+ line_list_sorted_hon_i 1))
    )
  ;
  
)
(defun c:TMEP_line_sorting_CT61 ()
  ; ;user-input_name_block_
    ;   (setq user_input_name_block "X10")
    ;   (TA:set-block-blockscaling user_input_name_block acUniform)
  ; ;
  ;user_input_
    ; (setq input_sc_ (cond ( (getint (strcat "\nspecify get block scale \n<" (rtos (setq input_sc_ (cond (input_sc_) (1.0) ) ) ) "> : " ) ) ) (input_sc_) ) )
    (setq input_dia_ (cond ( (getreal (strcat "\nspecify get block scale \n<" (rtos (setq input_dia_ (cond (input_dia_) (1.0) ) ) ) "> : " ) ) ) (input_dia_) ) )
  ;
  ;selection_set_for_fillter_blk_name
    (if  ;pre_select_ssget_or_post_select_ssget
      (=
        (setq ss_pre_filter_set_xx_hon_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_hon_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_hon_)
    )
  ;
  ;preloop_and_while
    (setq ss_pre_filter_set_xx_hon_i 0)
    (setq line_list_hon ())
    (while (< ss_pre_filter_set_xx_hon_i (sslength ss_pre_filter_set_xx_hon_))
      (setq ss_pre_filter_set_xx_hon_ename_ (ssname ss_pre_filter_set_xx_hon_ ss_pre_filter_set_xx_hon_i))
      (setq ss_pre_filter_set_xx_hon_obj_ (vlax-ename->vla-object ss_pre_filter_set_xx_hon_ename_))
      (setq obj_type_ (vla-get-objectname (vlax-ename->vla-object ss_pre_filter_set_xx_hon_ename_)))
      (cond
        (;obj_type_case_1
           (and
              (= obj_type_ "AcDbPolyline" )

           )
           (progn
             (setq sumlist_ (list   
                              (list 
                                (car (vlax-safearray->list (vlax-variant-value (vla-get-coordinates ss_pre_filter_set_xx_hon_obj_ ))))
                                (cadr (vlax-safearray->list (vlax-variant-value (vla-get-coordinates ss_pre_filter_set_xx_hon_obj_ ))))
                                0
                              )
                              ss_pre_filter_set_xx_hon_ename_
                            )
             )
             (setq line_list_hon (cons sumlist_  line_list_hon ))
             (princ "obj_type_case_1")
           )
        )
        (;obj_type_case_2
           (and
              (= obj_type_ "AcDbLine" )

           )
           (progn
             (setq ss_pre_filter_set_xx_hon_obj_start_end_pt_ (list
                                      (setq ss_pre_filter_set_xx_hon_obj_startpt_ (vlax-safearray->list
                                                                 (vlax-variant-value ( vla-get-startpoint ss_pre_filter_set_xx_hon_obj_ ))
                                                               )
                                      )
                                      (setq ss_pre_filter_set_xx_hon_obj_endpt_ (vlax-safearray->list
                                                                (vlax-variant-value ( vla-get-endpoint ss_pre_filter_set_xx_hon_obj_ ))
                                                             )
                                      )
                                    )
              )
              (setq sumlist_ (list ss_pre_filter_set_xx_hon_obj_startpt_ ss_pre_filter_set_xx_hon_ename_ ))
              (setq line_list_hon (cons sumlist_  line_list_hon ))
             (princ "obj_type_case_2")
           )
        )
      )
      
      
      
      (setq ss_pre_filter_set_xx_hon_i (+ ss_pre_filter_set_xx_hon_i 1))
    )
  ;
  ;TA:stanndard_lambda_sorting
    (setq line_list_sorted_hon_ (vl-sort line_list_hon  ;bigest open indent list
                                    (function 
                                      (lambda (a b) 
                                        (> (nth 0 (car a)) (nth 0 (car b)))
                                      )
                                    )
                            ) ;bigest close indent list
    )
  ;

  ;selection_set_for_fillter_blk_name
    (if  ;pre_select_ssget_or_post_select_ssget
      (=
        (setq ss_pre_filter_set_xx_ver_ (ssget "i"
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ver_ (ssget 
                                          (list
                                            (cons 0 "line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_ver_)
    )
  ;
  ;preloop_and_while
    (setq ss_pre_filter_set_xx_ver_i 0)
    (setq line_list_ver ())
    (while (< ss_pre_filter_set_xx_ver_i (sslength ss_pre_filter_set_xx_ver_))
      (setq ss_pre_filter_set_xx_ver_ename_ (ssname ss_pre_filter_set_xx_ver_ ss_pre_filter_set_xx_ver_i))
      (setq ss_pre_filter_set_xx_ver_obj_ (vlax-ename->vla-object ss_pre_filter_set_xx_ver_ename_))
      (setq obj_type_ (vla-get-objectname (vlax-ename->vla-object ss_pre_filter_set_xx_ver_ename_)))
      (cond
        (;obj_type_case_1
           (and
              (= obj_type_ "AcDbPolyline" )

           )
           (progn
             (setq sumlist_ (list   
                              (list 
                                (car (vlax-safearray->list (vlax-variant-value (vla-get-coordinates ss_pre_filter_set_xx_ver_obj_ ))))
                                (cadr (vlax-safearray->list (vlax-variant-value (vla-get-coordinates ss_pre_filter_set_xx_ver_obj_ ))))
                                0
                              )
                              ss_pre_filter_set_xx_ver_ename_
                            )
             )
             (setq line_list_ver (cons sumlist_  line_list_ver ))
             (princ "obj_type_case_1")
           )
        )
        (;obj_type_case_2
           (and
              (= obj_type_ "AcDbLine" )

           )
           (progn
             (setq ss_pre_filter_set_xx_ver_obj_start_end_pt_ (list
                                      (setq ss_pre_filter_set_xx_ver_obj_startpt_ (vlax-safearray->list
                                                                 (vlax-variant-value ( vla-get-startpoint ss_pre_filter_set_xx_ver_obj_ ))
                                                               )
                                      )
                                      (setq ss_pre_filter_set_xx_ver_obj_endpt_ (vlax-safearray->list
                                                                (vlax-variant-value ( vla-get-endpoint ss_pre_filter_set_xx_ver_obj_ ))
                                                             )
                                      )
                                    )
              )
              (setq sumlist_ (list ss_pre_filter_set_xx_ver_obj_startpt_ ss_pre_filter_set_xx_ver_ename_ ))
              (setq line_list_ver (cons sumlist_  line_list_ver ))
             (princ "obj_type_case_2")
           )
        )
      )
      
      
      
      (setq ss_pre_filter_set_xx_ver_i (+ ss_pre_filter_set_xx_ver_i 1))
    )
  ;
  ;TA:stanndard_lambda_sorting
    (setq line_list_sorted_ver_ (vl-sort line_list_ver  ;bigest open indent list
                                    (function 
                                      (lambda (a b) 
                                        (< (nth 1 (car a)) (nth 1 (car b)))
                                      )
                                    )
                            ) ;bigest close indent list
    )
  ;

  ;preloop_and_while
    (setq line_list_sorted_hon_i 0)
    (setq intersec_list_ ())
    (while (< line_list_sorted_hon_i (length line_list_sorted_hon_))
      (setq line_list_sorted_hon_ename_ (cadr (nth  line_list_sorted_hon_i line_list_sorted_hon_)))
      (setq line_list_sorted_hon_obj_ (vlax-ename->vla-object line_list_sorted_hon_ename_))
      (setq line_list_sorted_hon_obj_color_ (vla-get-color line_list_sorted_hon_obj_))
      
      
        ;preloop_and_while
          (setq line_list_sorted_ver_i 0)
          ; (setq blk_scale_i (* (length line_list_sorted_ver_) 0.20))
          (setq blk_scale_i 1)
      
          (while (< line_list_sorted_ver_i (length line_list_sorted_ver_))
            (setq line_list_sorted_ver_ename_ (cadr (nth  line_list_sorted_ver_i line_list_sorted_ver_)))
            (setq line_list_sorted_ver_obj_ (vlax-ename->vla-object line_list_sorted_ver_ename_))
            (setq line_list_sorted_ver_obj_color_ (vla-get-color line_list_sorted_ver_obj_))
            
            
            
              (cond
                (;color_case_1
                   (and
                      (= line_list_sorted_hon_obj_color_ 1)
                      (= line_list_sorted_ver_obj_color_ 1)
                      
                   )
                   (progn
                      (setq insertion_point_val_ (car (LM:intersections+0 line_list_sorted_hon_obj_ line_list_sorted_ver_obj_  acextendnone)))
                      (setq intersec_list_ (cons insertion_point_val_ intersec_list_ ))
                    ;  (command "insert" user_input_name_block insertion_point_val_ blk_scale_i 0)
                     (princ "color_case_1")
                   )
                )
                (;color_case_2
                   (and
                      (= line_list_sorted_hon_obj_color_ 2)
                      (= line_list_sorted_ver_obj_color_ 2)
                      
                   )
                   (progn
                     (setq insertion_point_val_ (car (LM:intersections+0 line_list_sorted_hon_obj_ line_list_sorted_ver_obj_  acextendnone)))
                    ;  (command "insert" user_input_name_block insertion_point_val_ blk_scale_i 0)
                     (princ "color_case_2")
                   )
                )
              )
            
            ; (if (=  "0.2" (rtos blk_scale_i 2 1))
            ;   (progn
            ;     (princ "S")
            ;   )
            ;     (setq blk_scale_i (- blk_scale_i 0.2))
            ; )
            
            (setq line_list_sorted_ver_i (+ line_list_sorted_ver_i 1))
          )
        ;
      
      (setq line_list_sorted_hon_i (+ line_list_sorted_hon_i 1))
    )
  ;
  
  ;foreach intersec circle
    (foreach i intersec_list_ 
      (TA:add_full_circle_ i (/  input_dia_ 2))
    )
  ;
)

(defun c:c:TMEP_line_sorting_CT7 ()
  ;user-input_name_block_
    (setq user_input_name_block "X15")
    (TA:set-block-explodable user_input_name_block acany)
    (TA:set-block-explodable user_input_name_block acUniform)
  ;
  ;selection_set_for_fillter_blk_name
    (if  ;pre_select_ssget_or_post_select_ssget
      (=
        (setq ss_pre_filter_set_xx_ (ssget "i"
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq line_list_ ())
    (while (< ss_pre_filter_set_xx_i (sslength ss_pre_filter_set_xx_))
      (setq ss_pre_filter_set_xx_ename_ (ssname ss_pre_filter_set_xx_ ss_pre_filter_set_xx_i))
      (setq ss_pre_filter_set_xx_hon_obj_ (vlax-ename->vla-object ss_pre_filter_set_xx_ename_))
      (setq obj_type_ (vla-get-objectname ss_pre_filter_set_xx_hon_obj_))
      (cond
        (;obj_type_case_1
           (and
              (= obj_type_ "AcDbPolyline" )

           )
           (progn
             (setq sumlist_ (list   
                              (list 
                                (car (vlax-safearray->list (vlax-variant-value (vla-get-coordinates ss_pre_filter_set_xx_hon_obj_ ))))
                                (cadr (vlax-safearray->list (vlax-variant-value (vla-get-coordinates ss_pre_filter_set_xx_hon_obj_ ))))
                                0
                              )
                              ss_pre_filter_set_xx_ename_
                            )
             )
             (setq line_list_ (cons sumlist_  line_list_ ))
             (princ "obj_type_case_1")
           )
        )
        (;obj_type_case_2
           (and
              (= obj_type_ "AcDbLine" )

           )
           (progn
             (setq ss_pre_filter_set_xx_hon_obj_start_end_pt_ (list
                                      (setq ss_pre_filter_set_xx_hon_obj_startpt_ (vlax-safearray->list
                                                                 (vlax-variant-value ( vla-get-startpoint ss_pre_filter_set_xx_hon_obj_ ))
                                                               )
                                      )
                                      (setq ss_pre_filter_set_xx_hon_obj_endpt_ (vlax-safearray->list
                                                                (vlax-variant-value ( vla-get-endpoint ss_pre_filter_set_xx_hon_obj_ ))
                                                             )
                                      )
                                    )
              )
              (setq sumlist_ (list ss_pre_filter_set_xx_hon_obj_startpt_ ss_pre_filter_set_xx_ename_ ))
              (setq line_list_ (cons sumlist_  line_list_ ))
             (princ "obj_type_case_2")
           )
        )
      )
      
      (setq ss_pre_filter_set_xx_i (+ ss_pre_filter_set_xx_i 1))
    )
  ;
  ;TA:stanndard_lambda_sorting
    (setq line_list_sorted_ (vl-sort line_list_  ;bigest open indent list
                                    (function 
                                      (lambda (a b) 
                                        (< (nth 0 (car a)) (nth 0 (car b)))
                                      )
                                    )
                            ) ;bigest close indent list
    )
  ;
  ;preloop_and_while
    (setq line_list_sorted_i 0)
    (setq line_list_sorted_i-color_ 1)
    (while (< line_list_sorted_i (length line_list_sorted_))
      (setq line_list_sorted_ename_ (cadr (nth  line_list_sorted_i line_list_sorted_)))
      (setq line_list_sorted_obj_ (vlax-ename->vla-object line_list_sorted_ename_))
      (setq line_list_sorted_obj_angle (rad-to-deg (vla-get-angle line_list_sorted_obj_)))
      (setq line_list_sorted_obj_color (vla-get-color line_list_sorted_obj_))
      (setq line_list_sorted_obj_start_end_pt_ (list
                                      (setq line_list_sorted_obj_startpt_ (vlax-safearray->list
                                                                 (vlax-variant-value ( vla-get-startpoint line_list_sorted_obj_ ))
                                                               )
                                      )
                                      (setq line_list_sorted_obj_endpt_ (vlax-safearray->list
                                                                (vlax-variant-value ( vla-get-endpoint line_list_sorted_obj_ ))
                                                             )
                                      )
                                    )
      )
      
      
      
   
      
      (cond
        (;_case_1
           (and
              (= line_list_sorted_obj_color 1)
           )
           (progn
             (command "insert" 
                      user_input_name_block
                      (polar line_list_sorted_obj_startpt_ 
                             (vla-get-angle line_list_sorted_obj_)
                             (* 0)
                      )
                     1
                      (rad-to-deg (vla-get-angle line_list_sorted_obj_))
             )
             (command "insert" 
                      user_input_name_block
                      (polar line_list_sorted_obj_startpt_ 
                             (vla-get-angle line_list_sorted_obj_)
                             (* 236 1)
                      )
                      0.6
                      (rad-to-deg (vla-get-angle line_list_sorted_obj_))
             )
             (command "insert" 
                      user_input_name_block
                      (polar line_list_sorted_obj_startpt_ 
                             (vla-get-angle line_list_sorted_obj_)
                             (* 236 2)
                      )
                      0.2
                      (rad-to-deg (vla-get-angle line_list_sorted_obj_))
             )
             (command "insert" 
                      user_input_name_block
                      (polar line_list_sorted_obj_startpt_ 
                             (vla-get-angle line_list_sorted_obj_)
                             (* 236 3)
                      )
                      0.2
                      (rad-to-deg (vla-get-angle line_list_sorted_obj_))
             )
             (princ "_case_1")
           )
        )
        (;_case_2
           (and
              (= line_list_sorted_obj_color 2)
           )
           (progn
             (command "insert" 
                      user_input_name_block
                      (polar line_list_sorted_obj_startpt_ 
                             (vla-get-angle line_list_sorted_obj_)
                             (+ 118 (*  0 118))
                      )
                      0.80
                      (rad-to-deg (vla-get-angle line_list_sorted_obj_))
             )
             (command "insert" 
                      user_input_name_block
                      (polar line_list_sorted_obj_startpt_ 
                             (vla-get-angle line_list_sorted_obj_)
                             (+ 118 (*  2 118))
                      )
                      0.4
                      (rad-to-deg (vla-get-angle line_list_sorted_obj_))
             )
             (command "insert" 
                      user_input_name_block
                      (polar line_list_sorted_obj_startpt_ 
                             (vla-get-angle line_list_sorted_obj_)
                             (+ 118 (*  4 118))
                      )
                      0.2
                      (rad-to-deg (vla-get-angle line_list_sorted_obj_))
             )
             (command "insert" 
                      user_input_name_block
                      (polar line_list_sorted_obj_startpt_ 
                             (vla-get-angle line_list_sorted_obj_)
                             (+ 118 (*  6 118))
                      )
                      0.2
                      (rad-to-deg (vla-get-angle line_list_sorted_obj_))
             )
             
             
             (princ "_case_2")
           )
        )
        
      )
      
      
      (setq line_list_sorted_i-color_ (+ line_list_sorted_i-color_ 1))
      (setq line_list_sorted_i (+ line_list_sorted_i 1))
    )
  ;
)













(defun c:resc ()
  

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;user_input_
    (setq input_sc_ (cond ( (getreal (strcat "\nspecify angle<" (rtos (setq input_sc_ (cond (input_sc_) (1.2) ) ) ) "> : " ) ) ) (input_sc_) ) )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))

        (setq ss_pre_filter_set_xx_obj_xsc_ (vla-get-xscalefactor ss_pre_filter_set_xx_obj_))

        (setq new_input_sc_ (* input_sc_ ss_pre_filter_set_xx_obj_xsc_))
      
        (vla-put-xscalefactor ss_pre_filter_set_xx_obj_ new_input_sc_)
      
      (setq ss_pre_filter_set_xx_i (+ ss_pre_filter_set_xx_i 1))
    )
  ;
)

(defun c:temp_PPLINE_INSERTION_BRACKET_INSBKK_ ()
  (setq PLine_ename_ (car (entsel "specify Object")))
  ;selection_set_for_fillter_blk_name
    (if  ;pre_select_ssget_or_post_select_ssget
      (=
        (setq SS_Line_ename_ (ssget "i"
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq SS_Line_ename_ (ssget
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength SS_Line_ename_)
    )
  ;preloop_and_while
    (setq SS_Line_ename_i 0)
    (while (< SS_Line_ename_i (sslength SS_Line_ename_))
      (setq PLine_ename_ (ssname SS_Line_ename_ SS_Line_ename_i))
        (if (= (vla-get-objectname (vlax-ename->vla-object PLine_ename_)) "AcDbPolyline")
          (progn
            (setq pline_pt_ (TA:Get_Pline_vertext_ins_point_ PLine_ename_))
            ; (TA:get_vertex_len_ PLine_ename_)
          ;
            (setq pline_pt_1pt (TA:midpoint (nth 0 (nth 1 pline_pt_)) (nth 1 (nth 1 pline_pt_)) ))
            (setq pline_pt_1dist (distance (nth 0 (nth 1 pline_pt_)) (nth 1 (nth 1 pline_pt_)) ))
            (setq pline_pt_1angle (angle (nth 0 (nth 1 pline_pt_)) (nth 1 (nth 1 pline_pt_)) ))
              (command "insert" "000 - DYNAMIC_VIEW_ASSCESSORIES_FAMELINE_ALEXTR._EQ.ANGLE-PROFILE_25x25mm._AG-25_COMBINE_VIEW" pline_pt_1pt 0.001 0 )
              (setq new_bk_ename_ (entlast))
              (setq new_bk_obj_ (vlax-ename->vla-object new_bk_ename_))
              (LM:setdynpropvalue new_bk_obj_ "view" "4_side_L_view")
              (LM:setdynpropvalue new_bk_obj_ "array_width" pline_pt_1dist )
              (LM:setdynpropvalue new_bk_obj_ "Flip state1" 1 )
              
            (setq pline_pt_2pt (TA:midpoint (nth 1 (nth 1 pline_pt_)) (nth 2 (nth 1 pline_pt_)) ))
            (setq pline_pt_2dist (distance (nth 1 (nth 1 pline_pt_)) (nth 2 (nth 1 pline_pt_)) ))
            (setq pline_pt_2angle (rad-to-deg (angle (nth 1 (nth 1 pline_pt_)) (nth 2 (nth 1 pline_pt_)) )))
              (command "insert" "000 - DYNAMIC_VIEW_ASSCESSORIES_FAMELINE_ALEXTR._EQ.ANGLE-PROFILE_25x25mm._AG-25_COMBINE_VIEW" pline_pt_2pt 0.001 pline_pt_2angle )
              (setq new_bk_ename_ (entlast))
              (setq new_bk_obj_ (vlax-ename->vla-object new_bk_ename_))
              (LM:setdynpropvalue new_bk_obj_ "view" "4_side_L_view")
              (LM:setdynpropvalue new_bk_obj_ "array_width" pline_pt_2dist )
              (LM:setdynpropvalue new_bk_obj_ "Flip state1" 1 )
                
            
            
            (setq pline_pt_3pt (TA:midpoint (nth 2 (nth 1 pline_pt_)) (nth 3 (nth 1 pline_pt_)) ))
            (setq pline_pt_3dist (distance (nth 2 (nth 1 pline_pt_)) (nth 3 (nth 1 pline_pt_)) ))
            (setq pline_pt_3angle (rad-to-deg (angle (nth 2 (nth 1 pline_pt_)) (nth 3 (nth 1 pline_pt_)) )))
              (command "insert" "000 - DYNAMIC_VIEW_ASSCESSORIES_FAMELINE_ALEXTR._EQ.ANGLE-PROFILE_25x25mm._AG-25_COMBINE_VIEW" pline_pt_3pt 0.001 pline_pt_3angle )
              (setq new_bk_ename_ (entlast))
              (setq new_bk_obj_ (vlax-ename->vla-object new_bk_ename_))
              (LM:setdynpropvalue new_bk_obj_ "view" "4_side_L_view")
              (LM:setdynpropvalue new_bk_obj_ "array_width" pline_pt_3dist )
              (LM:setdynpropvalue new_bk_obj_ "Flip state1" 1 )
            
            (setq pline_pt_4pt (TA:midpoint (nth 3 (nth 1 pline_pt_)) (nth 0 (nth 1 pline_pt_)) ))
            (setq pline_pt_4dist (distance (nth 3 (nth 1 pline_pt_)) (nth 0 (nth 1 pline_pt_)) ))
            (setq pline_pt_4angle (rad-to-deg (angle (nth 3 (nth 1 pline_pt_)) (nth 0 (nth 1 pline_pt_)) )))
              (command "insert" "000 - DYNAMIC_VIEW_ASSCESSORIES_FAMELINE_ALEXTR._EQ.ANGLE-PROFILE_25x25mm._AG-25_COMBINE_VIEW" pline_pt_4pt 0.001 pline_pt_4angle )
              (setq new_bk_ename_ (entlast))
              (setq new_bk_obj_ (vlax-ename->vla-object new_bk_ename_))
              (LM:setdynpropvalue new_bk_obj_ "view" "4_side_L_view")
              (LM:setdynpropvalue new_bk_obj_ "array_width" pline_pt_4dist )
              (LM:setdynpropvalue new_bk_obj_ "Flip state1" 1 )
          ;
            
          )
        )
        (if (= (vla-get-objectname (vlax-ename->vla-object PLine_ename_)) "AcDbBlockReference")
          (progn
            (setq new_dyn_obj_ (vlax-ename->vla-object PLine_ename_))
            (setq new_dyn_obj_ins_ (vlax-safearray->list (vlax-variant-value (vla-get-insertionpoint new_dyn_obj_))))
            (setq point1_xy_
              (list
                (setq point1_x (+ (car new_dyn_obj_ins_) (LM:getdynpropvalue new_dyn_obj_ "position1 x" )))
                (setq point1_y (+ (cadr new_dyn_obj_ins_) (LM:getdynpropvalue new_dyn_obj_ "position1 y" )))
              )
            )
            (setq point2_xy_
              (list
                (setq point2_x (+ (car new_dyn_obj_ins_) (LM:getdynpropvalue new_dyn_obj_ "position2 x" )))
                (setq point2_y (+ (cadr new_dyn_obj_ins_) (LM:getdynpropvalue new_dyn_obj_ "position2 y" )))
              )
            )
            (setq point3_xy_
              (list
                (setq point3_x (+ (car new_dyn_obj_ins_) (LM:getdynpropvalue new_dyn_obj_ "position3 x" )))
                (setq point3_y (+ (cadr new_dyn_obj_ins_) (LM:getdynpropvalue new_dyn_obj_ "position3 y" )))
              )
            )
            (setq point4_xy_
              (list
                (setq point4_x (+ (car new_dyn_obj_ins_) (LM:getdynpropvalue new_dyn_obj_ "position4 x" )))
                (setq point4_y (+ (cadr new_dyn_obj_ins_) (LM:getdynpropvalue new_dyn_obj_ "position4 y" )))
              )
            )
            (setq pline_pt_ (list "sss" (list point1_xy_ point2_xy_ point3_xy_ point4_xy_ )))
            ;
              (setq pline_pt_1pt (TA:midpoint (nth 0 (nth 1 pline_pt_)) (nth 1 (nth 1 pline_pt_)) ))
              (setq pline_pt_1dist (distance (nth 0 (nth 1 pline_pt_)) (nth 1 (nth 1 pline_pt_)) ))
              (setq pline_pt_1angle (angle (nth 0 (nth 1 pline_pt_)) (nth 1 (nth 1 pline_pt_)) ))
                (command "insert" "000 - DYNAMIC_VIEW_ASSCESSORIES_FAMELINE_ALEXTR._EQ.ANGLE-PROFILE_25x25mm._AG-25_COMBINE_VIEW" pline_pt_1pt 0.001 0 )
                (setq new_bk_ename_ (entlast))
                (setq new_bk_obj_ (vlax-ename->vla-object new_bk_ename_))
                (LM:setdynpropvalue new_bk_obj_ "view" "4_side_L_view")
                (LM:setdynpropvalue new_bk_obj_ "array_width" pline_pt_1dist )
                (LM:setdynpropvalue new_bk_obj_ "move" 50 )
                (LM:setdynpropvalue new_bk_obj_ "Flip state1" 1 )
                
              (setq pline_pt_2pt (TA:midpoint (nth 1 (nth 1 pline_pt_)) (nth 2 (nth 1 pline_pt_)) ))
              (setq pline_pt_2dist (distance (nth 1 (nth 1 pline_pt_)) (nth 2 (nth 1 pline_pt_)) ))
              (setq pline_pt_2angle (rad-to-deg (angle (nth 1 (nth 1 pline_pt_)) (nth 2 (nth 1 pline_pt_)) )))
                (command "insert" "000 - DYNAMIC_VIEW_ASSCESSORIES_FAMELINE_ALEXTR._EQ.ANGLE-PROFILE_25x25mm._AG-25_COMBINE_VIEW" pline_pt_2pt 0.001 pline_pt_2angle )
                (setq new_bk_ename_ (entlast))
                (setq new_bk_obj_ (vlax-ename->vla-object new_bk_ename_))
                (LM:setdynpropvalue new_bk_obj_ "view" "4_side_L_view")
                (LM:setdynpropvalue new_bk_obj_ "array_width" pline_pt_2dist )
                (LM:setdynpropvalue new_bk_obj_ "move" 50 )
                (LM:setdynpropvalue new_bk_obj_ "Flip state1" 1 )
                  
              
              
              (setq pline_pt_3pt (TA:midpoint (nth 2 (nth 1 pline_pt_)) (nth 3 (nth 1 pline_pt_)) ))
              (setq pline_pt_3dist (distance (nth 2 (nth 1 pline_pt_)) (nth 3 (nth 1 pline_pt_)) ))
              (setq pline_pt_3angle (rad-to-deg (angle (nth 2 (nth 1 pline_pt_)) (nth 3 (nth 1 pline_pt_)) )))
                (command "insert" "000 - DYNAMIC_VIEW_ASSCESSORIES_FAMELINE_ALEXTR._EQ.ANGLE-PROFILE_25x25mm._AG-25_COMBINE_VIEW" pline_pt_3pt 0.001 pline_pt_3angle )
                (setq new_bk_ename_ (entlast))
                (setq new_bk_obj_ (vlax-ename->vla-object new_bk_ename_))
                (LM:setdynpropvalue new_bk_obj_ "view" "4_side_L_view")
                (LM:setdynpropvalue new_bk_obj_ "array_width" pline_pt_3dist )
                (LM:setdynpropvalue new_bk_obj_ "Flip state1" 1 )
              
              (setq pline_pt_4pt (TA:midpoint (nth 3 (nth 1 pline_pt_)) (nth 0 (nth 1 pline_pt_)) ))
              (setq pline_pt_4dist (distance (nth 3 (nth 1 pline_pt_)) (nth 0 (nth 1 pline_pt_)) ))
              (setq pline_pt_4angle (rad-to-deg (angle (nth 3 (nth 1 pline_pt_)) (nth 0 (nth 1 pline_pt_)) )))
                (command "insert" "000 - DYNAMIC_VIEW_ASSCESSORIES_FAMELINE_ALEXTR._EQ.ANGLE-PROFILE_25x25mm._AG-25_COMBINE_VIEW" pline_pt_4pt 0.001 pline_pt_4angle )
                (setq new_bk_ename_ (entlast))
                (setq new_bk_obj_ (vlax-ename->vla-object new_bk_ename_))
                (LM:setdynpropvalue new_bk_obj_ "view" "4_side_L_view")
                (LM:setdynpropvalue new_bk_obj_ "array_width" pline_pt_4dist )
                (LM:setdynpropvalue new_bk_obj_ "Flip state1" 1 )
            ;
          )
        )
      (setq SS_Line_ename_i (+ SS_Line_ename_i 1))
    )
  ;
  ;
)
(defun c:temp_PPLINE_INSERTION_BRACKET_INSBKK1_ ()
  ;selection_set_for_fillter_blk_name
    (if  ;pre_select_ssget_or_post_select_ssget
      (=
        (setq SS_Line_ename_ (ssget "i"
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq SS_Line_ename_ (ssget
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength SS_Line_ename_)
    )
  ;preloop_and_while
    (setq SS_Line_ename_i 0)
    (while (< SS_Line_ename_i (sslength SS_Line_ename_))
      (setq PLine_ename_ (ssname SS_Line_ename_ SS_Line_ename_i))
        (if (= (vla-get-objectname (vlax-ename->vla-object PLine_ename_)) "AcDbPolyline")
          (progn
            (setq pline_pt_ (TA:Get_Pline_vertext_ins_point_ PLine_ename_))
            ; (TA:get_vertex_len_ PLine_ename_)
          ;
            (setq pline_pt_1pt (TA:midpoint (nth 0 (nth 1 pline_pt_)) (nth 1 (nth 1 pline_pt_)) ))
            (setq pline_pt_1dist (distance (nth 0 (nth 1 pline_pt_)) (nth 1 (nth 1 pline_pt_)) ))
            (setq pline_pt_1angle (angle (nth 0 (nth 1 pline_pt_)) (nth 1 (nth 1 pline_pt_)) ))
              (command "insert" "BKMNSET1" pline_pt_1pt 1 0 )
              (setq new_bk_ename_ (entlast))
              (setq new_bk_obj_ (vlax-ename->vla-object new_bk_ename_))
              ; (LM:setdynpropvalue new_bk_obj_ "view" "4_side_L_view")
              (LM:setdynpropvalue new_bk_obj_ "array_width" pline_pt_1dist )
              ; (LM:setdynpropvalue new_bk_obj_ "Flip state1" 1 )
              
            (setq pline_pt_2pt (TA:midpoint (nth 1 (nth 1 pline_pt_)) (nth 2 (nth 1 pline_pt_)) ))
            (setq pline_pt_2dist (distance (nth 1 (nth 1 pline_pt_)) (nth 2 (nth 1 pline_pt_)) ))
            (setq pline_pt_2angle (rad-to-deg (angle (nth 1 (nth 1 pline_pt_)) (nth 2 (nth 1 pline_pt_)) )))
              (command "insert" "BKMNSET1" pline_pt_2pt 1 pline_pt_2angle )
              (setq new_bk_ename_ (entlast))
              (setq new_bk_obj_ (vlax-ename->vla-object new_bk_ename_))
              ; (LM:setdynpropvalue new_bk_obj_ "view" "4_side_L_view")
              (LM:setdynpropvalue new_bk_obj_ "array_width" pline_pt_2dist )
              ; (LM:setdynpropvalue new_bk_obj_ "Flip state1" 1 )
            (setq pline_pt_3pt (TA:midpoint (nth 2 (nth 1 pline_pt_)) (nth 3 (nth 1 pline_pt_)) ))
            (setq pline_pt_3dist (distance (nth 2 (nth 1 pline_pt_)) (nth 3 (nth 1 pline_pt_)) ))
            (setq pline_pt_3angle (rad-to-deg (angle (nth 2 (nth 1 pline_pt_)) (nth 3 (nth 1 pline_pt_)) )))
              (command "insert" "BKMNSET1" pline_pt_3pt 1 pline_pt_3angle )
              (setq new_bk_ename_ (entlast))
              (setq new_bk_obj_ (vlax-ename->vla-object new_bk_ename_))
              ; (LM:setdynpropvalue new_bk_obj_ "view" "4_side_L_view")
              (LM:setdynpropvalue new_bk_obj_ "array_width" pline_pt_3dist )
              ; (LM:setdynpropvalue new_bk_obj_ "Flip state1" 1 )
            
            (setq pline_pt_4pt (TA:midpoint (nth 3 (nth 1 pline_pt_)) (nth 0 (nth 1 pline_pt_)) ))
            (setq pline_pt_4dist (distance (nth 3 (nth 1 pline_pt_)) (nth 0 (nth 1 pline_pt_)) ))
            (setq pline_pt_4angle (rad-to-deg (angle (nth 3 (nth 1 pline_pt_)) (nth 0 (nth 1 pline_pt_)) )))
              (command "insert" "BKMNSET1" pline_pt_4pt 1 pline_pt_4angle )
              (setq new_bk_ename_ (entlast))
              (setq new_bk_obj_ (vlax-ename->vla-object new_bk_ename_))
              ; (LM:setdynpropvalue new_bk_obj_ "view" "4_side_L_view")
              (LM:setdynpropvalue new_bk_obj_ "array_width" pline_pt_4dist )
              ; (LM:setdynpropvalue new_bk_obj_ "Flip state1" 1 )
          ;
            
          )
        )
        (if (= (vla-get-objectname (vlax-ename->vla-object PLine_ename_)) "AcDbBlockReference")
          (progn
            (setq new_dyn_obj_ (vlax-ename->vla-object PLine_ename_))
            (setq new_dyn_obj_ins_ (vlax-safearray->list (vlax-variant-value (vla-get-insertionpoint new_dyn_obj_))))
            (setq point1_xy_
              (list
                (setq point1_x (+ (car new_dyn_obj_ins_) (LM:getdynpropvalue new_dyn_obj_ "position1 x" )))
                (setq point1_y (+ (cadr new_dyn_obj_ins_) (LM:getdynpropvalue new_dyn_obj_ "position1 y" )))
              )
            )
            (setq point2_xy_
              (list
                (setq point2_x (+ (car new_dyn_obj_ins_) (LM:getdynpropvalue new_dyn_obj_ "position2 x" )))
                (setq point2_y (+ (cadr new_dyn_obj_ins_) (LM:getdynpropvalue new_dyn_obj_ "position2 y" )))
              )
            )
            (setq point3_xy_
              (list
                (setq point3_x (+ (car new_dyn_obj_ins_) (LM:getdynpropvalue new_dyn_obj_ "position3 x" )))
                (setq point3_y (+ (cadr new_dyn_obj_ins_) (LM:getdynpropvalue new_dyn_obj_ "position3 y" )))
              )
            )
            (setq point4_xy_
              (list
                (setq point4_x (+ (car new_dyn_obj_ins_) (LM:getdynpropvalue new_dyn_obj_ "position4 x" )))
                (setq point4_y (+ (cadr new_dyn_obj_ins_) (LM:getdynpropvalue new_dyn_obj_ "position4 y" )))
              )
            )
            (setq pline_pt_ (list "sss" (list point1_xy_ point2_xy_ point3_xy_ point4_xy_ )))
            ;
              (setq pline_pt_1pt (TA:midpoint (nth 0 (nth 1 pline_pt_)) (nth 1 (nth 1 pline_pt_)) ))
              (setq pline_pt_1dist (distance (nth 0 (nth 1 pline_pt_)) (nth 1 (nth 1 pline_pt_)) ))
              (setq pline_pt_1angle (angle (nth 0 (nth 1 pline_pt_)) (nth 1 (nth 1 pline_pt_)) ))
                (command "insert" "000 - DYNAMIC_VIEW_ASSCESSORIES_FAMELINE_ALEXTR._EQ.ANGLE-PROFILE_25x25mm._AG-25_COMBINE_VIEW" pline_pt_1pt 0.001 0 )
                (setq new_bk_ename_ (entlast))
                (setq new_bk_obj_ (vlax-ename->vla-object new_bk_ename_))
                (LM:setdynpropvalue new_bk_obj_ "view" "4_side_L_view")
                (LM:setdynpropvalue new_bk_obj_ "array_width" pline_pt_1dist )
                (LM:setdynpropvalue new_bk_obj_ "move" 50 )
                (LM:setdynpropvalue new_bk_obj_ "Flip state1" 1 )
                
              (setq pline_pt_2pt (TA:midpoint (nth 1 (nth 1 pline_pt_)) (nth 2 (nth 1 pline_pt_)) ))
              (setq pline_pt_2dist (distance (nth 1 (nth 1 pline_pt_)) (nth 2 (nth 1 pline_pt_)) ))
              (setq pline_pt_2angle (rad-to-deg (angle (nth 1 (nth 1 pline_pt_)) (nth 2 (nth 1 pline_pt_)) )))
                (command "insert" "000 - DYNAMIC_VIEW_ASSCESSORIES_FAMELINE_ALEXTR._EQ.ANGLE-PROFILE_25x25mm._AG-25_COMBINE_VIEW" pline_pt_2pt 0.001 pline_pt_2angle )
                (setq new_bk_ename_ (entlast))
                (setq new_bk_obj_ (vlax-ename->vla-object new_bk_ename_))
                (LM:setdynpropvalue new_bk_obj_ "view" "4_side_L_view")
                (LM:setdynpropvalue new_bk_obj_ "array_width" pline_pt_2dist )
                (LM:setdynpropvalue new_bk_obj_ "move" 50 )
                (LM:setdynpropvalue new_bk_obj_ "Flip state1" 1 )
                  
              
              
              (setq pline_pt_3pt (TA:midpoint (nth 2 (nth 1 pline_pt_)) (nth 3 (nth 1 pline_pt_)) ))
              (setq pline_pt_3dist (distance (nth 2 (nth 1 pline_pt_)) (nth 3 (nth 1 pline_pt_)) ))
              (setq pline_pt_3angle (rad-to-deg (angle (nth 2 (nth 1 pline_pt_)) (nth 3 (nth 1 pline_pt_)) )))
                (command "insert" "000 - DYNAMIC_VIEW_ASSCESSORIES_FAMELINE_ALEXTR._EQ.ANGLE-PROFILE_25x25mm._AG-25_COMBINE_VIEW" pline_pt_3pt 0.001 pline_pt_3angle )
                (setq new_bk_ename_ (entlast))
                (setq new_bk_obj_ (vlax-ename->vla-object new_bk_ename_))
                (LM:setdynpropvalue new_bk_obj_ "view" "4_side_L_view")
                (LM:setdynpropvalue new_bk_obj_ "array_width" pline_pt_3dist )
                (LM:setdynpropvalue new_bk_obj_ "Flip state1" 1 )
              
              (setq pline_pt_4pt (TA:midpoint (nth 3 (nth 1 pline_pt_)) (nth 0 (nth 1 pline_pt_)) ))
              (setq pline_pt_4dist (distance (nth 3 (nth 1 pline_pt_)) (nth 0 (nth 1 pline_pt_)) ))
              (setq pline_pt_4angle (rad-to-deg (angle (nth 3 (nth 1 pline_pt_)) (nth 0 (nth 1 pline_pt_)) )))
                (command "insert" "000 - DYNAMIC_VIEW_ASSCESSORIES_FAMELINE_ALEXTR._EQ.ANGLE-PROFILE_25x25mm._AG-25_COMBINE_VIEW" pline_pt_4pt 0.001 pline_pt_4angle )
                (setq new_bk_ename_ (entlast))
                (setq new_bk_obj_ (vlax-ename->vla-object new_bk_ename_))
                (LM:setdynpropvalue new_bk_obj_ "view" "4_side_L_view")
                (LM:setdynpropvalue new_bk_obj_ "array_width" pline_pt_4dist )
                (LM:setdynpropvalue new_bk_obj_ "Flip state1" 1 )
            ;
          )
        )
      (setq SS_Line_ename_i (+ SS_Line_ename_i 1))
    )
  ;
  ;
)
(defun c:temp_PPLINE_INSERTION_STLINE ()
  (setq PLine_ename_ (car (entsel "specify Object")))
  (if (= (vla-get-objectname (vlax-ename->vla-object PLine_ename_)) "AcDbPolyline")
    (progn
      (setq pline_pt_ (TA:Get_Pline_vertext_ins_point_ PLine_ename_))
      (TA:get_vertex_len_ PLine_ename_)
    ;
      (setq pline_pt_1pt (TA:midpoint (nth 0 (nth 1 pline_pt_)) (nth 1 (nth 1 pline_pt_)) ))
      (setq pline_pt_1dist (distance (nth 0 (nth 1 pline_pt_)) (nth 1 (nth 1 pline_pt_)) ))
      (setq pline_pt_1angle (rad-to-deg (angle (nth 0 (nth 1 pline_pt_)) (nth 1 (nth 1 pline_pt_)) )))
        (command "insert" "001 - DYNAMIC REC&SSQ SHAPE SOLID_midpoint" (nth 0 (nth 1 pline_pt_)) 1 pline_pt_1angle )
        (setq new_bk_ename_ (entlast))
        (setq new_bk_obj_ (vlax-ename->vla-object new_bk_ename_))
        (LM:setdynpropvalue new_bk_obj_ "h" pline_pt_1dist)
        (LM:setdynpropvalue new_bk_obj_ "w" 50)
        ; (LM:setdynpropvalue new_bk_obj_ "array_width" pline_pt_1dist )
        ; (LM:setdynpropvalue new_bk_obj_ "Flip state1" 1 )
        
      (setq pline_pt_2pt (TA:midpoint (nth 1 (nth 1 pline_pt_)) (nth 2 (nth 1 pline_pt_)) ))
      (setq pline_pt_2dist (distance (nth 1 (nth 1 pline_pt_)) (nth 2 (nth 1 pline_pt_)) ))
      (setq pline_pt_2angle (rad-to-deg (angle (nth 1 (nth 1 pline_pt_)) (nth 2 (nth 1 pline_pt_)) )))
        (command "insert" "001 - DYNAMIC REC&SSQ SHAPE SOLID_midpoint" (nth 1 (nth 1 pline_pt_)) 1 pline_pt_2angle )
        (setq new_bk_ename_ (entlast))
        (setq new_bk_obj_ (vlax-ename->vla-object new_bk_ename_))
        (LM:setdynpropvalue new_bk_obj_ "h" pline_pt_2dist)
        (LM:setdynpropvalue new_bk_obj_ "w" 50)
        ; (LM:setdynpropvalue new_bk_obj_ "array_width" pline_pt_2dist )
        ; (LM:setdynpropvalue new_bk_obj_ "Flip state1" 1 )
          
      
      
      (setq pline_pt_3pt (TA:midpoint (nth 2 (nth 1 pline_pt_)) (nth 3 (nth 1 pline_pt_)) ))
      (setq pline_pt_3dist (distance (nth 2 (nth 1 pline_pt_)) (nth 3 (nth 1 pline_pt_)) ))
      (setq pline_pt_3angle (rad-to-deg (angle (nth 2 (nth 1 pline_pt_)) (nth 3 (nth 1 pline_pt_)) )))
        (command "insert" "001 - DYNAMIC REC&SSQ SHAPE SOLID_midpoint" (nth 2 (nth 1 pline_pt_)) 1 pline_pt_3angle )
        (setq new_bk_ename_ (entlast))
        (setq new_bk_obj_ (vlax-ename->vla-object new_bk_ename_))
        (LM:setdynpropvalue new_bk_obj_ "h" pline_pt_3dist)
        (LM:setdynpropvalue new_bk_obj_ "w" 50)
        ; (LM:setdynpropvalue new_bk_obj_ "array_width" pline_pt_3dist )
        ; (LM:setdynpropvalue new_bk_obj_ "Flip state1" 1 )
      
      (setq pline_pt_4pt (TA:midpoint (nth 3 (nth 1 pline_pt_)) (nth 0 (nth 1 pline_pt_)) ))
      (setq pline_pt_4dist (distance (nth 3 (nth 1 pline_pt_)) (nth 0 (nth 1 pline_pt_)) ))
      (setq pline_pt_4angle (rad-to-deg (angle (nth 3 (nth 1 pline_pt_)) (nth 0 (nth 1 pline_pt_)) )))
        (command "insert" "001 - DYNAMIC REC&SSQ SHAPE SOLID_midpoint" (nth 3 (nth 1 pline_pt_)) 1 pline_pt_4angle )
        (setq new_bk_ename_ (entlast))
        (setq new_bk_obj_ (vlax-ename->vla-object new_bk_ename_))
        (LM:setdynpropvalue new_bk_obj_ "h" pline_pt_4dist)
        (LM:setdynpropvalue new_bk_obj_ "w" 50)
        ; (LM:setdynpropvalue new_bk_obj_ "array_width" pline_pt_4dist )
        ; (LM:setdynpropvalue new_bk_obj_ "Flip state1" 1 )
    ;
      
    )
  )
)
(defun c:temp_PPLINE_INSERTION_SSTLINE ()
  ;selection_set_for_fillter_blk_name
    (if  ;pre_select_ssget_or_post_select_ssget
      (=
        (setq ss_pre_filter_set_xx_ (ssget "i"
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;user_input_
    (setq get_steel_size (cond ( (getint (strcat "\nspecify get get_steel_size" (rtos (setq get_steel_size (cond (get_steel_size) (1.0) ) ) ) "> : " ) ) ) (get_steel_size) ) )
  ;
  ;preloop_and_while
    (setq ss_pre_filter_set_xx_i 0)
    (while (< ss_pre_filter_set_xx_i (sslength ss_pre_filter_set_xx_))
      (setq PLine_ename_ (ssname ss_pre_filter_set_xx_ ss_pre_filter_set_xx_i))
      (setq PLine_obj_ (vlax-ename->vla-object PLine_ename_))
      (setq pline_obj_start_end_pt_ (list
                                      (setq pline_obj_startpt_ (vlax-safearray->list
                                                                 (vlax-variant-value ( vla-get-startpoint pline_obj_ ))
                                                               )
                                      )
                                      (setq pline_obj_endpt_ (vlax-safearray->list
                                                                (vlax-variant-value ( vla-get-endpoint pline_obj_ ))
                                                             )
                                      )
                                    )
      )
      (setq pline_obj_get_angle (rad-to-deg (vla-get-angle pline_obj_)))
      (setq pline_obj_get_length (vla-get-length pline_obj_))
      (command "insert" "001 - DYNAMIC REC&SSQ SHAPE SOLID_midpoint" pline_obj_startpt_ 1 pline_obj_get_angle )
      (setq pline_new_ename_ (entlast))
      (setq pline_new_obj_ (vlax-ename->vla-object pline_new_ename_))
      (LM:setdynpropvalue pline_new_obj_ "H" pline_obj_get_length )
      (LM:setdynpropvalue pline_new_obj_ "W" get_steel_size )
      
        
      
      (setq ss_pre_filter_set_xx_i (+ ss_pre_filter_set_xx_i 1))
    )
  ;
)
(defun c:temp_PPLINE_INSERTION_GGLINE ()
  ;selection_set_for_fillter_blk_name
    (if  ;pre_select_ssget_or_post_select_ssget
      (=
        (setq ss_pre_filter_set_xx_ (ssget "i"
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ; ;user_input_
  ;   (setq get_steel_size (cond ( (getint (strcat "\nspecify get get_steel_size" (rtos (setq get_steel_size (cond (get_steel_size) (1.0) ) ) ) "> : " ) ) ) (get_steel_size) ) )
  ; ;
  ;preloop_and_while
    (setq ss_pre_filter_set_xx_i 0)
    (while (< ss_pre_filter_set_xx_i (sslength ss_pre_filter_set_xx_))
      (setq PLine_ename_ (ssname ss_pre_filter_set_xx_ ss_pre_filter_set_xx_i))
      (setq PLine_obj_ (vlax-ename->vla-object PLine_ename_))
      (setq pline_obj_start_end_pt_ (list
                                      (setq pline_obj_startpt_ (vlax-safearray->list
                                                                 (vlax-variant-value ( vla-get-startpoint pline_obj_ ))
                                                               )
                                      )
                                      (setq pline_obj_endpt_ (vlax-safearray->list
                                                                (vlax-variant-value ( vla-get-endpoint pline_obj_ ))
                                                             )
                                      )
                                    )
      )
      (if ;reverse object process
        (or 
          (> (car pline_obj_startpt_) (car pline_obj_endpt_))
          (< (cadr pline_obj_startpt_) (cadr pline_obj_endpt_))
        )
        (progn
          (command "reverse" PLine_ename_ "")
          (setq pline_obj_start_end_pt_ (list
                                      (setq pline_obj_startpt_ (vlax-safearray->list
                                                                 (vlax-variant-value ( vla-get-startpoint pline_obj_ ))
                                                               )
                                      )
                                      (setq pline_obj_endpt_ (vlax-safearray->list
                                                                (vlax-variant-value ( vla-get-endpoint pline_obj_ ))
                                                             )
                                      )
                                    )
          )
        )
      )
      
      
      (setq pline_obj_get_angle (rad-to-deg (vla-get-angle pline_obj_)))
      (setq pline_obj_get_length (vla-get-length pline_obj_))
      (command "insert" "000-GRID_LINE_DYN" pline_obj_startpt_ 1 (+ 90 pline_obj_get_angle) )
      
      (setq pline_new_ename_ (entlast))
      (setq pline_new_obj_ (vlax-ename->vla-object pline_new_ename_))
      (vla-put-layer pline_new_obj_ "000 - GRID")
      (vla-put-color pline_new_obj_ 256)
      
      (LM:setdynpropvalue pline_new_obj_ "H" pline_obj_get_length )
      (LM:setdynpropvalue pline_new_obj_ "offset" 250 )
      
      
      (vla-delete pline_obj_)
        
      
      (setq ss_pre_filter_set_xx_i (+ ss_pre_filter_set_xx_i 1))
    )
  ;
)


(defun c:temp_PPLINE_summary_matterial_summ_ ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;filler process
    (setq blk_ename_ (car (entsel "specify filter Object")))
    (setq blk_obj_ (vlax-ename->vla-object blk_ename_))
      (if 
        (and
          (= (vla-get-objectname blk_obj_) "AcDbBlockReference")
          (= (vla-get-hasattributes blk_obj_) :vlax-true)
          
        )
        (progn
          (setq blk_filter_ (LM:vl-getattributevalue blk_obj_ "PART_NAME_") )
        )
      )
  ;
  ;preloop_and_while
    (setq ss_pre_filter_set_xx_i 0)
    (setq TTL_ 0)
    (setq qty_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      
      
      (if (= (LM:vl-getattributevalue ss_pre_filter_set_xx_obj_ "PART_NAME_") blk_filter_  )
        (progn
          
          (if (/= (setq TL_ (LM:getdynpropvalue ss_pre_filter_set_xx_obj_ "H")) nil)
            (progn
              (setq TTL_ (+ TTL_ TL_))
            )
          )
          
          (setq code_name_ (LM:vl-getattributevalue ss_pre_filter_set_xx_obj_ "CODE_NAME_"))
          (setq qty_i (+ qty_i 1 ))
        )
      )
      
      (setq ss_pre_filter_set_xx_i (+ ss_pre_filter_set_xx_i 1))
    )
  ;
  ;fillter_summary_list_name_object_
    (setq summary_list_ename_ nil)
    (while (= summary_list_ename_ nil)
      ;user_input_data
        (setq summary_list_ename_ (car (entsel "specify summary_list_ename_ Object")))
      ;
      ;fillter_object_type_
        (if 
          (and
            (if (/= summary_list_ename_ nil) (progn (setq summary_list_obj_ (vlax-ename->vla-object summary_list_ename_)) ))
              (= (vla-get-objectname summary_list_obj_) "AcDbBlockReference")
              (= (vla-get-hasattributes summary_list_obj_) :vlax-true )
              (= (LM:effectivename summary_list_obj_) "000 - DAYNAMIC_DATA_FAMELINE_SUMMARY_LIST" )
            )
          (progn
            (setq summary_list_tag_list_ (LM:vl-getattributevalues summary_list_obj_))
            (LM:vl-setattributevalue summary_list_obj_ "PART_NAME_" blk_filter_  )
            (LM:vl-setattributevalue summary_list_obj_ "CODE_NAME_" code_name_  )
            (LM:vl-setattributevalue summary_list_obj_ "QTY_VAL" qty_i  )
            (LM:vl-setattributevalue summary_list_obj_ "LENGTH_VAL" (rtos (/ TTL_ 1000) 2 2)  )
            (setq get_total_ (cond ( (getint (strcat "\nspecify get_total_ <" (rtos (setq get_total_ (cond (get_total_) (1.0) ) ) ) "> : " ) ) ) (get_total_) ) )
            (LM:vl-setattributevalue summary_list_obj_ "SET_VALUE" get_total_  )
            
          )
          (setq summary_list_ename_ nil)
        )
        (if
          (or
            (= summary_list_ename_ nil)
            (/= (vla-get-objectname summary_list_obj_) "AcDbBlockReference")
            (if (= (vla-get-objectname summary_list_obj_) "AcDbBlockReference") (progn (/= (vla-get-hasattributes summary_list_obj_) :vlax-true ) ))
          )
          (progn
            (alert "Please selection attribute object")
          )
        )
      ;
    )
  ;
  
)


(defun c:line_2_line_L2L_()
  (setq p1_ename_ (car (entsel "specify Object")))
  (setq p1_obj_ (vlax-ename->vla-object p1_ename_))
  (setq p2_ename_ (car (entsel "specify Object")))
  (setq p2_obj_ (vlax-ename->vla-object p2_ename_))
  
  (setq p1_obj_start_end_pt_ (list
                                  (setq p1_obj_startpt_ (vlax-safearray->list
                                                             (vlax-variant-value ( vla-get-startpoint p1_obj_ ))
                                                           )
                                  )
                                  (setq p1_obj_endpt_ (vlax-safearray->list
                                                            (vlax-variant-value ( vla-get-endpoint p1_obj_ ))
                                                         )
                                  )
                                )
  )
  (setq p2_obj_start_end_pt_ (list
                                  (setq p2_obj_startpt_ (vlax-safearray->list
                                                             (vlax-variant-value ( vla-get-startpoint p2_obj_ ))
                                                           )
                                  )
                                  (setq p2_obj_endpt_ (vlax-safearray->list
                                                            (vlax-variant-value ( vla-get-endpoint p2_obj_ ))
                                                         )
                                  )
                                )
  )
  (command "line" p1_obj_startpt_ p2_obj_startpt_ "")
  (command "line" p1_obj_endpt_ p2_obj_endpt_ "")
)


(defun c:Asum_ ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;filler process
    (setq blk_ename_ (car (entsel "specify filter Object")))
    (setq blk_obj_ (vlax-ename->vla-object blk_ename_))
      (if 
        (and
          (= (vla-get-objectname blk_obj_) "AcDbBlockReference")
          (= (vla-get-hasattributes blk_obj_) :vlax-true)
          
        )
        (progn
          (setq blk_filter_ (LM:vl-getattributevalue blk_obj_ "PART_NAME_") )
        )
      )
  ;
  
  
  (initget "Yes No")
  (setq ss_ ;Detect the variable's result in case of a function error
    (vl-catch-all-apply 
      (function 
        (lambda () 
          (setq DELETE_OBJ_ (not (eq "No" (getkword "\nKeep Existing point with object? [Yes/No] <Y>: "))))
        )
      )
    )
  )
  (if (or (= ss_ nil) (= (vl-prin1-to-string ss_) "#<%catch-all-apply-error%>")  )
    (progn
      (setq input_sc_ (cond ( (getint (strcat "\nspecify get block scale \n<" (rtos (setq input_sc_ (cond (input_sc_) (1.0) ) ) ) "> : " ) ) ) (input_sc_) ) )
      (setq user_input_inspt_ (getpoint "specify point for insertion data list "))
        (command "insert" "000 - DAYNAMIC_DATA_FAMELINE_SUMMARY_LIST" user_input_inspt_ input_sc_ 0)
        (setq new_blk_ename1_ (entlast))
        (setq new_blk_obj1_ (vlax-ename->vla-object new_blk_ename1_))
        (LM:setdynpropvalue new_blk_obj1_ "visibility1" "head_only" )
    )
    (setq user_input_inspt_ 
                                    (list 
                                      (car user_input_inspt_)
                                      (- (cadr user_input_inspt_) (* input_sc_ 5))
                                      (caddr user_input_inspt_)
                                    )
            )
  )
  
  
  
 
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      
      
      (if (= (setq part_name_ (LM:vl-getattributevalue ss_pre_filter_set_xx_obj_ "PART_NAME_")) blk_filter_  )
        (progn
          ;getdata_
            (if 
              (and
                (/= (LM:getdynpropvalue ss_pre_filter_set_xx_obj_ "H") nil)
                (/= (setq LENGTH_VAL (/ (LM:getdynpropvalue ss_pre_filter_set_xx_obj_ "H") 1000 ) ) nil )
              )
              (progn 
                (setq TL_ TL_)
                (setq UNIT "m.")
                (setq LENGTH_VAL (RTOS LENGTH_VAL 2 2))
              )
              (setq TL_  ""
                    UNIT "pc."
                    LENGTH_VAL ""
              )
            )
            (setq QTY_ "1")
            (setq SET_VAL "")
            (setq TOTAL_VALUE "")
          
            (command "insert" "000 - DAYNAMIC_DATA_FAMELINE_SUMMARY_LIST" user_input_inspt_ input_sc_ 0)
            (setq new_blk_ename_ (entlast))
            (setq new_blk_obj_ (vlax-ename->vla-object new_blk_ename_))
              (LM:vl-setattributevalue new_blk_obj_ "PART_NAME_" part_name_ )
              (LM:vl-setattributevalue new_blk_obj_ "QTY_VAL" QTY_ )
              (LM:vl-setattributevalue new_blk_obj_ "LENGTH_VAL" (RTOS LENGTH_VAL 2 2) )
              (LM:vl-setattributevalue new_blk_obj_ "UNIT_VALUE" UNIT )
              (LM:vl-setattributevalue new_blk_obj_ "SET_VALUE" SET_VAL )
              (LM:vl-setattributevalue new_blk_obj_ "TOTAL_VALUE" TOTAL_VALUE )

            (setq user_input_inspt_ 
                                    (list 
                                      (car user_input_inspt_)
                                      (- (cadr user_input_inspt_) (* input_sc_ 5))
                                      (caddr user_input_inspt_)
                                    )
            )
          
          
          
        )
      )
      
      (setq ss_pre_filter_set_xx_i (+ ss_pre_filter_set_xx_i 1))
    )
  ;
)

(defun c:sumset_ ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;get_data_process_for_fillter_blk_name
    (setq ss_pre_filter_set_xx_ (TA:EF_Filter_ss_set_ ss_pre_filter_set_xx_ "000 - DAYNAMIC_DATA_FAMELINE_SUMMARY_LIST" ))
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (if 
        (and
          (= 1 1)
          ; (/= (LM:getdynpropvalue ss_pre_filter_set_xx_obj_ "visibility1" ) "SHOW_HEAD_TABLE" )
        )
        (progn
          (cond
            (;UNIT_case_1
               (and
                  (= (LM:vl-getattributevalue ss_pre_filter_set_xx_obj_ "UNIT_VALUE") "pc.")
               )
               (progn
                (LM:vl-setattributevalue ss_pre_filter_set_xx_obj_ "TOTAL_VALUE"
                  (strcat 
                    (rtos 
                      (LM:vl-setattributevalue ss_pre_filter_set_xx_obj_ "TOTAL_VALUE"
                        (* 
                          (atoi (LM:vl-getattributevalue ss_pre_filter_set_xx_obj_ "QTY_VAL" ) ) 
                          (atoi (LM:vl-getattributevalue ss_pre_filter_set_xx_obj_ "SET_VALUE" ) ) 
                        )
                      )
                      2 0
                    )
                    " pc."
                  )
                )
                 (princ "UNIT_case_1")
               )
            )
            (;UNIT_case_2
               (and
                  (= (LM:vl-getattributevalue ss_pre_filter_set_xx_obj_ "UNIT_VALUE") "m.")
               )
               (progn
                  (LM:vl-setattributevalue ss_pre_filter_set_xx_obj_ "TOTAL_VALUE"
                    (strcat 
                      (rtos 
                        (LM:vl-setattributevalue ss_pre_filter_set_xx_obj_ "TOTAL_VALUE"
                          (* 
                            (atoi (LM:vl-getattributevalue ss_pre_filter_set_xx_obj_ "QTY_VAL" ) ) 
                            (atof (LM:vl-getattributevalue ss_pre_filter_set_xx_obj_ "LENGTH_VAL" ) ) 
                          )
                        )
                        2 2
                      )
                      " m."
                    )
                  )
                 (princ "UNIT_case_2")
               )
            )

          )
          
        )
      )
      (setq ss_pre_filter_set_xx_i (+ ss_pre_filter_set_xx_i 1))
    )
  ;
)



;PURPLE_LINE_
  (defun c:insertion_AL_Ceiling_300SK_skins_ ()
    
    ;selection_set_for_fillter_blk_name
      (if  ;pre_select_ssget_or_post_select_ssget
        (=
          (setq ss_pre_filter_set_xx_ (ssget "i"
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget 
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (setq ss_pre_filter_set_xx_ii 1)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        
          ;insertion_by_center_recline
          (setq ss_pre_filter_set_xx_ename_ (ssname ss_pre_filter_set_xx_ ss_pre_filter_set_xx_i))
          (setq ss_pre_filter_set_xx_ename_centroid_ (LM:PolyCentroid ss_pre_filter_set_xx_ename_ ))
          (setq Bo_line_ (TA:Find_boundary_line_ ss_pre_filter_set_xx_ename_ ))
          (setq dist_x
                (distance 
                  (car Bo_line_)
                  (list (car (cadr bo_line_)) (cadr (car bo_line_)))
                )
          )
          (setq dist_y
                (distance 
                  
                  (list (car (cadr bo_line_)) (cadr (car bo_line_)))
                  (cadr Bo_line_)
                )
          )
          ; (TA:set-block-blockscaling "000 - FAMELINE_AL.CELING_300SK_TOP_VIEW" acUniform)
          (TA:vla-insertblock "000 - FAMELINE_AL.CELING_300SK_TOP_VIEW"  ss_pre_filter_set_xx_ename_centroid_ 1 0)
          
          
          (setq new_dynamic_blk_ (entlast))
          (setq new_dynamic_blk_obj_ (vlax-ename->vla-object new_dynamic_blk_))
          (LM:setdynpropvalue new_dynamic_blk_obj_ "ALL_X" dist_x )
          (LM:setdynpropvalue new_dynamic_blk_obj_ "ALL_Y" dist_y)

          (vla-delete ss_pre_filter_set_xx_obj_ ) 

        ;screen process
          (setq percent (fix (* (/ (float ss_pre_filter_set_xx_i) (sslength ss_pre_filter_set_xx_)) 100)))  
          ; (princ 
          ;   (strcat "tranfering " (rtos ss_pre_filter_set_xx_i 2 0) "/" (rtos (sslength ss_pre_filter_set_xx_) 2 0)  " (" (rtos percent 2 0) "%" ")" "\n")
          ; ) 
          (cond
            (;_case_1
              (and
                (= ss_pre_filter_set_xx_ii 1)
              )
              (progn
                (princ 
                  (strcat "tranfering " (rtos ss_pre_filter_set_xx_i 2 0) "/" (rtos (sslength ss_pre_filter_set_xx_) 2 0) " (" (rtos percent 2 0) "%" ")" "] \n" )
                )
              )
            )
            (;_case_1
              (and
                (= ss_pre_filter_set_xx_ii 2)
              )
              (progn
                (princ 
                  (strcat "tranfering " (rtos ss_pre_filter_set_xx_i 2 0) "/" (rtos (sslength ss_pre_filter_set_xx_) 2 0) " (" (rtos percent 2 0) "%" ")" "]] \n " )
                )
              )
            )
            (;_case_1
              (and
                (= ss_pre_filter_set_xx_ii 3)
              )
              (progn
                (princ 
                  (strcat "tranfering " (rtos ss_pre_filter_set_xx_i 2 0) "/" (rtos (sslength ss_pre_filter_set_xx_) 2 0) " (" (rtos percent 2 0) "%" ")" "]]] \n " )
                )
              )
            )
            (;_case_1
              (and
                (= ss_pre_filter_set_xx_ii 4)
              )
              (progn
                (princ 
                  (strcat "tranfering " (rtos ss_pre_filter_set_xx_i 2 0) "/" (rtos (sslength ss_pre_filter_set_xx_) 2 0) " (" (rtos percent 2 0) "%" ")" "]]]] \n " )
                )
              )
            )
            (;_case_1
              (and
                (= ss_pre_filter_set_xx_ii 5)
              )
              (progn
                (princ 
                  (strcat "tranfering " (rtos ss_pre_filter_set_xx_i 2 0) "/" (rtos (sslength ss_pre_filter_set_xx_) 2 0) " (" (rtos percent 2 0) "%" ")" "]]]]] \n " )
                )
              )
            )
            (;_case_1
              (and
                (= ss_pre_filter_set_xx_ii 6)
              )
              (progn
                (princ 
                  (strcat "tranfering " (rtos ss_pre_filter_set_xx_i 2 0) "/" (rtos (sslength ss_pre_filter_set_xx_) 2 0) " (" (rtos percent 2 0) "%" ")" "]]]]]] \n " )
                )
              )
            )
            (;_case_1
              (and
                (= ss_pre_filter_set_xx_ii 7)
              )
              (progn
                (princ 
                  (strcat "tranfering " (rtos ss_pre_filter_set_xx_i 2 0) "/" (rtos (sslength ss_pre_filter_set_xx_) 2 0) " (" (rtos percent 2 0) "%" ")" "]]]]]]] \n " )
                )
              )
            )
            (;_case_1
              (and
                (= ss_pre_filter_set_xx_ii 8)
              )
              (progn
                (princ 
                  (strcat "tranfering " (rtos ss_pre_filter_set_xx_i 2 0) "/" (rtos (sslength ss_pre_filter_set_xx_) 2 0) " (" (rtos percent 2 0) "%" ")" "]]]]]]]] \n " )
                )
              )
            )
            (;_case_1
              (and
                (= ss_pre_filter_set_xx_ii 9)
              )
              (progn
                (princ 
                  (strcat "tranfering " (rtos ss_pre_filter_set_xx_i 2 0) "/" (rtos (sslength ss_pre_filter_set_xx_) 2 0) " (" (rtos percent 2 0) "%" ")" "]]]]]]]]] \n " )
                )
              )
            )
            (;_case_1
              (and
                (= ss_pre_filter_set_xx_ii 10)
              )
              (progn
                (princ 
                  (strcat "tranfering " (rtos ss_pre_filter_set_xx_i 2 0) "/" (rtos (sslength ss_pre_filter_set_xx_) 2 0) " (" (rtos percent 2 0) "%" ")" "]]]]]]]]]] \n " )
                  
                )
              )
            )
            
            
            (;_case_1
              (and
                (= ss_pre_filter_set_xx_ii 20)
              )
              (progn
                (princ 
                  (strcat "tranfering " (rtos ss_pre_filter_set_xx_i 2 0) "/" (rtos (sslength ss_pre_filter_set_xx_) 2 0) " (" (rtos percent 2 0) "%" ")" "] \n" )
                )
                (setq ss_pre_filter_set_xx_ii 1)
              )
            )
            (;_case_1
              (and
                (= ss_pre_filter_set_xx_ii 19)
              )
              (progn
                (princ 
                  (strcat "tranfering " (rtos ss_pre_filter_set_xx_i 2 0) "/" (rtos (sslength ss_pre_filter_set_xx_) 2 0) " (" (rtos percent 2 0) "%" ")" "]] \n " )
                )
              )
            )
            (;_case_1
              (and
                (= ss_pre_filter_set_xx_ii 18)
              )
              (progn
                (princ 
                  (strcat "tranfering " (rtos ss_pre_filter_set_xx_i 2 0) "/" (rtos (sslength ss_pre_filter_set_xx_) 2 0) " (" (rtos percent 2 0) "%" ")" "]]] \n " )
                )
              )
            )
            (;_case_1
              (and
                (= ss_pre_filter_set_xx_ii 17)
              )
              (progn
                (princ 
                  (strcat "tranfering " (rtos ss_pre_filter_set_xx_i 2 0) "/" (rtos (sslength ss_pre_filter_set_xx_) 2 0) " (" (rtos percent 2 0) "%" ")" "]]]] \n " )
                )
              )
            )
            (;_case_1
              (and
                (= ss_pre_filter_set_xx_ii 16)
              )
              (progn
                (princ 
                  (strcat "tranfering " (rtos ss_pre_filter_set_xx_i 2 0) "/" (rtos (sslength ss_pre_filter_set_xx_) 2 0) " (" (rtos percent 2 0) "%" ")" "]]]]] \n " )
                )
              )
            )
            (;_case_1
              (and
                (= ss_pre_filter_set_xx_ii 15)
              )
              (progn
                (princ 
                  (strcat "tranfering " (rtos ss_pre_filter_set_xx_i 2 0) "/" (rtos (sslength ss_pre_filter_set_xx_) 2 0) " (" (rtos percent 2 0) "%" ")" "]]]]]] \n " )
                )
              )
            )
            (;_case_1
              (and
                (= ss_pre_filter_set_xx_ii 14)
              )
              (progn
                (princ 
                  (strcat "tranfering " (rtos ss_pre_filter_set_xx_i 2 0) "/" (rtos (sslength ss_pre_filter_set_xx_) 2 0) " (" (rtos percent 2 0) "%" ")" "]]]]]]] \n " )
                )
              )
            )
            (;_case_1
              (and
                (= ss_pre_filter_set_xx_ii 13)
              )
              (progn
                (princ 
                  (strcat "tranfering " (rtos ss_pre_filter_set_xx_i 2 0) "/" (rtos (sslength ss_pre_filter_set_xx_) 2 0) " (" (rtos percent 2 0) "%" ")" "]]]]]]]] \n " )
                )
              )
            )
            (;_case_1
              (and
                (= ss_pre_filter_set_xx_ii 12)
              )
              (progn
                (princ 
                  (strcat "tranfering " (rtos ss_pre_filter_set_xx_i 2 0) "/" (rtos (sslength ss_pre_filter_set_xx_) 2 0) " (" (rtos percent 2 0) "%" ")" "]]]]]]]]] \n " )
                )
              )
            )
            (;_case_1
              (and
                (= ss_pre_filter_set_xx_ii 11)
              )
              (progn
                (princ 
                  (strcat "tranfering " (rtos ss_pre_filter_set_xx_i 2 0) "/" (rtos (sslength ss_pre_filter_set_xx_) 2 0) " (" (rtos percent 2 0) "%" ")" "]]]]]]]]]] \n " )
                  
                )
              )
            )
            
          )
          
          (textscr)
        ; 
        
        (setq ss_pre_filter_set_xx_i (+ ss_pre_filter_set_xx_i 1))
        (setq ss_pre_filter_set_xx_ii (+ ss_pre_filter_set_xx_ii 1))
      )
    ;
  )
  (defun c:temp_ppline_start-end_insk1 ()
    (setq user_input_pt_ (getpoint "specify point "))
    (setq user_input_pt_new_ (List 
                          (+ (car user_input_pt_) 150)
                          (+ (cadr user_input_pt_) 75)
                        )
    )

    (command "insert" "000TYP-LINE_AND_ARRAY_@400mm._TYPE1_" user_input_pt_new_ 1 0 )
    (setq new_ename_ (entlast))
    (setq new_obj_ (vlax-ename->vla-object new_ename_))
    (LM:setdynpropvalue new_obj_ "lookup1" "AL-C300SK")
    (vla-put-color new_obj_ 3)
    
  )
  (defun c:temp_ppline_center_insk2 ()
    (setq user_input_pt_ (getpoint "specify point "))
    (command "insert" "000TYP-LINE_AND_ARRAY_@400mm._TYPE2_" user_input_pt_ 1 0 )
    (setq new_ename_ (entlast))
    (setq new_obj_ (vlax-ename->vla-object new_ename_))
    (LM:setdynpropvalue new_obj_ "lookup1" "AL-C300SK")
    (vla-put-color new_obj_ 3)
    
  )
  (defun c:temp_ppline_mk300sk ()
    ; (setq line_ename_ (car (entsel "specify Object")))
    ; (setq line_obj_ (vlax-ename->vla-object line_ename_))
    ; (setq line_obj_length (vla-get-length line_obj_))
    
    (setq user_input_pt_ (getpoint "specify point "))
    (setq user_input_pt_1 (list 
                          (+ (car user_input_pt_) 150)
                          (cadr user_input_pt_)
                          (caddr user_input_pt_)
                        )
    )
    ; (setq H (- (* 2 (getdist user_input_pt_ )) 150))
    (setq H (- (* 2 (distance user_input_pt_ (list (car user_input_pt_) (cadr (getpoint "specify point length")) ) ) ) 150 ) )
    (setq array_length_ (getdist user_input_pt_ ))
    (setvar "osmode" 0)
    (command "insert" "000TYP-LINE_AND_ARRAY_@400mm._TYPE2_" user_input_pt_1 1 0 )
    (setq new_ename_ (entlast))
    (setq new_obj_ (vlax-ename->vla-object new_ename_))
    (LM:setdynpropvalue new_obj_ "lookup1" "AL-C300SK")
    (LM:setdynpropvalue new_obj_ "h" H   )
    (LM:setdynpropvalue new_obj_ "array_width" (+ 400 array_length_) )
    (setvar "osmode" 1215)
    
    (vla-put-color new_obj_ 3)
    
    
    
    
  )
  (defun c:temp_ppline_mk400sk ()
    (setq user_input_pt_ (getpoint "specify point "))
    (setq user_input_pt_new_ (List 
                          (+ (car user_input_pt_) 150)
                          (+ (cadr user_input_pt_) 75)
                        )
    )
    ; (setq H (- (getdist user_input_pt_new_ ) 100))
    (setq H (- (distance user_input_pt_ (list (car user_input_pt_) (cadr (getpoint "specify point length")) ) ) 150 ) )
    (setq array_length_ (getdist user_input_pt_ ))
    (setvar "osmode" 0)
    (command "insert" "000TYP-LINE_AND_ARRAY_@400mm._TYPE1_" user_input_pt_new_ 1 0 )
    (setq new_ename_ (entlast))
    (setq new_obj_ (vlax-ename->vla-object new_ename_))
    (LM:setdynpropvalue new_obj_ "lookup1" "AL-C300SK")
    (LM:setdynpropvalue new_obj_ "h" H   )
    (LM:setdynpropvalue new_obj_ "array_width" (+ 400 array_length_) )
    (setvar "osmode" 1215)
    
    (vla-put-color new_obj_ 3)
    
  )
  (defun c:temp_ppline_mk500sk ()
    (setq user_input_pt_ (getpoint "specify point "))
    (setq user_input_pt_new_ (List 
                          (+ (car user_input_pt_) 150)
                          (- (cadr user_input_pt_) 75)
                        )
    )
    ; (setq H (- (getdist user_input_pt_new_ ) 100))
    (setq H (- (distance user_input_pt_ (list (car user_input_pt_) (cadr (getpoint "specify point length")) ) ) 150 ) )
    (setq array_length_ (getdist user_input_pt_new_ ))
    (setvar "osmode" 0)
    (command "insert" "000TYP-LINE_AND_ARRAY_@400mm._TYPE1_" user_input_pt_new_ 1 0 )
    (setq new_ename_ (entlast))
    (setq new_obj_ (vlax-ename->vla-object new_ename_))
    (LM:setdynpropvalue new_obj_ "lookup1" "AL-C300SK")
    (LM:setdynpropvalue new_obj_ "Flip state1" 1)
    (LM:setdynpropvalue new_obj_ "h" H   )
    (LM:setdynpropvalue new_obj_ "array_width" (+ 400 array_length_) )
    (setvar "osmode" 1215)
    
    (vla-put-color new_obj_ 3)
    
  )
  (defun c:temp_ppline_convert_dynamic_side_condyn ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget 
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
      (setq ss_pre_filter_set_xx_ (TA:EF_Filter_ss_set_ ss_pre_filter_set_xx_ "000 - FAMELINE_AL.CELING_300SK_TOP_VIEW"))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (setq get_dyn_all_x (LM:getdynpropvalue ss_pre_filter_set_xx_obj_ "all_x"))
        (setq get_dyn_all_y (rtos (LM:getdynpropvalue ss_pre_filter_set_xx_obj_ "all_y") 2 0))
        ;input back_
          (if (= get_dyn_all_y "300")
            (progn
              (vla-put-rotation ss_pre_filter_set_xx_obj_ (deg-to-rad 90))
              (LM:setdynpropvalue ss_pre_filter_set_xx_obj_ "all_y" get_dyn_all_x)
              (LM:setdynpropvalue ss_pre_filter_set_xx_obj_ "all_x" get_dyn_all_y)
            )
          )
          
        ;
        ;screen process
        (setq percent (fix (* (/ (float ss_pre_filter_set_xx_i) (sslength ss_pre_filter_set_xx_)) 100)))  
        (princ (strcat "tranfering " (rtos ss_pre_filter_set_xx_i 2 0) "/" (rtos (sslength ss_pre_filter_set_xx_) 2 0)  " (" (rtos percent 2 0) "%" ")" "\n"))
        (textscr)
        (setq ss_pre_filter_set_xx_i (+ ss_pre_filter_set_xx_i 1))
      )
    ;
  )
  (defun c:temp_ppline_getalllength_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget 
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ;
        (setq ss_pre_filter_set_xx_ (TA:EF_Filter_ss_set_ ss_pre_filter_set_xx_ "000 - FAMELINE_AL.CELING_300SK_TOP_VIEW"))
      ;
    ;
    ;preloop_and_while
      (setq ss_pre_filter_set_xx_i 0)
      (setq sum_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        
        (setq get_dyn_all_y (rtos (LM:getdynpropvalue ss_pre_filter_set_xx_obj_ "all_y") 2 2))
        (setq sum_ (cons get_dyn_all_y sum_))
        ;screen process
          (setq percent (fix (* (/ (float ss_pre_filter_set_xx_i) (sslength ss_pre_filter_set_xx_)) 100)))  
          (princ (strcat "tranfering " (rtos ss_pre_filter_set_xx_i 2 0) "/" (rtos (sslength ss_pre_filter_set_xx_) 2 0)  " (" (rtos percent 2 0) "%" ")" "\n"))
          (textscr)
        ; 
          ; (princ)
        (setq ss_pre_filter_set_xx_i (+ ss_pre_filter_set_xx_i 1))
      )
    ;
    ;TA:stanndard_lambda_sorting
      (setq sum_sorted_ (vl-sort sum_  ;bigest open indent list
                                (function 
                                  (lambda (a b) 
                                    (< a b)
                                  )
                                )
                        ) ;bigest close indent list
      )
    ;
    
    (princ (TA:Count_item_in_list_ sum_sorted_ ))
    (princ (setq sum_length_all_ (LM:CountItems sum_sorted_ )))
      (if (= vla-obj_app nil)
      (progn
        (setq vla-obj_app (vlax-get-or-create-object "Excel.Application"))
        
      )
    )
    (setq Excel_obj_ (TA:New_Excel_File_NEX_ vla-obj_app ))
    ;preloop_and_while
      (setq sum_length_all_i 0)
      (setq row_i 3)
      (while (< sum_length_all_i (length sum_length_all_))
        (setq sum_length_all_main_ (car (nth  sum_length_all_i sum_length_all_)))
        (setq sum_length_all_sub_ (cdr (nth  sum_length_all_i sum_length_all_)))

        (setq Excel_entlast_ (caddr (car (nth 3 (car (reverse (TA:Excel_Assembly_ALL-obj_list_ Excel_obj_ )))))))
        
        (TA:Excel_input_data_R1C1 Excel_entlast_ row_i 1 "AL.300SK" )
        (TA:Excel_input_data_R1C1 Excel_entlast_ row_i 2 sum_length_all_main_ )
        (TA:Excel_input_data_R1C1 Excel_entlast_ row_i 3 sum_length_all_sub_ )
        
        (setq row_i (+ row_i 1))
        (setq sum_length_all_i (+ sum_length_all_i 1))
      )
      (TA:Excel_input_data_R1C1 Excel_entlast_ 2 1 "Matt." )
      (TA:Excel_input_data_R1C1 Excel_entlast_ 2 2 "legnth" )
      (TA:Excel_input_data_R1C1 Excel_entlast_ 2 3 "qty." )
      (TA:Excel_input_data_R1C1 Excel_entlast_ 1 1 (getvar "dwgname") )
        
    ;
    
  )
  (defun c:c+ ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq get_l (LM:getdynpropvalue sss_obj_ "array_width" ) )
                  (LM:setdynpropvalue sss_obj_ "array_width" (+ get_l 250) )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
            (setq ss_pre_filter_set_xx_ename_ (ssname ss_pre_filter_set_xx_ ss_pre_filter_set_xx_i ) )
            (setq sss_obj_ (vlax-ename->vla-object ss_pre_filter_set_xx_ename_))
            (setq get_l (LM:getdynpropvalue sss_obj_ "array_width"))
            (LM:setdynpropvalue sss_obj_ "array_width" (+ get_l 250))
            (setq ss_pre_filter_set_xx_i (+ ss_pre_filter_set_xx_i 1))
          )
        )
        
      )
    ;

  )
  (defun c:c- ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq get_l (LM:getdynpropvalue sss_obj_ "array_width" ) )
                  (LM:setdynpropvalue sss_obj_ "array_width" (- get_l 250) )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
            (setq ss_pre_filter_set_xx_ename_ (ssname ss_pre_filter_set_xx_ ss_pre_filter_set_xx_i ) )
            (setq sss_obj_ (vlax-ename->vla-object ss_pre_filter_set_xx_ename_))
            (setq get_l (LM:getdynpropvalue sss_obj_ "array_width"))
            (LM:setdynpropvalue sss_obj_ "array_width" (- get_l 250))
            (setq ss_pre_filter_set_xx_i (+ ss_pre_filter_set_xx_i 1))
          )
        )
        
      )
    ;

  )
  (defun c:y+ ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (car sss_obj_ins_)
                                          (+ (cadr sss_obj_ins_) move_length_) 
                                          (caddr sss_obj_ins_)
                                        ) 
                  )
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (car sss_obj_ins_)
                                          (+ (cadr sss_obj_ins_) move_length_) 
                                          (caddr sss_obj_ins_)
                                        ) 
                  )
                  (vla-put-insertionpoint sss_obj_ (vlax-3d-point sss_obj_putins_))
              (setq ss_pre_filter_set_xx_i (+ ss_pre_filter_set_xx_i 1))
            )
        )
        
      )
    ;

  )
  (defun c:y- ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (car sss_obj_ins_)
                                          (- (cadr sss_obj_ins_) move_length_) 
                                          (caddr sss_obj_ins_)
                                        ) 
                  )
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (car sss_obj_ins_)
                                          (- (cadr sss_obj_ins_) move__length_) 
                                          (caddr sss_obj_ins_)
                                        ) 
                  )
                  (vla-put-insertionpoint sss_obj_ (vlax-3d-point sss_obj_putins_))
              (setq ss_pre_filter_set_xx_i (+ ss_pre_filter_set_xx_i 1))
            )
        )
        
      )
    ;

  )
  (defun c:px+ ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "x" (- move_length_ ) )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "x" (- move_length_ ) )
              (setq ss_pre_filter_set_xx_i (+ ss_pre_filter_set_xx_i 1))
            )
        )
        
      )
    ;

  )
  (defun c:px- ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "x" move_length_ )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "x" move_length_ )
              (setq ss_pre_filter_set_xx_i (+ ss_pre_filter_set_xx_i 1))
            )
        )
        
      )
    ;

  )
  (defun c:py+ ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "Y" (- move_length_ ) )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "Y" (- move_length_ ) )
              (setq ss_pre_filter_set_xx_i (+ ss_pre_filter_set_xx_i 1))
            )
        )
        
      )
    ;

  )
  (defun c:py- ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "Y" move_length_ )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (TA:move_polar_insertionpoint sss_obj_ "Y" move_length_ )
              (setq ss_pre_filter_set_xx_i (+ ss_pre_filter_set_xx_i 1))
            )
        )
        
      )
    ;

  )
  (defun c:yc+ ()
    ;for moving support frame Fameline celing SK300 (0.025 / 1 enter)
    ;set paremeter for moving
      (setq move_length_ 1300)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (car sss_obj_ins_)
                                          (+ (cadr sss_obj_ins_) move_length_) 
                                          (caddr sss_obj_ins_)
                                        ) 
                  )
                  (vla-copy sss_obj_)
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (car sss_obj_ins_)
                                          (+ (cadr sss_obj_ins_) move_length_) 
                                          (caddr sss_obj_ins_)
                                        ) 
                  )
                  (vla-copy sss_obj_)
                  (vla-put-insertionpoint sss_obj_ (vlax-3d-point sss_obj_putins_))
              (setq ss_pre_filter_set_xx_i (+ ss_pre_filter_set_xx_i 1))
            )
        )
        
      )
    ;

  )
  (defun c:mox ()
    (_startundo doc)
    ;selection_set_for_fillter_blk_name
      (if  ;pre_select_ssget_or_post_select_ssget
        (=
          (setq ss_selection_ (ssget "i"
                                            (list 
                                  (cons 0 "INSERT") ;type of object
                                  ; (cons 8 "000 - GRID,001 - ASCESSORIES") ;kind of layer
                                  ; (cons 2 "000-GRID_LINE_DYN")       ;kind of nameblock
                                  ; (cons 62 1)           ;kind of color call sign with color code index
                                )
                                      )
          )
          nil
        )
        (progn
          (setq ss_selection_ (ssget 
                                (list 
                                  (cons 0 "INSERT") ;type of object
                                  ; (cons 8 "000 - GRID,001 - ASCESSORIES") ;kind of layer
                                  ; (cons 2 "000-GRID_LINE_DYN")       ;kind of nameblock
                                  ; (cons 62 1)           ;kind of color call sign with color code index
                                )
                              )
          )
        )
        (sslength ss_selection_)
      )
    ;
    (setq ERR_ nil)
    (setq temp_increment_num_ 0)
    (setq temp_increment_num_ 0)
    (if (= increment_num_ nil)
      (progn
        (setq increment_num_ 0)
      )
    )
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos (setq temp_increment_num_ (+ temp_increment_num_ increment_num_)) 2 2) " <" (rtos (setq increment_num_ (cond (increment_num_) (1.0) ) ) ) "> : " ) ) ) (increment_num_) ) )
            )
          )
        )
      )
      ;preloop_and_while
        (setq ss_selection_i 0)
        (while 
          (and
            (= (vl-catch-all-error-p ERR_) nil)
            (< ss_selection_i (sslength ss_selection_))
          )
          (setq ss_selection_ename_ (ssname ss_selection_ ss_selection_i)) 
          (setq ss_selection_obj_ (vlax-ename->vla-object  ss_selection_ename_))
          (setq ss_selection_obj_rotation_ (vla-get-rotation  ss_selection_obj_))
          (setq ss_selection_obj_ins_ (vlax-safearray->list (vlax-variant-value (vla-get-insertionpoint ss_selection_obj_))))
          
          (cond
            (;ssss_case_1
              (and
                  (= (vl-catch-all-error-p ERR_) nil)
                  (< increment_num_ 0)
              )
              (progn
                (TA:move_axis_insertionpoint ss_selection_obj_ "x" increment_num_)
                (princ "ssss_case_1")
              )
            )
            (;ssss_case_2
              (and
                  (= (vl-catch-all-error-p ERR_) nil)
                  (> increment_num_ 0)
              )
              (progn
                (TA:move_axis_insertionpoint ss_selection_obj_ "x" increment_num_)
                (princ "ssss_case_2")
              )
            )
          )
          
          
          (setq ss_selection_i (+ ss_selection_i 1))
        )
      ;
    )
    (_endundo doc)
  )
  (defun c:pox ()
    (_startundo doc)
    ;selection_set_for_fillter_blk_name
      (if  ;pre_select_ssget_or_post_select_ssget
        (=
          (setq ss_selection_ (ssget "i"
                                            (list 
                                  (cons 0 "INSERT") ;type of object
                                  ; (cons 8 "000 - GRID,001 - ASCESSORIES") ;kind of layer
                                  ; (cons 2 "000-GRID_LINE_DYN")       ;kind of nameblock
                                  ; (cons 62 1)           ;kind of color call sign with color code index
                                )
                                      )
          )
          nil
        )
        (progn
          (setq ss_selection_ (ssget 
                                (list 
                                  (cons 0 "INSERT") ;type of object
                                  ; (cons 8 "000 - GRID,001 - ASCESSORIES") ;kind of layer
                                  ; (cons 2 "000-GRID_LINE_DYN")       ;kind of nameblock
                                  ; (cons 62 1)           ;kind of color call sign with color code index
                                )
                              )
          )
        )
        (sslength ss_selection_)
      )
    ;
    (setq ERR_ nil)
    (setq temp_increment_num_ 0)
    (setq temp_increment_num_ 0)
    (if (= increment_num_ nil)
      (progn
        (setq increment_num_ 0)
      )
    )
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos (setq temp_increment_num_ (+ temp_increment_num_ increment_num_)) 2 2) " <" (rtos (setq increment_num_ (cond (increment_num_) (1.0) ) ) ) "> : " ) ) ) (increment_num_) ) )
            )
          )
        )
      )
      ;preloop_and_while
        (setq ss_selection_i 0)
        (while 
          (and
            (= (vl-catch-all-error-p ERR_) nil)
            (< ss_selection_i (sslength ss_selection_))
          )
          (setq ss_selection_ename_ (ssname ss_selection_ ss_selection_i)) 
          (setq ss_selection_obj_ (vlax-ename->vla-object  ss_selection_ename_))
          (setq ss_selection_obj_rotation_ (vla-get-rotation  ss_selection_obj_))
          (setq ss_selection_obj_ins_ (vlax-safearray->list (vlax-variant-value (vla-get-insertionpoint ss_selection_obj_))))
          
          (cond
            (;ssss_case_1
              (and
                  (= (vl-catch-all-error-p ERR_) nil)
                  (< increment_num_ 0)
              )
              (progn
                (TA:move_polar_insertionpoint ss_selection_obj_ "x" increment_num_)
                (princ "ssss_case_1")
              )
            )
            (;ssss_case_2
              (and
                  (= (vl-catch-all-error-p ERR_) nil)
                  (> increment_num_ 0)
              )
              (progn
                (TA:move_polar_insertionpoint ss_selection_obj_ "x" increment_num_)
                (princ "ssss_case_2")
              )
            )
          )
          
          
          (setq ss_selection_i (+ ss_selection_i 1))
        )
      ;
    )
    (_endundo doc)
  )
  (defun c:poY ()
    (_startundo doc)
    ;selection_set_for_fillter_blk_name
      (if  ;pre_select_ssget_or_post_select_ssget
        (=
          (setq ss_selection_ (ssget "i"
                                            (list 
                                  (cons 0 "INSERT") ;type of object
                                  ; (cons 8 "000 - GRID,001 - ASCESSORIES") ;kind of layer
                                  ; (cons 2 "000-GRID_LINE_DYN")       ;kind of nameblock
                                  ; (cons 62 1)           ;kind of color call sign with color code index
                                )
                                      )
          )
          nil
        )
        (progn
          (setq ss_selection_ (ssget 
                                (list 
                                  (cons 0 "INSERT") ;type of object
                                  ; (cons 8 "000 - GRID,001 - ASCESSORIES") ;kind of layer
                                  ; (cons 2 "000-GRID_LINE_DYN")       ;kind of nameblock
                                  ; (cons 62 1)           ;kind of color call sign with color code index
                                )
                              )
          )
        )
        (sslength ss_selection_)
      )
    ;
    (setq ERR_ nil)
    (setq temp_increment_num_ 0)
    (setq temp_increment_num_ 0)
    (if (= increment_num_ nil)
      (progn
        (setq increment_num_ 0)
      )
    )
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos (setq temp_increment_num_ (+ temp_increment_num_ increment_num_)) 2 2) " <" (rtos (setq increment_num_ (cond (increment_num_) (1.0) ) ) ) "> : " ) ) ) (increment_num_) ) )
            )
          )
        )
      )
      ;preloop_and_while
        (setq ss_selection_i 0)
        (while 
          (and
            (= (vl-catch-all-error-p ERR_) nil)
            (< ss_selection_i (sslength ss_selection_))
          )
          (setq ss_selection_ename_ (ssname ss_selection_ ss_selection_i)) 
          (setq ss_selection_obj_ (vlax-ename->vla-object  ss_selection_ename_))
          (setq ss_selection_obj_rotation_ (vla-get-rotation  ss_selection_obj_))
          (setq ss_selection_obj_ins_ (vlax-safearray->list (vlax-variant-value (vla-get-insertionpoint ss_selection_obj_))))
          
          (cond
            (;ssss_case_1
              (and
                  (= (vl-catch-all-error-p ERR_) nil)
                  (< increment_num_ 0)
              )
              (progn
                (TA:move_polar_insertionpoint ss_selection_obj_ "Y" increment_num_)
                (princ "ssss_case_1")
              )
            )
            (;ssss_case_2
              (and
                  (= (vl-catch-all-error-p ERR_) nil)
                  (> increment_num_ 0)
              )
              (progn
                (TA:move_polar_insertionpoint ss_selection_obj_ "Y" increment_num_)
                (princ "ssss_case_2")
              )
            )
          )
          
          
          (setq ss_selection_i (+ ss_selection_i 1))
        )
      ;
    )
    (_endundo doc)
  )
  (defun c:move_line_lix_ ()
    ;selection_set_for_fillter_blk_name
      (if  ;pre_select_ssget_or_post_select_ssget
        (=
          (setq ss_selection_ (ssget "i"
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_selection_ (ssget
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
        )
        (sslength ss_selection_)
      )
    ;
    (setq ERR_ nil)
    (setq temp_increment_num_ 0)
    (if (= increment_num_ nil) (progn (setq increment_num_ 0) ) )
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos (setq temp_increment_num_ (+ temp_increment_num_ increment_num_)) 2 2) " <" (rtos (setq increment_num_ (cond (increment_num_) (1.0) ) ) ) "> : " ) ) ) (increment_num_) ) )
            )
          )
        )
      )
      ;preloop_and_while
        (setq ss_selection_i 0)
        (while 
            (and
              (= (vl-catch-all-error-p ERR_) nil)
              (< ss_selection_i (sslength ss_selection_))
            )
            (setq ss_selection_ename_ (ssname ss_selection_ ss_selection_i)) 
            (setq ss_selection_obj_ (vlax-ename->vla-object  ss_selection_ename_))
            (setq ss_selection_obj_start_end_pt_ (list 
                                                   (setq ss_selection_obj_startpt_ (vlax-safearray->list ( vlax-variant-value ( vla-get-startpoint ss_selection_obj_ ) ) ) )
                                                   (setq ss_selection_obj_endpt_ (vlax-safearray->list (vlax-variant-value ( vla-get-endpoint ss_selection_obj_ ) ) ) )
                                                 )
            )
            (cond
              (;ssss_case_1
                (and
                    (= (vl-catch-all-error-p ERR_) nil)
                    (< increment_num_ 0)
                )
                (progn
                  (vla-put-startpoint ss_selection_obj_ (vlax-3d-point 
                                                          (- (car ss_selection_obj_startpt_) (- increment_num_))
                                                          (- (cadr ss_selection_obj_startpt_) 0)
                                                          (caddr ss_selection_obj_startpt_)
                                                        )
                  )
                  (vla-put-endpoint ss_selection_obj_ (vlax-3d-point 
                                                          (- (car ss_selection_obj_endpt_) (- increment_num_))
                                                          (- (cadr ss_selection_obj_endpt_) 0)
                                                          (caddr ss_selection_obj_endpt_)
                                                        )
                  )
                  (princ "ssss_case_1")
                )
              )
              (;ssss_case_2
                (and
                    (= (vl-catch-all-error-p ERR_) nil)
                    (> increment_num_ 0)
                )
                (progn
                  (vla-put-startpoint ss_selection_obj_ (vlax-3d-point 
                                                          (+ (car ss_selection_obj_startpt_) increment_num_)
                                                          (+ (cadr ss_selection_obj_startpt_) 0)
                                                          (caddr ss_selection_obj_startpt_)
                                                        )
                  )
                  (vla-put-endpoint ss_selection_obj_ (vlax-3d-point 
                                                          (+ (car ss_selection_obj_endpt_) increment_num_)
                                                          (+ (cadr ss_selection_obj_endpt_) 0)
                                                          (caddr ss_selection_obj_endpt_)
                                                        )
                  )
                  (princ "ssss_case_2")
                )
              )
            )
            (setq ss_selection_i (+ ss_selection_i 1))
          )
      ;
    )
  )
  (defun c:move_line_liy_ ()
    ;selection_set_for_fillter_blk_name
      (if  ;pre_select_ssget_or_post_select_ssget
        (=
          (setq ss_selection_ (ssget "i"
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_selection_ (ssget
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
        )
        (sslength ss_selection_)
      )
    ;
    (setq ERR_ nil)
    (setq temp_increment_num_ 0)
    (if (= increment_num_ nil) (progn (setq increment_num_ 0) ) )
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos (setq temp_increment_num_ (+ temp_increment_num_ increment_num_)) 2 2) " <" (rtos (setq increment_num_ (cond (increment_num_) (1.0) ) ) ) "> : " ) ) ) (increment_num_) ) )
            )
          )
        )
      )
      ;preloop_and_while
        (setq ss_selection_i 0)
        (while 
            (and
              (= (vl-catch-all-error-p ERR_) nil)
              (< ss_selection_i (sslength ss_selection_))
            )
            (setq ss_selection_ename_ (ssname ss_selection_ ss_selection_i)) 
            (setq ss_selection_obj_ (vlax-ename->vla-object  ss_selection_ename_))
            (setq ss_selection_obj_start_end_pt_ (list 
                                                   (setq ss_selection_obj_startpt_ (vlax-safearray->list ( vlax-variant-value ( vla-get-startpoint ss_selection_obj_ ) ) ) )
                                                   (setq ss_selection_obj_endpt_ (vlax-safearray->list (vlax-variant-value ( vla-get-endpoint ss_selection_obj_ ) ) ) )
                                                 )
            )
            (cond
              (;ssss_case_1
                (and
                    (= (vl-catch-all-error-p ERR_) nil)
                    (< increment_num_ 0)
                )
                (progn
                  (vla-put-startpoint ss_selection_obj_ (vlax-3d-point 
                                                          (- (car ss_selection_obj_startpt_) 0)
                                                          (- (cadr ss_selection_obj_startpt_) (- increment_num_))
                                                          (caddr ss_selection_obj_startpt_)
                                                        )
                  )
                  (vla-put-endpoint ss_selection_obj_ (vlax-3d-point 
                                                          (- (car ss_selection_obj_endpt_) 0)
                                                          (- (cadr ss_selection_obj_endpt_) (- increment_num_))
                                                          (caddr ss_selection_obj_endpt_)
                                                        )
                  )
                  (princ "ssss_case_1")
                )
              )
              (;ssss_case_2
                (and
                    (= (vl-catch-all-error-p ERR_) nil)
                    (> increment_num_ 0)
                )
                (progn
                  (vla-put-startpoint ss_selection_obj_ (vlax-3d-point 
                                                          (+ (car ss_selection_obj_startpt_) 0)
                                                          (+ (cadr ss_selection_obj_startpt_) increment_num_)
                                                          (caddr ss_selection_obj_startpt_)
                                                        )
                  )
                  (vla-put-endpoint ss_selection_obj_ (vlax-3d-point 
                                                          (+ (car ss_selection_obj_endpt_) 0)
                                                          (+ (cadr ss_selection_obj_endpt_) increment_num_)
                                                          (caddr ss_selection_obj_endpt_)
                                                        )
                  )
                  (princ "ssss_case_2")
                )
              )
            )
            (setq ss_selection_i (+ ss_selection_i 1))
          )
      ;
    )
  )
  (defun c:temp_outer_move_omx ()
    
    (while
      (/=
        (vl-princ-to-string
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            (cons 0 "INSERT") ;type of object
                                                            (cons 8 "000 - GRID,001 - ASCESSORIES")   ;kind of layer
                                                            ; (cons 2 "000-GRID_LINE_DYN")       ;kind of nameblock
                                                            ; (cons 62 1)           ;kind of color call sign with color code index
                                                          ) 
                                                    )
                        )
                        nil
                      )
                      (progn
                        (setq ss_pre_filter_set_xx_ (ssget
                                                          (list
                                                            (cons 0 "INSERT") ;type of object
                                                            (cons 8 "000 - GRID,001 - ASCESSORIES")   ;kind of layer
                                                            ; (cons 2 "000-GRID_LINE_DYN")       ;kind of nameblock
                                                            ; (cons 62 1)           ;kind of color call sign with color code index
                                                          )
                                                    )
                        )
                      )
                      (sslength ss_pre_filter_set_xx_)
                    )
                    (setq ss_pre_filter_set_xx_ (TA:EF_Filter_ss_set_ ss_pre_filter_set_xx_ "000-GRID_LINE_DYN_V2-FOR-CC012"))
                    (setq ss_pre_filter_set_xx_ (TA:standard_list_croodinate_sorting ss_pre_filter_set_xx_ "X"))
                  ;
                )
              )
            )
          )
        )
        "#<%catch-all-apply-error%>"
      )
      (_StartUndo doc)
      (setq blank_ss_ (ssadd))
      (setq blk1_ename_ (car (nth 0 ss_pre_filter_set_xx_ )))
      (setq blk1_obj_ (vlax-ename->vla-object blk1_ename_))
      (setq blk1_obj_ins_ (vlax-safearray->list (vlax-variant-value (vla-get-insertionpoint blk1_obj_))))
      (setq blk1_obj_ro (vla-get-rotation blk1_obj_))
      (setq blk2_ename_ (car (nth 1 ss_pre_filter_set_xx_ )))
      (setq blk2_obj_ (vlax-ename->vla-object blk2_ename_))
      (setq blk2_obj_ins_ (vlax-safearray->list (vlax-variant-value (vla-get-insertionpoint blk2_obj_))))
      (TA:move_axis_insertionpoint blk1_obj_ "X" -50)
      (TA:move_axis_insertionpoint blk2_obj_ "X" 50)
      (vla-put-color blk1_obj_ 3)
      (vla-put-color blk2_obj_ 3)
      (command "pselect"  blank_ss_  "" )
      (_EndUndo doc)
    ) 
    
  )
  (defun c:temp_inner_move_imx ()
    (_StartUndo doc)
    (while
      (/=
        (vl-princ-to-string
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            (cons 0 "INSERT") ;type of object
                                                            (cons 8 "000 - GRID,001 - ASCESSORIES")   ;kind of layer
                                                            ; (cons 2 "000-GRID_LINE_DYN")       ;kind of nameblock
                                                            ; (cons 62 1)           ;kind of color call sign with color code index
                                                          ) 
                                                    )
                        )
                        nil
                      )
                      (progn
                        (setq ss_pre_filter_set_xx_ (ssget
                                                          (list
                                                            (cons 0 "INSERT") ;type of object
                                                            (cons 8 "000 - GRID,001 - ASCESSORIES")   ;kind of layer
                                                            ; (cons 2 "000-GRID_LINE_DYN")       ;kind of nameblock
                                                            ; (cons 62 1)           ;kind of color call sign with color code index
                                                          )
                                                    )
                        )
                      )
                      (sslength ss_pre_filter_set_xx_)
                    )
                    (setq ss_pre_filter_set_xx_ (TA:EF_Filter_ss_set_ ss_pre_filter_set_xx_ "000-GRID_LINE_DYN_V2-FOR-CC012"))
                    (setq ss_pre_filter_set_xx_ (TA:standard_list_croodinate_sorting ss_pre_filter_set_xx_ "X"))
                  ;
                )
              )
            )
          )
        )
        "#<%catch-all-apply-error%>"
      )
      (setq blank_ss_ (ssadd))
      (setq blk1_ename_ (car (nth 0 ss_pre_filter_set_xx_ )))
      (setq blk1_obj_ (vlax-ename->vla-object blk1_ename_))
      (setq blk1_obj_ins_ (vlax-safearray->list (vlax-variant-value (vla-get-insertionpoint blk1_obj_))))
      (setq blk1_obj_ro (vla-get-rotation blk1_obj_))
      (setq blk2_ename_ (car (nth 1 ss_pre_filter_set_xx_ )))
      (setq blk2_obj_ (vlax-ename->vla-object blk2_ename_))
      (setq blk2_obj_ins_ (vlax-safearray->list (vlax-variant-value (vla-get-insertionpoint blk2_obj_))))
      (TA:move_axis_insertionpoint blk1_obj_ "X" 50)
      (TA:move_axis_insertionpoint blk2_obj_ "X" 0)
      (vla-put-color blk1_obj_ 4)
      (vla-put-color blk2_obj_ 4)
      (command "pselect"  blank_ss_  "" )
    ) 
    (_EndUndo doc)
  )
  (defun c:temp_inner_move_imy ()
    (_StartUndo doc)
    (while
      (/=
        (vl-princ-to-string
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            (cons 0 "INSERT") ;type of object
                                                            (cons 8 "001 - ASCESSORIES")   ;kind of layer
                                                            ; (cons 2 "000-GRID_LINE_DYN")       ;kind of nameblock
                                                            ; (cons 62 1)           ;kind of color call sign with color code index
                                                          ) 
                                                    )
                        )
                        nil
                      )
                      (progn
                        (setq ss_pre_filter_set_xx_ (ssget
                                                          (list
                                                            (cons 0 "INSERT") ;type of object
                                                            (cons 8 "001 - ASCESSORIES")   ;kind of layer
                                                            ; (cons 2 "000-GRID_LINE_DYN")       ;kind of nameblock
                                                            ; (cons 62 1)           ;kind of color call sign with color code index
                                                          )
                                                    )
                        )
                      )
                      (sslength ss_pre_filter_set_xx_)
                    )
                    (setq ss_pre_filter_set_xx_ (TA:EF_Filter_ss_set_ ss_pre_filter_set_xx_ "000 - DYNAMIC_COMBINE+VIEW_ASSCESSORIES_FAMELINE_GALV.BRACKET_FITTING_U-PROFILE_CC-01-4_COMBINE_VIEW"))
                    (setq ss_pre_filter_set_xx_ (TA:standard_list_croodinate_sorting ss_pre_filter_set_xx_ "Y"))
                  ;
                )
              )
            )
          )
        )
        "#<%catch-all-apply-error%>"
      )
      (setq blank_ss_ (ssadd))
      (setq blk1_ename_ (car (nth 0 ss_pre_filter_set_xx_ )))
      (setq blk1_obj_ (vlax-ename->vla-object blk1_ename_))
      (setq blk1_obj_ins_ (vlax-safearray->list (vlax-variant-value (vla-get-insertionpoint blk1_obj_))))
      (setq blk1_obj_ro (vla-get-rotation blk1_obj_))
      (setq blk2_ename_ (car (nth 1 ss_pre_filter_set_xx_ )))
      (setq blk2_obj_ (vlax-ename->vla-object blk2_ename_))
      (setq blk2_obj_ins_ (vlax-safearray->list (vlax-variant-value (vla-get-insertionpoint blk2_obj_))))
      (TA:move_axis_insertionpoint blk1_obj_ "y" 25)
      (TA:move_axis_insertionpoint blk2_obj_ "y" -25)
      (vla-put-color blk1_obj_ 4)
      (vla-put-color blk2_obj_ 4)
      (command "pselect"  blank_ss_  "" )
    ) 
    (_EndUndo doc)
  )
  
  (defun c:moy ()
    ;selection_set_for_fillter_blk_name
      (if  ;pre_select_ssget_or_post_select_ssget
        (=
          (setq ss_selection_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_selection_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_selection_)
      )
    ;
    (setq ERR_ nil)
    (setq temp_increment_num_ 0)
    (if (= increment_num_ nil) (progn (setq increment_num_ 0) ) )
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos (setq temp_increment_num_ (+ temp_increment_num_ increment_num_)) 2 2) " <" (rtos (setq increment_num_ (cond (increment_num_) (1.0) ) ) ) "> : " ) ) ) (increment_num_) ) )
            )
          )
        )
      )
      ;preloop_and_while
        (setq ss_selection_i 0)
        (while 
          (and
            (= (vl-catch-all-error-p ERR_) nil)
            (< ss_selection_i (sslength ss_selection_))
          )
          (setq ss_selection_ename_ (ssname ss_selection_ ss_selection_i)) 
          (setq ss_selection_obj_ (vlax-ename->vla-object  ss_selection_ename_))
          (setq ss_selection_obj_rotation_ (vla-get-rotation  ss_selection_obj_))
          (setq ss_selection_obj_ins_ (vlax-safearray->list (vlax-variant-value (vla-get-insertionpoint ss_selection_obj_))))
          
          (cond
            (;ssss_case_1
              (and
                  (= (vl-catch-all-error-p ERR_) nil)
                  (< increment_num_ 0)
              )
              (progn
                (TA:move_axis_insertionpoint ss_selection_obj_ "y" increment_num_)
                (princ "ssss_case_1")
              )
            )
            (;ssss_case_2
              (and
                  (= (vl-catch-all-error-p ERR_) nil)
                  (> increment_num_ 0)
              )
              (progn
                (TA:move_axis_insertionpoint ss_selection_obj_ "y" increment_num_)
                (princ "ssss_case_2")
              )
            )
          )
          
          
          (setq ss_selection_i (+ ss_selection_i 1))
        )
      ;
    )
  )
  (defun c:x+ ()
    ;for moving support frame Fameline celing SK300 (0.025 / 1 enter)
    ;set paremeter for moving
      (setq move_length_ 25)
    ;
    ;user_input_
    ;user_input_ss
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (+ (car sss_obj_ins_) move_length_) 
                                          (cadr sss_obj_ins_) 
                                          (caddr sss_obj_ins_)
                                        ) 
                  )
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (+ (car sss_obj_ins_) move_length_) 
                                          (cadr sss_obj_ins_) 
                                          (caddr sss_obj_ins_)
                                        ) 
                  )
                  (vla-put-insertionpoint sss_obj_ (vlax-3d-point sss_obj_putins_))
              (setq ss_pre_filter_set_xx_i (+ ss_pre_filter_set_xx_i 1))
            )
        )
        
      )
    ;
  )
  (defun c:x- ()
    ;for moving support frame Fameline celing SK300 (0.025 / 1 enter)
    ;set paremeter for moving
      (setq move_length_ 25)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (- (car sss_obj_ins_) move_length_) 
                                          (cadr sss_obj_ins_) 
                                          (caddr sss_obj_ins_)
                                        ) 
                  )
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (- (car sss_obj_ins_) move_length_) 
                                          (cadr sss_obj_ins_) 
                                          (caddr sss_obj_ins_)
                                        ) 
                  )
                  (vla-put-insertionpoint sss_obj_ (vlax-3d-point sss_obj_putins_))
              (setq ss_pre_filter_set_xx_i (+ ss_pre_filter_set_xx_i 1))
            )
        )
        
      )
    ;
  )
  (defun c:xx+ ()
    ;for moving support frame Fameline celing SK300 (0.025 / 1 enter)
    ;set paremeter for moving
      (setq move_length_ 50)
    ;
    ;user_input_
    ;user_input_ss
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (+ (car sss_obj_ins_) move_length_) 
                                          (cadr sss_obj_ins_) 
                                          (caddr sss_obj_ins_)
                                        ) 
                  )
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (+ (car sss_obj_ins_) move_length_) 
                                          (cadr sss_obj_ins_) 
                                          (caddr sss_obj_ins_)
                                        ) 
                  )
                  (vla-put-insertionpoint sss_obj_ (vlax-3d-point sss_obj_putins_))
              (setq ss_pre_filter_set_xx_i (+ ss_pre_filter_set_xx_i 1))
            )
        )
        
      )
    ;
  )
  (defun c:xx- ()
    ;for moving support frame Fameline celing SK300 (0.025 / 1 enter)
    ;set paremeter for moving
      (setq move_length_ 50)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (- (car sss_obj_ins_) move_length_) 
                                          (cadr sss_obj_ins_) 
                                          (caddr sss_obj_ins_)
                                        ) 
                  )
                  (vla-put-insertionpoint sss_obj_ (vlax-3d-point sss_obj_putins_))
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (- (car sss_obj_ins_) move_length_) 
                                          (cadr sss_obj_ins_) 
                                          (caddr sss_obj_ins_)
                                        ) 
                  )
                  (vla-put-insertionpoint sss_obj_ (vlax-3d-point sss_obj_putins_))
              (setq ss_pre_filter_set_xx_i (+ ss_pre_filter_set_xx_i 1))
            )
        )
        
      )
    ;
  )
  (defun c:xc+ ()
    ;for moving support frame Fameline celing SK300 (0.025 / 1 enter)
    ;set paremeter for moving
      (setq move_length_ 12)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (+ (car sss_obj_ins_) move_length_) 
                                          (cadr sss_obj_ins_) 
                                          (caddr sss_obj_ins_)
                                        ) 
                  )
                  (vla-copy sss_obj_ )
                  (vla-put-insertionpoint sss_obj_ (vlax-3d-point sss_obj_putins_))
                  
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (+ (car sss_obj_ins_) move_length_) 
                                          (cadr sss_obj_ins_) 
                                          (caddr sss_obj_ins_)
                                        ) 
                  )
                  (vla-copy sss_obj_ )
                  (vla-put-insertionpoint sss_obj_ (vlax-3d-point sss_obj_putins_))
                  
              (setq ss_pre_filter_set_xx_i (+ ss_pre_filter_set_xx_i 1))
            )
        )
        
      )
    ;
  )
  (defun c:xc- ()
    ;for moving support frame Fameline celing SK300 (0.025 / 1 enter)
    ;set paremeter for moving
      (setq move_length_ 1200)
    ;
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (- (car sss_obj_ins_) move_length_) 
                                          (cadr sss_obj_ins_) 
                                          (caddr sss_obj_ins_)
                                        ) 
                  )
                  (vla-copy sss_obj_ )
                  (vla-put-insertionpoint sss_obj_ (vlax-3d-point sss_obj_putins_))
                  
              
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq sss_obj_ins_ (vlax-safearray->list (vlax-variant-value (vla-get-insertionpoint sss_obj_))))
                  (setq sss_obj_putins_ (list
                                          (- (car sss_obj_ins_) move_length_) 
                                          (cadr sss_obj_ins_) 
                                          (caddr sss_obj_ins_)
                                        ) 
                  )
                  (vla-copy sss_obj_ )
                  (vla-put-insertionpoint sss_obj_ (vlax-3d-point sss_obj_putins_))
                  
              (setq ss_pre_filter_set_xx_i (+ ss_pre_filter_set_xx_i 1))
            )
        )
        
      )
    ;
  )
  (defun c:copy_same_place_csame ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (vla-copy ss_pre_filter_set_xx_obj_)
        (setq ss_pre_filter_set_xx_i (+ ss_pre_filter_set_xx_i 1))
      )
    ;
  )
  (defun c:TEMP:copy_from_basepoint_cfb_ () 
    ;selection_set
      (if  ;pre_select_ssget_or_post_select_ssget
        (= 
          (setq ss_pre_filter_set_xx (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq tar_copy_        (car (entsel))
                tar_copy_obj_    (vlax-ename->vla-object tar_copy_)
                tar_copy_obj_ins (vlax-safearray->list 
                                    (vlax-variant-value (vla-get-insertionpoint tar_copy_obj_))
                                  )
                tar_result_      (list (car tar_copy_obj_ins) 
                                        (cadr tar_copy_obj_ins)
                                  )
          )
          
          (if (= (getvar "worlducs") 0)(progn (setq tar_copy_obj_ins (trans tar_copy_obj_ins 0 1))) tar_copy_obj_ins )
          (command "_copy" tar_copy_ "" "m" tar_copy_obj_ins)
        )
        (princ "\n")
      )
    ;
    (if (/= ss_pre_filter_set_xx nil)
      (progn 
        (setq tar_copy_        (ssname ss_pre_filter_set_xx 0)
              tar_copy_obj_    (vlax-ename->vla-object tar_copy_)
              tar_copy_obj_ins (vlax-safearray->list 
                                  (vlax-variant-value (vla-get-insertionpoint tar_copy_obj_))
                                )
              tar_copy_obj_ins (if (= (getvar "worlducs") 0)(progn (setq tar_copy_obj_ins (trans tar_copy_obj_ins 0 1))) tar_copy_obj_ins )
              tar_result_ (list (car tar_copy_obj_ins)(cadr tar_copy_obj_ins))
        )
        
        
        (command "_copy" "m" tar_copy_obj_ins   )
        
        
      )
      (princ "\n")
    )
  )
  (defun c:TEMP:copy_from_basepoint_mfb_ () 
    ;selection_set
      (if  ;pre_select_ssget_or_post_select_ssget
        (= 
          (setq ss_pre_filter_set_xx (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                     )
          )
          nil
        )
        (progn 
          (setq tar_copy_        (car (entsel))
                tar_copy_obj_    (vlax-ename->vla-object tar_copy_)
                tar_copy_obj_ins (vlax-safearray->list 
                                   (vlax-variant-value (vla-get-insertionpoint tar_copy_obj_))
                                 )
                tar_result_      (list (car tar_copy_obj_ins) 
                                       (cadr tar_copy_obj_ins)
                                 )
          )
          (if (= (getvar "worlducs") 0)(progn (setq tar_copy_obj_ins (trans tar_copy_obj_ins 0 1))) tar_copy_obj_ins )
          (command "_move" tar_copy_ "" tar_copy_obj_ins)
        )
        (princ "\n")
      )
    ;
    (if (/= ss_pre_filter_set_xx nil)
      (progn 
        (setq tar_copy_        (ssname ss_pre_filter_set_xx 0)
              tar_copy_obj_    (vlax-ename->vla-object tar_copy_)
              tar_copy_obj_ins (vlax-safearray->list 
                                 (vlax-variant-value (vla-get-insertionpoint tar_copy_obj_))
                               )
              tar_copy_obj_ins (if (= (getvar "worlducs") 0)(progn (setq tar_copy_obj_ins (trans tar_copy_obj_ins 0 1))) tar_copy_obj_ins )
              tar_result_ (list (car tar_copy_obj_ins)(cadr tar_copy_obj_ins))
        )
        
        
        ; (command "_move" ss_pre_filter_set_xx "" tar_copy_obj_ins )
        (command "_move" tar_copy_obj_ins)
        
        
      )
      (princ "\n")
    )
  )
  (defun c:TEMP:copy_from_basepoint_cfs_ () 
    ;selection_set
      (if  ;pre_select_ssget_or_post_select_ssget
        (= 
          (setq ss_pre_filter_set_xx (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq tar_copy_        (car (entsel))
                tar_copy_obj_    (vlax-ename->vla-object tar_copy_)
                tar_copy_obj_ins (vlax-safearray->list 
                                  (vlax-variant-value (vla-get-insertionpoint tar_copy_obj_))
                                )
                tar_copy_obj_ins (list (+ (car tar_copy_obj_ins) 150) 
                                      (- (cadr tar_copy_obj_ins) 75)
                                      0
                                )
          )
          (command "_copy" tar_copy_ "" "m" tar_copy_obj_ins)
        )
        (princ "\n")
      )
    ;
    (if (/= ss_pre_filter_set_xx nil)
      (progn 
        (setq tar_copy_        (ssname ss_pre_filter_set_xx 0)
                tar_copy_obj_    (vlax-ename->vla-object tar_copy_)
                tar_copy_obj_ins (vlax-safearray->list 
                                  (vlax-variant-value (vla-get-insertionpoint tar_copy_obj_))
                                )
                tar_copy_obj_ins (list (+ (car tar_copy_obj_ins) 150) 
                                      (- (cadr tar_copy_obj_ins) 75)
                                      0
                                )
          )
        
        
        
        ; (command "_copy" "m" tar_copy_ "" tar_copy_obj_ins  )
        (command "_copy" "m" tar_copy_obj_ins   )
        
      )
      (princ "\n")
    )
  )
  (defun c:TEMP:copy_from_basepoint_cfs1_ () 
    ;selection_set
      (if  ;pre_select_ssget_or_post_select_ssget
        (= 
          (setq ss_pre_filter_set_xx (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq tar_copy_        (car (entsel))
                tar_copy_obj_    (vlax-ename->vla-object tar_copy_)
                tar_copy_obj_ins (vlax-safearray->list 
                                  (vlax-variant-value (vla-get-insertionpoint tar_copy_obj_))
                                )
                tar_copy_obj_ins (list (+ (car tar_copy_obj_ins) 150) 
                                      (- (cadr tar_copy_obj_ins) 0)
                                      0
                                )
          )
          (command "_copy" tar_copy_ "" "m" tar_copy_obj_ins)
        )
        (princ "\n")
      )
    ;
    (if (/= ss_pre_filter_set_xx nil)
      (progn 
        (setq tar_copy_        (ssname ss_pre_filter_set_xx 0)
                tar_copy_obj_    (vlax-ename->vla-object tar_copy_)
                tar_copy_obj_ins (vlax-safearray->list 
                                  (vlax-variant-value (vla-get-insertionpoint tar_copy_obj_))
                                )
                tar_copy_obj_ins (list (+ (car tar_copy_obj_ins) 150) 
                                      (- (cadr tar_copy_obj_ins) 0)
                                      0
                                )
          )
        
        
        
        ; (command "_copy" "m" tar_copy_ "" tar_copy_obj_ins  )
        (command "_copy" "m" tar_copy_obj_ins   )
        
      )
      (princ "\n")
    )
  )
  (defun c:TEMP:move_to_basepoint_mv2bk_ () 
    
    (setq ERR_
      (vl-catch-all-apply
        (function
          (lambda ()
            (setvar "SELECTIONPREVIEW" 3)
            (setq main_ename_ (car (entsel "specify Object")))
            (setq main_obj_ (vlax-ename->vla-object main_ename_))
            (setq main_obj_ins_ (vlax-safearray->list (vlax-variant-value (vla-get-insertionpoint main_obj_))))
            (if (= (getvar "worlducs") 0)(progn (setq main_obj_ins_ (trans main_obj_ins_ 0 1))) main_obj_ins_ )
            ;input_cond entsel ssget
          )
        )
      )
    )

    
    ;while selection process
      (setq ERR_ nil)
      (while ;for keep insertion point and dist. fix length one side
        (and
          (= (vl-catch-all-error-p ERR_) nil)
        )
        (setq ERR_
          (vl-catch-all-apply
            (function
              (lambda ()
                (if (and 
                      (/= (setq target_ename_ (car (entsel "specify Object"))) nil) 
                      (/= (setq target_obj_ (vlax-ename->vla-object target_ename_)) nil) 
                      (= (vla-get-objectname target_obj_) "AcDbBlockReference") 
                    )
                  (progn
                    (setq target_obj_ins_ (vlax-safearray->list (vlax-variant-value (vla-get-insertionpoint target_obj_))))
                    (setq main_obj_ins_input main_obj_ins_)
                    (vla-put-insertionpoint
                      target_obj_
                      (vlax-3d-point
                        (if (= (getvar "worlducs") 0)(progn (setq main_obj_ins_input (trans main_obj_ins_input 1 0))) main_obj_ins_input )
                      )
                    )
                  )
                )
                ;input_cond entsel ssget
              )
            )
          )
        )
      )
    ;
    (setvar "SELECTIONPREVIEW" 0)
  )
  (defun c:TEMP:move_to_basepoint_mv2x_ () 
    
    (setq ERR_
      (vl-catch-all-apply
        (function
          (lambda ()
            (setvar "SELECTIONPREVIEW" 3)
            (setq main_ename_ (car (entsel "specify Object")))
            (setq main_obj_ (vlax-ename->vla-object main_ename_))
            (setq main_obj_ins_ (vlax-safearray->list (vlax-variant-value (vla-get-insertionpoint main_obj_))))
            (if (= (getvar "worlducs") 0)(progn 
                                           (setq main_obj_ins_ (trans main_obj_ins_ 0 1))
                                         ) 
              main_obj_ins_ 
            )
            ;input_cond entsel ssget
          )
        )
      )
    )

    
    ;while selection process
      (setq ERR_ nil)
      (while ;for keep insertion point and dist. fix length one side
        (and
          (= (vl-catch-all-error-p ERR_) nil)
        )
        (setq ERR_
          (vl-catch-all-apply
            (function
              (lambda ()
                (if (and 
                      (/= (setq target_ename_ (car (entsel "specify Object"))) nil) 
                      (/= (setq target_obj_ (vlax-ename->vla-object target_ename_)) nil) 
                      (= (vla-get-objectname target_obj_) "AcDbBlockReference") 
                    )
                  (progn
                    (setq target_obj_ins_ (vlax-safearray->list (vlax-variant-value (vla-get-insertionpoint target_obj_))))
                    (if (= (getvar "worlducs") 0) 
                      (progn 
                        (setq target_obj_ins_ (list 
                                                    (car (trans target_obj_ins_ 0 1))
                                                    (cadr (trans target_obj_ins_ 0 1))
                                                    0
                                                  )
                        )
                      )
                      (list 
                        (car target_obj_ins_)
                        (cadr target_obj_ins_)
                        0
                      )
                    )
                    (setq main_obj_ins_input main_obj_ins_)
                    (vla-put-insertionpoint
                      target_obj_
                      (vlax-3d-point
                        (if (= (getvar "worlducs") 0) 
                          (progn 
                            (setq main_obj_ins_input (list 
                                                       (car (trans main_obj_ins_input 1 0))
                                                       (cadr (trans target_obj_ins_ 1 0))
                                                       0
                                                     )
                            )
                          )
                          (list 
                            (car main_obj_ins_input)
                            (cadr target_obj_ins_)
                            0
                          )
                        )
                      )
                    )
                  )
                )
                ;input_cond entsel ssget
              )
            )
          )
        )
      )
    ;
    (setvar "SELECTIONPREVIEW" 0)
  )
  (defun c:TEMP:move_to_basepoint_mv2y_ () 
    
    (setq ERR_
      (vl-catch-all-apply
        (function
          (lambda ()
            (setvar "SELECTIONPREVIEW" 3)
            (setq main_ename_ (car (entsel "specify Object")))
            (setq main_obj_ (vlax-ename->vla-object main_ename_))
            (setq main_obj_ins_ (vlax-safearray->list (vlax-variant-value (vla-get-insertionpoint main_obj_))))
            (if (= (getvar "worlducs") 0)(progn 
                                           (setq main_obj_ins_ (trans main_obj_ins_ 0 1))
                                         ) 
              main_obj_ins_ 
            )
            ;input_cond entsel ssget
          )
        )
      )
    )

    
    ;while selection process
      (setq ERR_ nil)
      (while ;for keep insertion point and dist. fix length one side
        (and
          (= (vl-catch-all-error-p ERR_) nil)
        )
        (setq ERR_
          (vl-catch-all-apply
            (function
              (lambda ()
                (if (and 
                      (/= (setq target_ename_ (car (entsel "specify Object"))) nil) 
                      (/= (setq target_obj_ (vlax-ename->vla-object target_ename_)) nil) 
                      (= (vla-get-objectname target_obj_) "AcDbBlockReference") 
                    )
                  (progn
                    (setq target_obj_ins_ (vlax-safearray->list (vlax-variant-value (vla-get-insertionpoint target_obj_))))
                    (if (= (getvar "worlducs") 0) 
                      (progn 
                        (setq target_obj_ins_ (list 
                                                    (car (trans target_obj_ins_ 0 1))
                                                    (cadr (trans target_obj_ins_ 0 1))
                                                    0
                                                  )
                        )
                      )
                      (list 
                        (car target_obj_ins_)
                        (cadr target_obj_ins_)
                        0
                      )
                    )
                    (setq main_obj_ins_input main_obj_ins_)
                    (vla-put-insertionpoint
                      target_obj_
                      (vlax-3d-point
                        (if (= (getvar "worlducs") 0) 
                          (progn 
                            (setq main_obj_ins_input (list 
                                                       (car (trans target_obj_ins_ 1 0))
                                                       (cadr (trans main_obj_ins_input 1 0))
                                                       0
                                                     )
                            )
                          )
                          (list 
                            (car target_obj_ins_)
                            (cadr main_obj_ins_input)
                            0
                          )
                        )
                      )
                    )
                  )
                )
                ;input_cond entsel ssget
              )
            )
          )
        )
      )
    ;
    (setvar "SELECTIONPREVIEW" 0)
  )
  (defun c:Resupport_spacing_DP1_ ()
    (setq insert_int_spcaing_dist_ (getint "insert_int_spcaing_dist_" ))
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
              (setq sss_obj_ (vlax-ename->vla-object ss_pre_filter_set_xx_ename_))
            
              (setq sss_obj_ins_ (vlax-safearray->list (vlax-variant-value (vla-get-insertionpoint sss_obj_))))
              (setq sss_obj_rotation_ (rad-to-deg (vla-get-rotation sss_obj_ )))
              
              ;get-dyn-blk_process
                (setq H (LM:getdynpropvalue sss_obj_ "H"))
                (setq array_width (LM:getdynpropvalue sss_obj_ "array_width"))
              ;
              (setq insert_blk_name_ (strcat "000TYP-LINE_AND_ARRAY_@" 
                                            (rtos insert_int_spcaing_dist_ 2 0)
                                            "mm._start"
                                    )
              )
              ;insertion-new_object_
                (command "insert" insert_blk_name_ sss_obj_ins_ 1 sss_obj_rotation_ )
                (setq new_ename_ (entlast))
                (setq new_obj_ (vlax-ename->vla-object new_ename_))
              
                (LM:setdynpropvalue new_obj_ "H" H)
                (LM:setdynpropvalue new_obj_ "array_width" array_width)
              ;
              ;delete main_obj_
                (vla-delete sss_obj_ )
              ;

              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_))
              (setq ss_pre_filter_set_xx_ename_ (ssname ss_pre_filter_set_xx_ ss_pre_filter_set_xx_i))
              (if (= (setq sss_obj_ (vlax-ename->vla-object ss_pre_filter_set_xx_ename_)) nil)
                (progn
                  (setq sss_obj_ (vlax-ename->vla-object (entlast)))
                )
              )
              
            
              (setq sss_obj_ins_ (vlax-safearray->list (vlax-variant-value (vla-get-insertionpoint sss_obj_))))
              (setq sss_obj_rotation_ (rad-to-deg (vla-get-rotation sss_obj_ )))
              
              ;get-dyn-blk_process
                (setq H (LM:getdynpropvalue sss_obj_ "H"))
                (setq array_width (LM:getdynpropvalue sss_obj_ "array_width"))
              ;
              (setq insert_blk_name_ (strcat "000TYP-LINE_AND_ARRAY_@" 
                                            (rtos insert_int_spcaing_dist_ 2 0)
                                            "mm._start"
                                    )
              )
              ;insertion-new_object_
                (command "insert" insert_blk_name_ sss_obj_ins_ 1 sss_obj_rotation_ )
                (setq new_ename_ (entlast))
                (setq new_obj_ (vlax-ename->vla-object new_ename_))
              
                (LM:setdynpropvalue new_obj_ "H" H)
                (LM:setdynpropvalue new_obj_ "array_width" array_width)
              ;
              ;delete main_obj_
                (vla-delete sss_obj_ )
              ;
              (setq ss_pre_filter_set_xx_i (+ ss_pre_filter_set_xx_i 1))
            )
        )
        
      )
    ;
  )
  (defun c:Assembly_blcok_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget 
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    
  
  
  )
  ;001 - DYNAMINC STEEL TUBE
  (defun c:insert_point-to-point_steel_tube_steelsingle ()
    ;presetting
      (setq offset_length 150)
      (setq x 50)
      (setq y 50)
    ;
    (while ;continue loop
      (/=
        (vl-princ-to-string
          (vl-catch-all-apply 
            (function 
              (lambda () 
                ;selection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)
                  )
                  (setq ss_pre_filter_set_xx_ (TA:EF_Filter_ss_set_ ss_pre_filter_set_xx_ "000 - DYNAMIC_LENGTH+COMBINE+VIEW_ASSCESSORIES_FAMELINE_BK-08_HANGING_SYSTEM_300HK_COMBINE_SET"))
                ;
              )
            )
          )
        )
        "#<%catch-all-apply-error%>"
      )
      ;preloop_and_while
        (setq ss_pre_filter_set_xx_i 0)
        (setq ss_pre_filter_set_xx_obj_ins_list_ ())
        (while (and 
                (/= (sslength ss_pre_filter_set_xx_) 1)
                (< ss_pre_filter_set_xx_i (sslength ss_pre_filter_set_xx_))
              )
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_ins_list_ (cons ss_pre_filter_set_xx_obj_ins_ ss_pre_filter_set_xx_obj_ins_list_ ) )
          (setq ss_pre_filter_set_xx_i (+ ss_pre_filter_set_xx_i 1))
        )
        (if (/= (length ss_pre_filter_set_xx_obj_ins_list_) 1)
          (progn
            ;TA:stanndard_lambda_sorting
              (setq ss_pre_filter_set_xx_obj_ins_list_sorted_ (vl-sort ss_pre_filter_set_xx_obj_ins_list_  ;bigest open indent list
                                                                      (function 
                                                                        (lambda (a b) 
                                                                          (>
                                                                            (cadr a)
                                                                            (cadr b)
                                                                          )
                                                                        )
                                                                      )
                                                              ) ;bigest close indent list
              )
              (setq ss_pre_filter_set_xx_obj_ins_list_sorted_top (car ss_pre_filter_set_xx_obj_ins_list_sorted_))
              (setq ss_pre_filter_set_xx_obj_ins_list_sorted_bot (car (reverse ss_pre_filter_set_xx_obj_ins_list_sorted_)))
              (setq ss_pre_filter_set_xx_obj_ins_list_sorted_ang_TB (angle ss_pre_filter_set_xx_obj_ins_list_sorted_top ss_pre_filter_set_xx_obj_ins_list_sorted_bot))
              (setq ss_pre_filter_set_xx_obj_ins_list_sorted_ang_BT (angle  ss_pre_filter_set_xx_obj_ins_list_sorted_bot ss_pre_filter_set_xx_obj_ins_list_sorted_top))
              (setq ss_pre_filter_set_xx_obj_ins_list_sorted_length_ (distance ss_pre_filter_set_xx_obj_ins_list_sorted_top ss_pre_filter_set_xx_obj_ins_list_sorted_bot))
            ;
            (TA:vla-insertblock 
              "000 - DYNAMIC_LENGTH+COMBINE+VIEW_ASSCESSORIES_STEEL_TUBE_COMBINE_SET"
              (polar ss_pre_filter_set_xx_obj_ins_list_sorted_top ss_pre_filter_set_xx_obj_ins_list_sorted_ang_BT offset_length )
              1
              ss_pre_filter_set_xx_obj_ins_list_sorted_ang_TB
            )
            ;new_blk_entlast object
              (setq newblk_ename (entlast))
              (setq newblk_obj_ (vlax-ename->vla-object newblk_ename))
              (vla-put-layer newblk_obj_ "defpoints")
              (vla-put-color newblk_obj_ 130)
              (LM:setdynpropvalue newblk_obj_ "x" x)
              (LM:setdynpropvalue newblk_obj_ "length" (+ (* offset_length 2 ) ss_pre_filter_set_xx_obj_ins_list_sorted_length_))
              (LM:setdynpropvalue newblk_obj_ "view" "2_top_view")
            ;
          )
        )

      ;
      (command "pselect"   "" )
    )
  )
  (defun c:insert_point-to-point_steel_tube_steelset ()
    ;presetting
      (setq offset_length 150)
      (setq x 50)
      (setq y 50)
    ;
    (while ;continue loop
      (/=
        (vl-princ-to-string
          (vl-catch-all-apply 
            (function 
              (lambda () 
                ;selection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)
                  )
                  (if  ;pre_select_ssget_or_post_select_ssget
                    (=
                      (setq ss_pre_filter_set_xxsub_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xxsub_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xxsub_)
                  )
                  
                  (setq ss_pre_filter_set_xx_ (TA:EF_Filter_ss_set_ ss_pre_filter_set_xx_ "000 - DYNAMIC_LENGTH+COMBINE+VIEW_ASSCESSORIES_FAMELINE_BK-08_HANGING_SYSTEM_300HK_COMBINE_SET"))
                  (setq ss_pre_filter_set_xxsub_ (TA:EF_Filter_ss_set_ ss_pre_filter_set_xxsub_ "000 - DYNAMIC_LENGTH+COMBINE+VIEW_ASSCESSORIES_FAMELINE_BK-08_HANGING_SYSTEM_300HK_COMBINE_SET"))
                ;
              )
            )
          )
        )
        "#<%catch-all-apply-error%>"
      )
      ;preloop_and_while
        (setq ss_pre_filter_set_xx_i 0)
        (setq ss_pre_filter_set_xx_obj_ins_list_ ())
        (setq ss_pre_filter_set_xxsub_obj_ins_list_ ())
        (while (and 
                 (/= ss_pre_filter_set_xx_ nil)
                 (/= ss_pre_filter_set_xxsub_ nil)
                 (/= (sslength ss_pre_filter_set_xx_) 1)
                 (< ss_pre_filter_set_xx_i (sslength ss_pre_filter_set_xx_))
               )
          (if (/= (setq ss_pre_filter_set_xx_ename_ (ssname ss_pre_filter_set_xx_ ss_pre_filter_set_xx_i)) nil)
            (progn
              (setq ss_pre_filter_set_xx_obj_ (vlax-ename->vla-object  ss_pre_filter_set_xx_ename_))
              (setq ss_pre_filter_set_xx_obj_ins_ (vlax-safearray->list (vlax-variant-value (vla-get-insertionpoint ss_pre_filter_set_xx_obj_))))
              (setq ss_pre_filter_set_xx_obj_ins_list_ (cons ss_pre_filter_set_xx_obj_ins_ ss_pre_filter_set_xx_obj_ins_list_))
            )
          )
          (if (/= (setq ss_pre_filter_set_xxsub_ename_ (ssname ss_pre_filter_set_xxsub_ ss_pre_filter_set_xx_i)) nil)
            (progn
              (setq ss_pre_filter_set_xxsub_obj_ (vlax-ename->vla-object  ss_pre_filter_set_xxsub_ename_))
              (setq ss_pre_filter_set_xxsub_obj_ins_ (vlax-safearray->list (vlax-variant-value (vla-get-insertionpoint ss_pre_filter_set_xxsub_obj_))))
              (setq ss_pre_filter_set_xxsub_obj_ins_list_ (cons ss_pre_filter_set_xxsub_obj_ins_ ss_pre_filter_set_xxsub_obj_ins_list_))
            )
          )
          (setq ss_pre_filter_set_xx_i (+ ss_pre_filter_set_xx_i 1))
        )
      ;
      ;TA:stanndard_lambda_sorting
        (setq ss_pre_filter_set_xx_obj_ins_list_sorted_ (vl-sort ss_pre_filter_set_xx_obj_ins_list_  ;bigest open indent list
                                                  (function 
                                                    (lambda (a b) 
                                                      (< (car a) (car b))
                                                    )
                                                  )
                              ) ;bigest close indent list
        )
      ;
      ;TA:stanndard_lambda_sorting
        (setq ss_pre_filter_set_xxsub_obj_ins_list_sorted_ (vl-sort ss_pre_filter_set_xxsub_obj_ins_list_  ;bigest open indent list
                                                  (function 
                                                    (lambda (a b) 
                                                      (< (car a) (car b))
                                                    )
                                                  )
                              ) ;bigest close indent list
        )
      ;
      ;preloop_and_while
        (setq ss_pre_filter_set_xx_obj_ins_list_sorted_i 0)
        (while (< ss_pre_filter_set_xx_obj_ins_list_sorted_i (length ss_pre_filter_set_xx_obj_ins_list_sorted_))
          (setq ss_pre_filter_set_xx_obj_ins_list_sorted_valtop_ (nth  ss_pre_filter_set_xx_obj_ins_list_sorted_i ss_pre_filter_set_xx_obj_ins_list_sorted_))
          (setq ss_pre_filter_set_xx_obj_ins_list_sorted_valbot_ (nth  ss_pre_filter_set_xx_obj_ins_list_sorted_i ss_pre_filter_set_xxsub_obj_ins_list_sorted_))
          (TA:vla-insertblock  
            "000 - DYNAMIC_LENGTH+COMBINE+VIEW_ASSCESSORIES_STEEL_TUBE_COMBINE_SET"
            (polar ss_pre_filter_set_xx_obj_ins_list_sorted_valtop_ (angle  ss_pre_filter_set_xx_obj_ins_list_sorted_valbot_ ss_pre_filter_set_xx_obj_ins_list_sorted_valtop_) offset_length )
            1
            (angle  ss_pre_filter_set_xx_obj_ins_list_sorted_valtop_ ss_pre_filter_set_xx_obj_ins_list_sorted_valbot_ )
          )
          ;new_blk_entlast object
            (setq newblk_ename (entlast))
            (setq newblk_obj_ (vlax-ename->vla-object newblk_ename))
            (vla-put-layer newblk_obj_ "defpoints")
            (vla-put-color newblk_obj_ 130)
            (LM:setdynpropvalue newblk_obj_ "x" x)
            (LM:setdynpropvalue newblk_obj_ "length" (+ (* offset_length 2 ) (distance  ss_pre_filter_set_xx_obj_ins_list_sorted_valbot_ ss_pre_filter_set_xx_obj_ins_list_sorted_valtop_)))
            (LM:setdynpropvalue newblk_obj_ "view" "2_top_view")
          ;
      
          (setq ss_pre_filter_set_xx_obj_ins_list_sorted_i (+ ss_pre_filter_set_xx_obj_ins_list_sorted_i 1))
        )
      ;
      ;
      (command "pselect"   "" )
    )
  )
  (defun c:insert_point-to-point_steel_tube_steelcenter ()
    ;presetting
      (setq offset_length 150)
      (setq increment_length 25)
      (setq x 50)
      (setq y 50)
    ;
    
    (while ;continue loop
      (/=
        (vl-princ-to-string
          (vl-catch-all-apply 
            (function 
              (lambda () 
                ;selection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)
                  )
                  (setq ss_pre_filter_set_xx_ (TA:EF_Filter_ss_set_ ss_pre_filter_set_xx_ "000 - DYNAMIC_LENGTH+COMBINE+VIEW_ASSCESSORIES_FAMELINE_BK-08_HANGING_SYSTEM_300HK_COMBINE_SET"))
                ;
              )
            )
          )
        )
        "#<%catch-all-apply-error%>"
      )
      (setq user_input_angle_val (cond ( (getint (strcat "\nSpecify user_input_angle_val <" (rtos (setq user_input_angle_val (cond (user_input_angle_val) (1.0) ) ) ) "> : " ) ) ) (user_input_angle_val) ) )
      ;preloop_and_while
        (setq ss_pre_filter_set_xx_i 0)
        (setq ss_pre_filter_set_xx_obj_ins_list_ ())
        (setq ss_new_set_xx_ (ssadd))
        (while (and 
                 (/= ss_pre_filter_set_xx_ nil)
                 (/= (sslength ss_pre_filter_set_xx_) 0)
                 (< ss_pre_filter_set_xx_i (sslength ss_pre_filter_set_xx_))
               )
          (if (/= (setq ss_pre_filter_set_xx_ename_ (ssname ss_pre_filter_set_xx_ ss_pre_filter_set_xx_i)) nil)
            (progn
              (setq ss_pre_filter_set_xx_obj_ (vlax-ename->vla-object  ss_pre_filter_set_xx_ename_))
              (setq ss_pre_filter_set_xx_obj_ins_ (vlax-safearray->list (vlax-variant-value (vla-get-insertionpoint ss_pre_filter_set_xx_obj_))))
              (TA:vla-insertblock  
                "000 - DYNAMIC_LENGTH+COMBINE+VIEW_ASSCESSORIES_STEEL_TUBE_COMBINE_SET"
                (polar ss_pre_filter_set_xx_obj_ins_ (deg-to-rad user_input_angle_val) offset_length )
                1
                (deg-to-rad (TA:ModifyRotation user_input_angle_val 180))
              )
              ;new_blk_entlast object
                (setq newblk_ename (entlast))
                (setq newblk_ss_new_set_xx_ename (ssadd (entlast) ss_new_set_xx_))
                (setq newblk_obj_ (vlax-ename->vla-object newblk_ename))
                (vla-put-layer newblk_obj_ "defpoints")
                (vla-put-color newblk_obj_ 130)
                (LM:setdynpropvalue newblk_obj_ "x" x)
                (LM:setdynpropvalue newblk_obj_ "y" y)
                (LM:setdynpropvalue newblk_obj_ "length" (+ (* offset_length 2 ) ))
                (LM:setdynpropvalue newblk_obj_ "view" "2_top_view")
              ;
            )
          )

          (setq ss_pre_filter_set_xx_i (+ ss_pre_filter_set_xx_i 1))
        )
        (setq ERR_ nil)
        (while ;for keep insertion point and dist. fix length one side
          (and
            (= (vl-catch-all-error-p ERR_) nil)
          )
          (setq ERR_
            (vl-catch-all-apply
              (function
                (lambda ()
                  (setq increment_num_ (cond ( (getint (strcat "\nSpecify sss_" (rtos ss_new_set_xx_obj_length 2 2)  " <" (rtos (setq increment_num_ (cond (increment_num_) (1.0) ) ) ) "> : " ) ) ) (increment_num_) ) )
                )
              )
            )
          )
          ;preloop_and_while
            (setq ss_new_set_xx_i 0)
            (while 
              (and
                (= (vl-catch-all-error-p ERR_) nil)
                (/= (sslength ss_new_set_xx_) 0)
                (< ss_new_set_xx_i (sslength ss_new_set_xx_))
              )
              (setq ss_new_set_xx_ename (ssname ss_new_set_xx_ ss_new_set_xx_i))  
              (setq ss_new_set_xx_obj_ (vlax-ename->vla-object  ss_new_set_xx_ename))
              (setq ss_new_set_xx_obj_rotation_ (vla-get-rotation  ss_new_set_xx_obj_))
              (setq ss_new_set_xx_obj_ins_ (vlax-safearray->list (vlax-variant-value (vla-get-insertionpoint ss_new_set_xx_obj_))))
              (setq ss_new_set_xx_obj_length (LM:getdynpropvalue ss_new_set_xx_obj_ "length" ))
              
              (cond
                (;ssss_case_1
                  (and
                      (= (vl-catch-all-error-p ERR_) nil)
                      (= (LM:getdynpropvalue ss_new_set_xx_obj_ "view") "2_top_view" )
                      (= increment_num_ 1)
                  )
                  (progn
                    (LM:setdynpropvalue ss_new_set_xx_obj_ "length" (setq ss_new_set_xx_obj_length (+ ss_new_set_xx_obj_length increment_length)))
                    (princ "ssss_case_1")
                  )
                )
                (;ssss_case_2
                  (and
                      (= (vl-catch-all-error-p ERR_) nil)
                      (= (LM:getdynpropvalue ss_new_set_xx_obj_ "view") "2_top_view" )
                      (= increment_num_ 0)
                  )
                  (progn
                    (LM:setdynpropvalue ss_new_set_xx_obj_ "length" (setq ss_new_set_xx_obj_length (- ss_new_set_xx_obj_length increment_length)))
                    (princ "ssss_case_2")
                  )
                )
                (;ssss_case_3
                  (and
                      (= (vl-catch-all-error-p ERR_) nil)
                      (= (LM:getdynpropvalue ss_new_set_xx_obj_ "view") "2_top_view" )
                      (= increment_num_ -1)
                  )
                  (cond
                      (;case3-1
                        (and
                            (= (rad-to-deg (setq ss_new_set_xx_obj_rotation_ (vla-get-rotation  ss_new_set_xx_obj_))) 0)
                        )
                        (progn
                          (LM:setdynpropvalue ss_new_set_xx_obj_ "length" (setq ss_new_set_xx_obj_length (- ss_new_set_xx_obj_length increment_length)))
                          (TA:move_axis_insertionpoint ss_new_set_xx_obj_ "x" (+ increment_length))
                          (princ "case3-1")
                        )
                      )
                      (;case3-2
                        (and
                            (= (rad-to-deg (setq ss_new_set_xx_obj_rotation_ (vla-get-rotation  ss_new_set_xx_obj_))) 270)
                        )
                        (progn
                          (LM:setdynpropvalue ss_new_set_xx_obj_ "length" (setq ss_new_set_xx_obj_length (- ss_new_set_xx_obj_length increment_length)))
                          (TA:move_axis_insertionpoint ss_new_set_xx_obj_ "Y" (- increment_length))
                          (princ "case3-2")
                        )
                      )
                    )
                )
                (;ssss_case_4
                  (and
                      (= (vl-catch-all-error-p ERR_) nil)
                      (= (LM:getdynpropvalue ss_new_set_xx_obj_ "view") "2_top_view" )
                      (= increment_num_ -2)
                  )
                  (progn
                    (cond
                      (;case4-1
                        (and
                            (or 
                              (= (TA:round-05 (rad-to-deg (setq ss_new_set_xx_obj_rotation_ (vla-get-rotation  ss_new_set_xx_obj_)))) 0)
                              (= (TA:round-05 (rad-to-deg (setq ss_new_set_xx_obj_rotation_ (vla-get-rotation  ss_new_set_xx_obj_)))) 180)
                            )
                        )
                        (progn
                          (LM:setdynpropvalue ss_new_set_xx_obj_ "length" (setq ss_new_set_xx_obj_length (+ ss_new_set_xx_obj_length increment_length)))
                          (TA:move_axis_insertionpoint ss_new_set_xx_obj_ "x" (- increment_length))
                          (princ "case4-1")
                        )
                      )
                      (;case4-2
                        (and
                            (or 
                              (= (TA:round-05 (rad-to-deg (setq ss_new_set_xx_obj_rotation_ (vla-get-rotation  ss_new_set_xx_obj_)))) 90)
                              (= (TA:round-05 (rad-to-deg (setq ss_new_set_xx_obj_rotation_ (vla-get-rotation  ss_new_set_xx_obj_)))) 270)
                            )
                        )
                        (progn
                          (LM:setdynpropvalue ss_new_set_xx_obj_ "length" (setq ss_new_set_xx_obj_length (+ ss_new_set_xx_obj_length increment_length)))
                          (TA:move_axis_insertionpoint ss_new_set_xx_obj_ "Y" increment_length)
                          (princ "case4-2")
                        )
                      )
                    )  
                  )
                )
                (;ssss_case_5
                  (and
                      (= (vl-catch-all-error-p ERR_) nil)
                      (= (LM:getdynpropvalue ss_new_set_xx_obj_ "view") "2_top_view" )
                      (= increment_num_ 3)
                  )
                  (progn
                    (cond
                      (;case4-1
                        (and
                            (or 
                              (= (TA:round-05 (rad-to-deg (setq ss_new_set_xx_obj_rotation_ (vla-get-rotation  ss_new_set_xx_obj_)))) 0)
                              (= (TA:round-05 (rad-to-deg (setq ss_new_set_xx_obj_rotation_ (vla-get-rotation  ss_new_set_xx_obj_)))) 180)
                            )
                        )
                        (progn
                          (LM:setdynpropvalue ss_new_set_xx_obj_ "length" (setq ss_new_set_xx_obj_length (+ ss_new_set_xx_obj_length increment_length)))
                          (TA:move_axis_insertionpoint ss_new_set_xx_obj_ "x" (- (/ increment_length 2)))
                          (princ "case4-1")
                        )
                      )
                      (;case4-2
                        (and
                            (or 
                              (= (TA:round-05 (rad-to-deg (setq ss_new_set_xx_obj_rotation_ (vla-get-rotation  ss_new_set_xx_obj_)))) 90)
                              (= (TA:round-05 (rad-to-deg (setq ss_new_set_xx_obj_rotation_ (vla-get-rotation  ss_new_set_xx_obj_)))) 270)
                            )
                        )
                        (progn
                          (LM:setdynpropvalue ss_new_set_xx_obj_ "length" (setq ss_new_set_xx_obj_length (+ ss_new_set_xx_obj_length increment_length)))
                          (TA:move_axis_insertionpoint ss_new_set_xx_obj_ "Y" (/ increment_length 2))
                          (princ "case4-2")
                        )
                      )
                    )  
                  )
                )
                (;ssss_case_6
                  (and
                      (= (vl-catch-all-error-p ERR_) nil)
                      (= (LM:getdynpropvalue ss_new_set_xx_obj_ "view") "2_top_view" )
                      (= increment_num_ 4)
                  )
                  (progn
                    (cond
                      (;case5-1
                        (and
                            (or 
                              (= (TA:round-05 (rad-to-deg (setq ss_new_set_xx_obj_rotation_ (vla-get-rotation  ss_new_set_xx_obj_)))) 0)
                              (= (TA:round-05 (rad-to-deg (setq ss_new_set_xx_obj_rotation_ (vla-get-rotation  ss_new_set_xx_obj_)))) 180)
                            )
                        )
                        (progn
                          (LM:setdynpropvalue ss_new_set_xx_obj_ "length" (setq ss_new_set_xx_obj_length (- ss_new_set_xx_obj_length increment_length)))
                          (TA:move_axis_insertionpoint ss_new_set_xx_obj_ "x" (+ (/ increment_length 2)))
                          (princ "case4-1")
                        )
                      )
                      (;case4-2
                        (and
                            (or 
                              (= (TA:round-05 (rad-to-deg (setq ss_new_set_xx_obj_rotation_ (vla-get-rotation  ss_new_set_xx_obj_)))) 90)
                              (= (TA:round-05 (rad-to-deg (setq ss_new_set_xx_obj_rotation_ (vla-get-rotation  ss_new_set_xx_obj_)))) 270)
                            )
                        )
                        (progn
                          (LM:setdynpropvalue ss_new_set_xx_obj_ "length" (setq ss_new_set_xx_obj_length (- ss_new_set_xx_obj_length increment_length)))
                          (TA:move_axis_insertionpoint ss_new_set_xx_obj_ "Y" (- (/ increment_length 2)))
                          (princ "case4-2")
                        )
                      )
                    )  
                  )
                )
              )
              
              
              (setq ss_new_set_xx_i (+ ss_new_set_xx_i 1))
            )
          ;
        )
      ;

      ;
      ;
      (command "pselect"   "" )
    )
  )
  (defun c:steel_match_X_axis_stmax ()
    (setq steeL_ename_ (ssname (ssget "_+.:E:S") 0))
    (setq steel_obj_ (vlax-ename->vla-object steel_ename_))
    (setq steel_obj_ins_ (vlax-safearray->list (vlax-variant-value (vla-get-insertionpoint steel_obj_))))
    (while
      (/=
        (vl-princ-to-string
          (setq Er-msg_steel_target
            (vl-catch-all-apply 
              (function 
                (lambda () 
                  (setq steel_target_ (car (entsel "specifysteel_target Object")))
                )
              )
            )
          )
        )
        "#<%catch-all-apply-error%>"
      )
      (setq steel_target_obj_ (vlax-ename->vla-object steel_target_))
      (setq steel_target_obj_ins_ (vlax-safearray->list (vlax-variant-value (vla-get-insertionpoint steel_target_obj_))))
      (vla-copy steel_obj_)
      (vla-move steel_obj_ 
                (vlax-3d-point (setq steel_obj_ins_ (vlax-safearray->list (vlax-variant-value (vla-get-insertionpoint steel_obj_)))) )
                (vlax-3d-point 
                  (list 
                    (car steel_target_obj_ins_)
                    (cadr steel_obj_ins_)
                    (caddr steel_obj_ins_)
                  )
                )
      )
    )

  )
  (defun c:steel_match_Y_axis_stmay ()
    (setq steel_ename_ (car (entsel "specify Object")))
    (setq steel_obj_ (vlax-ename->vla-object steel_ename_))
    (setq steel_obj_ins_ (vlax-safearray->list (vlax-variant-value (vla-get-insertionpoint steel_obj_))))
    (while
      (/=
        (vl-princ-to-string
          (setq Er-msg_steel_target
            (vl-catch-all-apply 
              (function 
                (lambda () 
                  (setq steel_target_ (car (entsel "specifysteel_target Object")))
                )
              )
            )
          )
        )
        "#<%catch-all-apply-error%>"
      )
      (setq steel_target_obj_ (vlax-ename->vla-object steel_target_))
      (setq steel_target_obj_ins_ (vlax-safearray->list (vlax-variant-value (vla-get-insertionpoint steel_target_obj_))))
      (vla-copy steel_obj_)
      (vla-move steel_obj_ 
                (vlax-3d-point (setq steel_obj_ins_ (vlax-safearray->list (vlax-variant-value (vla-get-insertionpoint steel_obj_)))) )
                (vlax-3d-point 
                  (list 
                    (car steel_obj_ins_)
                    (cadr steel_target_obj_ins_)
                    (caddr steel_obj_ins_)
                  )
                )
      )
    )

  )
  (defun c:sssteel ()
    ;presetting
      (setq length_val_ 25)
    ;
    ;selection_set_for_fillter_blk_name
      (if  ;pre_select_ssget_or_post_select_ssget
        (=
          (setq ss_steel_tube_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_steel_tube_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_steel_tube_)
      )
      (setq ss_steel_tube_ (TA:EF_Filter_ss_set_ ss_steel_tube_ "000 - DYNAMIC_LENGTH+COMBINE+VIEW_ASSCESSORIES_STEEL_TUBE_COMBINE_SET"))
    ;
    (setq ERR_ nil)
    (while ;for keep insertion point and dist. fix length one side
      (and
        (= (vl-catch-all-error-p ERR_) nil)
      )
      (setq ERR_
        (vl-catch-all-apply
          (function
            (lambda ()
              (setq increment_num_ (cond ( (getint (strcat "\nSpecify sss_" (rtos ss_steel_tube_obj_length 2 2) " <" (rtos (setq increment_num_ (cond (increment_num_) (1.0) ) ) ) "> : " ) ) ) (increment_num_) ) )
            )
          )
        )
      )
      ;preloop_and_while
        (setq ss_steel_tube_i 0)
        (while 
          (and
            (= (vl-catch-all-error-p ERR_) nil)
            (< ss_steel_tube_i (sslength ss_steel_tube_))
          )
          (setq ss_steel_tube_ename_ (ssname ss_steel_tube_ ss_steel_tube_i)) 
          (setq ss_steel_tube_obj_ (vlax-ename->vla-object  ss_steel_tube_ename_))
          (setq ss_steel_tube_obj_rotation_ (vla-get-rotation  ss_steel_tube_obj_))
          (setq ss_steel_tube_obj_ins_ (vlax-safearray->list (vlax-variant-value (vla-get-insertionpoint ss_steel_tube_obj_))))
          (setq ss_steel_tube_obj_length (LM:getdynpropvalue ss_steel_tube_obj_ "length" ))
          
          (cond
            (;ssss_case_1
              (and
                  (= (vl-catch-all-error-p ERR_) nil)
                  (= (LM:getdynpropvalue ss_steel_tube_obj_ "view") "2_top_view" )
                  (= increment_num_ 1)
              )
              (progn
                (LM:setdynpropvalue ss_steel_tube_obj_ "length" (setq ss_steel_tube_obj_length (+ ss_steel_tube_obj_length length_val_)))
                (princ "ssss_case_1")
              )
            )
            (;ssss_case_2
              (and
                  (= (vl-catch-all-error-p ERR_) nil)
                  (= (LM:getdynpropvalue ss_steel_tube_obj_ "view") "2_top_view" )
                  (= increment_num_ 0)
              )
              (progn
                (LM:setdynpropvalue ss_steel_tube_obj_ "length" (setq ss_steel_tube_obj_length (- ss_steel_tube_obj_length length_val_)))
                (princ "ssss_case_2")
              )
            )
            (;ssss_case_3
              (and
                  (= (vl-catch-all-error-p ERR_) nil)
                  (= (LM:getdynpropvalue ss_steel_tube_obj_ "view") "2_top_view" )
                  (= increment_num_ -1)
              )
              (cond
                  (;case3-1
                     (and
                        (= (rad-to-deg (setq ss_steel_tube_obj_rotation_ (vla-get-rotation  ss_steel_tube_obj_))) 0)
                     )
                     (progn
                       (LM:setdynpropvalue ss_steel_tube_obj_ "length" (setq ss_steel_tube_obj_length (- ss_steel_tube_obj_length length_val_)))
                       (TA:move_axis_insertionpoint ss_steel_tube_obj_ "x" (+ length_val_))
                       (princ "case3-1")
                     )
                  )
                  (;case3-2
                     (and
                        (= (rad-to-deg (setq ss_steel_tube_obj_rotation_ (vla-get-rotation  ss_steel_tube_obj_))) 270)
                     )
                     (progn
                       (LM:setdynpropvalue ss_steel_tube_obj_ "length" (setq ss_steel_tube_obj_length (- ss_steel_tube_obj_length length_val_)))
                       (TA:move_axis_insertionpoint ss_steel_tube_obj_ "Y" (- length_val_))
                       (princ "case3-2")
                     )
                  )
                )
            )
            (;ssss_case_4
              (and
                  (= (vl-catch-all-error-p ERR_) nil)
                  (= (LM:getdynpropvalue ss_steel_tube_obj_ "view") "2_top_view" )
                  (= increment_num_ -2)
              )
              (progn
                (cond
                  (;case4-1
                     (and
                        (or 
                          (= (TA:round-05 (rad-to-deg (setq ss_steel_tube_obj_rotation_ (vla-get-rotation  ss_steel_tube_obj_)))) 0)
                          (= (TA:round-05 (rad-to-deg (setq ss_steel_tube_obj_rotation_ (vla-get-rotation  ss_steel_tube_obj_)))) 180)
                        )
                     )
                     (progn
                       (LM:setdynpropvalue ss_steel_tube_obj_ "length" (setq ss_steel_tube_obj_length (+ ss_steel_tube_obj_length length_val_)))
                       (TA:move_axis_insertionpoint ss_steel_tube_obj_ "x" (- length_val_))
                       (princ "case4-1")
                     )
                  )
                  (;case4-2
                     (and
                        (or 
                          (= (TA:round-05 (rad-to-deg (setq ss_steel_tube_obj_rotation_ (vla-get-rotation  ss_steel_tube_obj_)))) 90)
                          (= (TA:round-05 (rad-to-deg (setq ss_steel_tube_obj_rotation_ (vla-get-rotation  ss_steel_tube_obj_)))) 270)
                        )
                     )
                     (progn
                       (LM:setdynpropvalue ss_steel_tube_obj_ "length" (setq ss_steel_tube_obj_length (+ ss_steel_tube_obj_length length_val_)))
                       (TA:move_axis_insertionpoint ss_steel_tube_obj_ "Y" length_val_)
                       (princ "case4-2")
                     )
                  )
                )  
              )
            )
          )
          
          
          (setq ss_steel_tube_i (+ ss_steel_tube_i 1))
        )
      ;
    )
  )
  ;
  ;001 - DYNAMIC REC&SSQ SHAPE SOLID_centerpoint
  (defun c:PPLINE_300hk_ins300Ex()
    ;selection_set_for_fillter_blk_name
      (if  ;pre_select_ssget_or_post_select_ssget
        (=
          (setq ss_pre_filter_set_xx_ (ssget "i"
                                            (list
                                              (cons 0 "insert,lwpolyline,line") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "insert,lwpolyline,line") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ; (setq panel_width_ (cond ( (getreal (strcat "\nspecify distance_measure_ <" (rtos (setq panel_width_ (cond (panel_width_) (10) ) ) ) "> : " ) ) ) (panel_width_) ) )
    (setq new_line_Extrud_obj_angle (cond ( (getreal (strcat "\nspecify new_line_Extrud_obj_angle <" (rtos (setq new_line_Extrud_obj_angle (cond (new_line_Extrud_obj_angle) (10) ) ) ) "> : " ) ) ) (new_line_Extrud_obj_angle) ) )
    ;preloop_and_while
      (setq line_i 0)
      (setq line_ ss_pre_filter_set_xx_)
      (while (< line_i 1)
        (setq line_ename_ (ssname line_ line_i))
        (setq line_obj_ (vlax-ename->vla-object  line_ename_ ))
        (setq line_obj_obj_getboundingbox (TA:ss_vla-getboundingbox ss_pre_filter_set_xx_))
        (setq line_obj_min_ (car line_obj_obj_getboundingbox)) 
        (setq line_obj_max_ (cadr line_obj_obj_getboundingbox))
        (setvar "osmode" 0)
        (command "rectangle" line_obj_min_ line_obj_max_)
        (setvar "osmode" 1215)
          ;main_idea_coding_code
            (if (= 1 1)
              (progn
                ;standard properties line
                (setq line_obj_midpt_ (LM:PolyCentroid (entlast)))
                (vla-delete (vlax-ename->vla-object (entlast)))
                (setq line_obj_midpt_ (list (car line_obj_midpt_ ) (cadr line_obj_midpt_ ) 0))
                ; (setq line_obj_angle (rad-to-deg (vla-get-angle line_obj_ )))
                (setq new_line_obj_angle new_line_Extrud_obj_angle)
                (setq REC-length_ (list line_obj_min_ line_obj_max_))
                (setq line_obj_length (distance (car REC-length_) (list (car (cadr REC-length_)) (cadr (car REC-length_)))   ))
                (setq panel_width_ (distance (car REC-length_) (list (car (car REC-length_)) (cadr (cadr REC-length_)))   ))
                ;
                ;insertion process
                  (TA:vla-insertblock 
                    "001 - DYNAMIC REC&SSQ SHAPE SOLID_centerpoint"
                    (if (= (getvar "worlducs") 0)(progn (trans line_obj_midpt_ 0 1)) line_obj_midpt_ ) 
                    1
                    (deg-to-rad new_line_obj_angle)
                  )
                  ;new_blk_entlast object
                    (setq new300HK_ename (entlast))
                    (setq new300HK_obj_ (vlax-ename->vla-object new300HK_ename))
                    ;input data
                      (cond
                        (;total_length_process_case_1
                          (and
                              ; (> line_obj_length 3000)
                              (= (LM:effectivename new300HK_obj_) "001 - DYNAMIC REC&SSQ SHAPE SOLID_centerpoint" )
                              (= "this dynamic block was create by me" "this dynamic block was create by me")
                          )
                          (progn
                            ; (LM:setdynpropvalue new300HK_obj_ "view" "DAFT")
                            (LM:setdynpropvalue new300HK_obj_ "H" line_obj_length)
                            (LM:setdynpropvalue new300HK_obj_ "W" panel_width_)
                            (command "draworder" new300HK_ename "" "F" )
                            
                            (princ "total_length_process_case_1")
                          )
                        )
                        (;total_length_process_case_2
                          (and
                              (> line_obj_length 3000)
                              (= (LM:effectivename new300HK_obj_) "001 - DYNAMIC REC&SSQ SHAPE SOLID_centerpoint" )
                              (/= "this dynamic block was create by me" "this dynamic block was create by me")
                          )
                          (progn
                            (princ "total_length_process_case_2")
                          )
                        )
                      )    
                    ;
                  ;
                ;
              )
            )
          ;
        (setq line_i (+ line_i 1))
      )
    ;

  )
  ;
  ;000 - DYNAMIC_ARRAY+COMBINE+VIEW_ASSCESSORIES_FAMELINE_AL.CELL_CELING_PANEL_300HK_COMBINE_SET
  (defun c:PPLINE_300hk_ins300hk ()
    ;selection_set_for_fillter_blk_name
      (if  ;pre_select_ssget_or_post_select_ssget
        (=
          (setq ss_pre_filter_set_xx_ (ssget "i"
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq panel_width_ (cond ( (getreal (strcat "\nspecify distance_measure_ <" (rtos (setq panel_width_ (cond (panel_width_) (10) ) ) ) "> : " ) ) ) (panel_width_) ) )
    ;preloop_and_while
      (setq line_i 0)
      (setq line_ ss_pre_filter_set_xx_)
      (while (< line_i (sslength line_))
        (setq line_ename_ (ssname line_ line_i))
        (setq line_obj_ (vlax-ename->vla-object  line_ename_ ))
          ;main_idea_coding_code
            (if (= (vla-get-objectname line_obj_) "AcDbLine")
              (progn
                ;standard properties line
                (setq line_obj_start_end_pt_ (list
                                                (setq line_obj_startpt_ (vlax-safearray->list
                                                                          (vlax-variant-value ( vla-get-startpoint line_obj_ ))
                                                                        )
                                                )
                                                (setq line_obj_endpt_ (vlax-safearray->list
                                                                          (vlax-variant-value ( vla-get-endpoint line_obj_ ))
                                                                      )
                                                )
                                              )
                )
                (setq line_obj_midpt_ (TA:midpoint line_obj_startpt_ line_obj_endpt_))
                (setq line_obj_angle (rad-to-deg (vla-get-angle line_obj_ )))
                (setq new_line_obj_angle (TA:ModifyRotation line_obj_angle -90))
                (setq line_obj_length (vla-get-length line_obj_))
                ;
                ;insertion process
                  (TA:vla-insertblock "000 - DYNAMIC_ARRAY+COMBINE+VIEW_ASSCESSORIES_FAMELINE_AL.CELL_CELING_PANEL_300HK_@400mm_COMBINE_SET" line_obj_midpt_ 1 (deg-to-rad new_line_obj_angle) )
                  ;new_blk_entlast object
                    (setq new300HK_ename (entlast))
                    (setq new300HK_obj_ (vlax-ename->vla-object new300HK_ename))
                    ;input data
                      (cond
                        (;total_length_process_case_1
                          (and
                              ; (> line_obj_length 3000)
                              (= (LM:effectivename new300HK_obj_) "000 - DYNAMIC_ARRAY+COMBINE+VIEW_ASSCESSORIES_FAMELINE_AL.CELL_CELING_PANEL_300HK_@400mm_COMBINE_SET" )
                              (= "this dynamic block was create by me" "this dynamic block was create by me")
                          )
                          (progn
                            (LM:setdynpropvalue new300HK_obj_ "view" "2_top_view")
                            (LM:setdynpropvalue new300HK_obj_ "array_panel_length" line_obj_length)
                            (LM:setdynpropvalue new300HK_obj_ "panel_width" panel_width_)
                            (command "draworder" new300HK_ename "" "F" )
                            
                            (princ "total_length_process_case_1")
                          )
                        )
                        (;total_length_process_case_2
                          (and
                              (> line_obj_length 3000)
                              (= (LM:effectivename new300HK_obj_) "000 - DYNAMIC_ARRAY+COMBINE+VIEW_ASSCESSORIES_FAMELINE_AL.CELL_CELING_PANEL_300HK_@400mm_COMBINE_SET" )
                              (/= "this dynamic block was create by me" "this dynamic block was create by me")
                          )
                          (progn
                            (princ "total_length_process_case_2")
                          )
                        )
                      )    
                    ;
                  ;
                ;
              )
            )
          ;
        (setq line_i (+ line_i 1))
      )
    ;

  )
  (defun c:PPLINE_300hk_ins300hdaft ()
    ;selection_set_for_fillter_blk_name
      (if  ;pre_select_ssget_or_post_select_ssget
        (=
          (setq ss_pre_filter_set_xx_ (ssget "i"
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ; (setq panel_width_ (cond ( (getreal (strcat "\nspecify distance_measure_ <" (rtos (setq panel_width_ (cond (panel_width_) (10) ) ) ) "> : " ) ) ) (panel_width_) ) )
    (setq new_line_panel_obj_angle (cond ( (getreal (strcat "\nspecify new_line_panel_obj_angle <" (rtos (setq new_line_panel_obj_angle (cond (new_line_panel_obj_angle) (10) ) ) ) "> : " ) ) ) (new_line_panel_obj_angle) ) )
    ;preloop_and_while
      (setq line_i 0)
      (setq line_ ss_pre_filter_set_xx_)
      (while (< line_i (sslength line_))
        (setq line_ename_ (ssname line_ line_i))
        (setq line_obj_ (vlax-ename->vla-object  line_ename_ ))
        (setq line_obj_obj_getboundingbox (vla-getboundingbox line_obj_ 'min_ 'max_)) 
        (setq line_obj_min_ (vlax-safearray->list min_)) 
        (setq line_obj_max_ (vlax-safearray->list max_)) 
        
          ;main_idea_coding_code
            (if (= (vla-get-objectname line_obj_) "AcDbPolyline")
              (progn
                ;standard properties line
                (setq line_obj_midpt_ (LM:PolyCentroid line_ename_))
                (setq line_obj_midpt_ (list (car line_obj_midpt_ ) (cadr line_obj_midpt_ ) 0))
                ; (setq line_obj_angle (rad-to-deg (vla-get-angle line_obj_ )))
                (setq new_line_obj_angle new_line_panel_obj_angle)
                (setq REC-length_ (list line_obj_min_ line_obj_max_))
                (setq line_obj_length (distance (car REC-length_) (list (car (cadr REC-length_)) (cadr (car REC-length_)))   ))
                (setq panel_width_ (distance (car REC-length_) (list (car (car REC-length_)) (cadr (cadr REC-length_)))   ))
                ;
                ;insertion process
                  (TA:vla-insertblock 
                    "000 - DYNAMIC_ARRAY+COMBINE+VIEW_ASSCESSORIES_FAMELINE_AL.CELL_CELING_PANEL_300HK_@400mm_COMBINE_SET"
                    (if (= (getvar "worlducs") 0)(progn (trans line_obj_midpt_ 1 1)) line_obj_midpt_ )
                    1
                    (deg-to-rad new_line_obj_angle)
                  )
                  ;new_blk_entlast object
                    (setq new300HK_ename (entlast))
                    (setq new300HK_obj_ (vlax-ename->vla-object new300HK_ename))
                    ;input data
                      (cond
                        (;total_length_process_case_1
                          (and
                              ; (> line_obj_length 3000)
                              (= (LM:effectivename new300HK_obj_) "000 - DYNAMIC_ARRAY+COMBINE+VIEW_ASSCESSORIES_FAMELINE_AL.CELL_CELING_PANEL_300HK_@400mm_COMBINE_SET" )
                              (= "this dynamic block was create by me" "this dynamic block was create by me")
                          )
                          (progn
                            (LM:setdynpropvalue new300HK_obj_ "view" "DAFT")
                            (LM:setdynpropvalue new300HK_obj_ "array_panel_length" line_obj_length)
                            (LM:setdynpropvalue new300HK_obj_ "panel_width" panel_width_)
                            (command "draworder" new300HK_ename "" "F" )
                            
                            (princ "total_length_process_case_1")
                          )
                        )
                        (;total_length_process_case_2
                          (and
                              (> line_obj_length 3000)
                              (= (LM:effectivename new300HK_obj_) "000 - DYNAMIC_ARRAY+COMBINE+VIEW_ASSCESSORIES_FAMELINE_AL.CELL_CELING_PANEL_300HK_@400mm_COMBINE_SET" )
                              (/= "this dynamic block was create by me" "this dynamic block was create by me")
                          )
                          (progn
                            (princ "total_length_process_case_2")
                          )
                        )
                      )    
                    ;
                  ;
                ;
              )
            )
          ;
        (setq line_i (+ line_i 1))
      )
    ;

  )
  (defun c:insdaft ()
    (TA:vla-insertblock 
      ; "000 - DYNAMIC_ARRAY+COMBINE+VIEW_ASSCESSORIES_PLAN_AL.SOLID_SHEET_HAT-PROFILE_VA_COMBINE_SET" ;original
      "000 - DYNAMIC_ARRAY_ASSCESSORIES_FAMELINE_AL.CELL_CELING_PANEL_300HK-VA_@400mm_BOTTOM_VIEW"
      (setq newpt_ (getpoint "input point"))
      1
      (setq new_ang (angle newpt_ (setq newpt2_ (getpoint newpt_ "input angle")) ) )  
    )
    ;new_blk_entlast object
      (setq newblk_ename (entlast))
      (setq newblk_obj (vlax-ename->vla-object newblk_ename))
      (vla-put-rotation newblk_obj (deg-to-rad (TA:ModifyRotation (rad-to-deg new_ang) -90)))
      (LM:setdynpropvalue newblk_obj "distance1" (distance newpt_ newpt2_)) 
      (LM:setdynpropvalue newblk_obj "distance2" (* (getdist newpt_) 2)) 
    ;
  )
  (defun c:PPLINE_300hk_strech_300st ()
    ;selection_set_for_fillter_blk_name
      (if  ;pre_select_ssget_or_post_select_ssget
        (=
          (setq c011_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq c011_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength c011_)
      )
      (setq c011_ (TA:EF_Filter_ss_set_ c011_ "000 - DYNAMIC_ARRAY+COMBINE+VIEW_ASSCESSORIES_FAMELINE_AL.CELL_CELING_PANEL_300HK_@400mm_COMBINE_SET"))
    ;
    

    (setq ERR_ nil)
    (while ;for keep insertion point and dist. fix length one side
      (and
        (= (vl-catch-all-error-p ERR_) nil)
      )
      (setq ERR_
        (vl-catch-all-apply
          (function
            (lambda ()
              (setq increment_num_ (cond ( (getint (strcat "\nSpecify sss_   <" (rtos (setq increment_num_ (cond (increment_num_) (1.0) ) ) ) "> : " ) ) ) (increment_num_) ) )
            )
          )
        )
      )
      ;preloop_and_while
        (setq c011_i 0)
        (while 
          (and
            (= (vl-catch-all-error-p ERR_) nil)
            (< c011_i (sslength c011_))
          )
          (setq c011_ename_ (ssname c011_ c011_i))
          (setq c011_obj_ (vlax-ename->vla-object  c011_ename_))
          (setq c011_obj_ins_ (vlax-safearray->list (vlax-variant-value (vla-get-insertionpoint c011_obj_))))
          (setq c011_obj_fragment_mid_ (LM:getdynpropvalue c011_obj_ "array_panel_length" ))
          
          (cond
            (;ssss_case_1
              (and
                  (= (vl-catch-all-error-p ERR_) nil)
                  ; (= (LM:getdynpropvalue c011_obj_ "view") "7_dynamic_length_view" )
                  (= increment_num_ 1)
              )
              (progn
                (LM:setdynpropvalue c011_obj_ "array_panel_length" (setq c011_obj_fragment_mid_ (+ c011_obj_fragment_mid_ 400)))
                (TA:move_polar_insertionpoint  c011_obj_ "x" +200)
                (princ "ssss_case_1")
              )
            )
            (;ssss_case_2
              (and
                  (= (vl-catch-all-error-p ERR_) nil)
                  ; (= (LM:getdynpropvalue c011_obj_ "view") "7_dynamic_length_view" )
                  (= increment_num_ 0)
              )
              (progn
                (LM:setdynpropvalue c011_obj_ "array_panel_length" (setq c011_obj_fragment_mid_ (- c011_obj_fragment_mid_ 400)))
                (TA:move_polar_insertionpoint  c011_obj_ "x" -200)
                (princ "ssss_case_2")
              )
            )
            (;ssss_case_3
              (and
                  (= (vl-catch-all-error-p ERR_) nil)
                  ; (= (LM:getdynpropvalue c011_obj_ "view") "7_dynamic_length_view" )
                  (< increment_num_ 0)
              )
              (progn
                (LM:setdynpropvalue c011_obj_ "array_panel_length" (setq c011_obj_fragment_mid_ (+ c011_obj_fragment_mid_ (* increment_num_ 400))))
                (TA:move_polar_insertionpoint  c011_obj_ "x" (* 200 increment_num_))
                (princ "ssss_case_3")
              )
            )
            (;ssss_case_4
              (and
                  (= (vl-catch-all-error-p ERR_) nil)
                  ; (= (LM:getdynpropvalue c011_obj_ "view") "7_dynamic_length_view" )
                  (> increment_num_ 1)
              )
              (progn
                (LM:setdynpropvalue c011_obj_ "array_panel_length" (setq c011_obj_fragment_mid_ (+ c011_obj_fragment_mid_ (* increment_num_ 400))))
                (TA:move_polar_insertionpoint  c011_obj_ "x" (* 200 increment_num_))
                (princ "ssss_case_3")
              )
            )
          )
          
          
          (setq c011_i (+ c011_i 1))
        )
      ;

    )
    
    
  )
  (defun c:PPLINE_300hk_300edge ()
    (setq pt_dist_2-3mid nil)
    (setq pt_dist_1_ (getpoint ))
    (setq pt_dist_2_ (getpoint pt_dist_1_))
    (setq pt_dist_3_ (getpoint pt_dist_2_))
    (setq pt_dist_ovl_ (* (fix ( / (LM:roundup (distance pt_dist_2_ pt_dist_3_ ) 1) 25)) 25))
    (setq pt_dist_2+75 (polar pt_dist_2_ (angle pt_dist_2_ pt_dist_3_ ) 75))
    (setq pt_dist_2-3 (polar pt_dist_2+75 (angle pt_dist_2_ pt_dist_3_ ) (- pt_dist_ovl_   75)))
    (setq pt_dist_3-offset_ (polar pt_dist_2-3 (angle  pt_dist_3_ pt_dist_2_) (getint "input offset ")))
    (setq pt_dist_2-3mid (polar pt_dist_2+75 (angle pt_dist_2_ pt_dist_3_ ) (/ (distance pt_dist_2+75 pt_dist_3-offset_) 2 )))
    ; (command "point" pt_dist_2+75 )
    ; (command "point" pt_dist_2-3 )
    ; (command "point" pt_dist_3-100_ )
    ; (command "point" pt_dist_2-3mid )
    (if (and 
          (/= pt_dist_2-3mid nil)
        )
      (progn
        (TA:vla-insertblock 
          "000 - DYNAMIC_ARRAY+COMBINE+VIEW_ASSCESSORIES_FAMELINE_AL.CELL_CELING_PANEL_300HK_@400mm_COMBINE_SET"
          pt_dist_2-3mid
          1
          (cond
            ((= (TA:round-05 (rad-to-deg (angle pt_dist_2_ pt_dist_3_ ) )) 270)
              (progn
                (deg-to-rad 90)
              )
            )
            ((= (TA:round-05 (rad-to-deg (angle pt_dist_2_ pt_dist_3_ ) )) 90)
              (progn
                (deg-to-rad 90)
              )
            )
            ((or 
               (= (TA:round-05 (rad-to-deg (angle pt_dist_2_ pt_dist_3_ ) )) 0)
               (= (TA:round-05 (rad-to-deg (angle pt_dist_2_ pt_dist_3_ ) )) 180)
             )
              (progn
                (deg-to-rad 0)
              )
            )
          )
        )
        ;new_blk_entlast object
          (setq new300hd_ename (entlast))
          (setq new300hd_obj_ (vlax-ename->vla-object new300hd_ename))
          (setq new300hd_obj_ins_ (vlax-safearray->list (vlax-variant-value (vla-get-insertionpoint new300hd_obj_))))
          (LM:setdynpropvalue new300hd_obj_ "view" "DAFT")
          (LM:setdynpropvalue new300hd_obj_ "panel_width" (distance pt_dist_2+75 pt_dist_3-offset_ ))
        ;
      )
    )
    (setq ERR_ nil)
    (setq first-time nil)
    (while ;for keep insertion point and dist. fix length one side
      (and
        (= (vl-catch-all-error-p ERR_) nil)
      )
      (if (= first-time nil)
        (progn
          (setq ERR_
            (vl-catch-all-apply
              (function
                (lambda ()
                  (setq increment_num_ (cond ( (getdist new300hd_obj_ins_ (strcat "\nSpecify sss_   <" (rtos (setq increment_num_ (cond (increment_num_) (1.0) ) ) ) "> : " ) ) ) (increment_num_) ) )
                  (setq increment_num_ (/ (/ (* (fix (/ (* increment_num_ 2) 400)) 400) 400) 2) )
                  (setq first-time 1)
                )
              )
            )
          )
        )
        (setq ERR_
          (vl-catch-all-apply
            (function
              (lambda ()
                (setq increment_num_ (cond ( (getint (strcat "\nSpecify sss_   <" (rtos (setq increment_num_ (cond (increment_num_) (1.0) ) ) ) "> : " ) ) ) (increment_num_) ) )
              )
            )
          )
        )
      )
      ;preloop_and_while
        (setq c011_i 0)
        (while 
          (and
            (= (vl-catch-all-error-p ERR_) nil)
            (< c011_i 1)
            (= (LM:effectivename new300hd_obj_ ) "000 - DYNAMIC_ARRAY+COMBINE+VIEW_ASSCESSORIES_FAMELINE_AL.CELL_CELING_PANEL_300HK_@400mm_COMBINE_SET" )
            (= (LM:effectivename new300hd_obj_ ) "000 - DYNAMIC_ARRAY+COMBINE+VIEW_ASSCESSORIES_FAMELINE_AL.CELL_CELING_PANEL_300HK_@400mm_COMBINE_SET" )
          )
          (setq c011_obj_ new300hd_obj_)
          (setq c011_obj_ins_ (vlax-safearray->list (vlax-variant-value (vla-get-insertionpoint c011_obj_))))
          (setq c011_obj_fragment_mid_ (LM:getdynpropvalue c011_obj_ "array_panel_length" ))
          
          (cond
            (;ssss_case_1
              (and
                  (= (vl-catch-all-error-p ERR_) nil)
                  ; (= (LM:getdynpropvalue c011_obj_ "view") "7_dynamic_length_view" )
                  (= increment_num_ 1)
              )
              (progn
                (LM:setdynpropvalue c011_obj_ "array_panel_length" (setq c011_obj_fragment_mid_ (+ c011_obj_fragment_mid_ 400)))
                (TA:move_polar_insertionpoint  c011_obj_ "x" +200)
                (princ "ssss_case_1")
              )
            )
            (;ssss_case_2
              (and
                  (= (vl-catch-all-error-p ERR_) nil)
                  ; (= (LM:getdynpropvalue c011_obj_ "view") "7_dynamic_length_view" )
                  (= increment_num_ 0)
              )
              (progn
                (LM:setdynpropvalue c011_obj_ "array_panel_length" (setq c011_obj_fragment_mid_ (- c011_obj_fragment_mid_ 400)))
                (TA:move_polar_insertionpoint  c011_obj_ "x" -200)
                (princ "ssss_case_2")
              )
            )
            (;ssss_case_3
              (and
                  (= (vl-catch-all-error-p ERR_) nil)
                  ; (= (LM:getdynpropvalue c011_obj_ "view") "7_dynamic_length_view" )
                  (< increment_num_ 0)
              )
              (progn
                (LM:setdynpropvalue c011_obj_ "array_panel_length" (setq c011_obj_fragment_mid_ (+ c011_obj_fragment_mid_ (* increment_num_ 400))))
                (TA:move_polar_insertionpoint  c011_obj_ "x" (* 200 increment_num_))
                (princ "ssss_case_3")
              )
            )
            (;ssss_case_4
              (and
                  (= (vl-catch-all-error-p ERR_) nil)
                  ; (= (LM:getdynpropvalue c011_obj_ "view") "7_dynamic_length_view" )
                  (> increment_num_ 1)
              )
              (progn
                (LM:setdynpropvalue c011_obj_ "array_panel_length" (setq c011_obj_fragment_mid_ (+ c011_obj_fragment_mid_ (* increment_num_ 400))))
                (TA:move_polar_insertionpoint  c011_obj_ "x" (* 200 increment_num_))
                (princ "ssss_case_3")
              )
            )
          )
          
          
          (setq c011_i (+ c011_i 1))
        )
      ;

    )
    
  )
  ;
  ;000 - 000TYP-LINE_AND_ARRAY_400mm.
  (defun c:PPLINE_300hk_ins300daft ()
    ;selection_set_for_fillter_blk_name
      (if  ;pre_select_ssget_or_post_select_ssget
        (=
          (setq ss_pre_filter_set_xx_ (ssget "i"
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "line") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq panel_width_ (cond ( (getreal (strcat "\nspecify distance_measure_ <" (rtos (setq panel_width_ (cond (panel_width_) (10) ) ) ) "> : " ) ) ) (panel_width_) ) )
    ;preloop_and_while
      (setq line_i 0)
      (setq line_ ss_pre_filter_set_xx_)
      (while (< line_i (sslength line_))
        (setq line_ename_ (ssname line_ line_i))
        (setq line_obj_ (vlax-ename->vla-object  line_ename_ ))
          ;main_idea_coding_code
            (if (= (vla-get-objectname line_obj_) "AcDbLine")
              (progn
                ;standard properties line
                (setq line_obj_start_end_pt_ (list
                                                (setq line_obj_startpt_ (vlax-safearray->list
                                                                          (vlax-variant-value ( vla-get-startpoint line_obj_ ))
                                                                        )
                                                )
                                                (setq line_obj_endpt_ (vlax-safearray->list
                                                                          (vlax-variant-value ( vla-get-endpoint line_obj_ ))
                                                                      )
                                                )
                                              )
                )
                (setq line_obj_midpt_ (TA:midpoint line_obj_startpt_ line_obj_endpt_))
                (setq line_obj_angle (rad-to-deg (vla-get-angle line_obj_ )))
                ; (setq new_line_obj_angle (TA:ModifyRotation line_obj_angle -90)) ;องศาตามจริง ไม่คำนวณเผื่อ
                (setq new_line_obj_angle line_obj_angle)
                (setq line_obj_length (vla-get-length line_obj_))
                ;
                ;insertion process
                  (TA:vla-insertblock "000TYP-LINE_AND_ARRAY_400mm." line_obj_midpt_ 1 (deg-to-rad new_line_obj_angle) )
                  ;new_blk_entlast object
                    (setq new300HK_ename (entlast))
                    (setq new300HK_obj_ (vlax-ename->vla-object new300HK_ename))
                    ;input data
                      (cond
                        (;total_length_process_case_1
                          (and
                              ; (> line_obj_length 3000)
                              (= (LM:effectivename new300HK_obj_) "000TYP-LINE_AND_ARRAY_400mm." )
                              (= "this dynamic block was create by me" "this dynamic block was create by me")
                          )
                          (progn
                            (LM:setdynpropvalue new300HK_obj_ "DEPT. LINE" "thk.")
                            (LM:setdynpropvalue new300HK_obj_ "array_width" line_obj_length)
                            (LM:setdynpropvalue new300HK_obj_ "thk.pline" 300)
                            (LM:setdynpropvalue new300HK_obj_ "H" panel_width_)
                            (command "draworder" new300HK_ename "" "F" )
                            
                            (princ "total_length_process_case_1")
                          )
                        )
                        (;total_length_process_case_2
                          (and
                              (> line_obj_length 3000)
                              (= (LM:effectivename new300HK_obj_) "000 - DYNAMIC_ARRAY+COMBINE+VIEW_ASSCESSORIES_FAMELINE_AL.CELL_CELING_PANEL_300HK_@400mm_COMBINE_SET" )
                              (/= "this dynamic block was create by me" "this dynamic block was create by me")
                          )
                          (progn
                            (princ "total_length_process_case_2")
                          )
                        )
                      )    
                    ;
                  ;
                ;
              )
            )
          ;
        (setq line_i (+ line_i 1))
      )
    ;
  )
  ;
  ;000 - DYNAMIC_COMBINE+VIEW_ASSCESSORIES_FAMELINE_GALV.BRACKET_FITTING_Z-PROFILE_HR-02AA_COMBINE_VIEW
  (defun c:PPLINE_300HK_insHRtopview_ ()
    (setq 300HK_ename_ (car (entsel "specify Object")))
    
    (setq 300HK_obj_ (vlax-ename->vla-object 300HK_ename_))
    ;main_idea_coding_code
      (if (or 
            (= (LM:Effectivename 300hk_obj_) "000 - DYNAMIC_ARRAY+COMBINE+VIEW_ASSCESSORIES_FAMELINE_AL.CELL_CELING_PANEL_300HK_COMBINE_SET")
            (= (LM:Effectivename 300hk_obj_) "000 - DYNAMIC_ARRAY+COMBINE+VIEW_ASSCESSORIES_FAMELINE_AL.CELL_CELING_PANEL_300HK_@400mm_COMBINE_SET")
            (= (LM:Effectivename 300hk_obj_) "000 - DYNAMIC_ARRAY+COMBINE+VIEW_ASSCESSORIES_FAMELINE_AL.CELL_CELING_PANEL_360HK_@372mm_COMBINE_SET")
            (= (LM:Effectivename 300hk_obj_) "000 - DYNAMIC_ARRAY+COMBINE+VIEW_ASSCESSORIES_FAMELINE_AL.CELL_CELING_PANEL_300HK_@310mm_COMBINE_SET")
            (= (LM:Effectivename 300hk_obj_) "000 - DYNAMIC_ARRAY+COMBINE+VIEW_ASSCESSORIES_FAMELINE_AL.CELL_CELING_PANEL_300HK_COMBINE_SET_startpoint_")
          )
        (progn
          ;get_ex-insertion_pt_300HK
            (list 
              (setq HR-02A_top_point_x (LM:getdynpropvalue 300hk_obj_ "HR-02A_top_point x" ) )
              (setq HR-02A_top_point_y (LM:getdynpropvalue 300hk_obj_ "HR-02A_top_point y" ) )
            )
            (list 
              (setq HR-02B_top_point_x (LM:getdynpropvalue 300hk_obj_ "HR-02B_top_point x" ) ) 
              (setq HR-02B_top_point_y (LM:getdynpropvalue 300hk_obj_ "HR-02B_top_point Y" ) )
            )
            (setq 300hk_obj_ins_ (vlax-safearray->list (vlax-variant-value (vla-get-insertionpoint 300hk_obj_))))
            ; (if (= (LM:Effectivename 300hk_obj_) "000 - DYNAMIC_ARRAY+COMBINE+VIEW_ASSCESSORIES_FAMELINE_AL.CELL_CELING_PANEL_300HK_COMBINE_SET_startpoint_")
            ;   (progn
            ;     (vlax-curve-getpointatdist 300hk_obj_ )
            ;   )
            ;   (setq 300hk_obj_ins_ (vlax-safearray->list (vlax-variant-value (vla-get-insertionpoint 300hk_obj_))))
            ; )
            (setq 300hk_obj_rotation_ (TA:ModifyRotation (rad-to-deg (vla-get-rotation 300hk_obj_ ) ) 180))
          ;
          ;insertion_panel_insertion_point_
            (setq HR-02A_top_point_preins_ (list 
                                              (+ ( car 300hk_obj_ins_ ) HR-02A_top_point_x  )
                                              (+ ( cadr 300hk_obj_ins_ ) 0  )
                                            )
            )
            (setq HR-02B_top_point_preins_ (list 
                                              (+ ( car 300hk_obj_ins_ ) HR-02B_top_point_x  )
                                              (+ ( cadr 300hk_obj_ins_ ) 0  )
                                            )
            )
          ;
          ;get_dynamic_data_
            (setq array_panel_length (- (LM:getdynpropvalue 300hk_obj_ "array_panel_length") 100))
          ; 
          ;insertion_HR_side_A
            (TA:vla-insertblock 
              "000 - DYNAMIC_COMBINE+VIEW_ASSCESSORIES_FAMELINE_GALV.BRACKET_FITTING_Z-PROFILE_HR-02AA_COMBINE_VIEW"
               (if (= (getvar "worlducs") 0)(progn (trans HR-02A_top_point_preins_ 1 1)) HR-02A_top_point_preins_ )
              1
              (deg-to-rad 90)
            ) 
            (setq new_ename_ (entlast))
            (setq new_obj_ (vlax-ename->vla-object new_ename_)) 
            
            (setvar "osmode" 0)
            (command "rotate" 
                     new_ename_
                     ""
                     (if (= (getvar "worlducs") 0) (progn (trans 300hk_obj_ins_ 0 1)) 300hk_obj_ins_ )
                     (rad-to-deg (vla-get-rotation 300hk_obj_))
            )  
            (LM:setdynpropvalue new_obj_ "view" "2_top_view")
            (TA:move_axis_insertionpoint new_obj_ "x" -25)
            (setq array_length (LM:setdynpropvalue new_obj_ "array_length" (* (fix (/ array_panel_length 2400)) 2400 ) ))
            (cond ;visibility&length condition
              ( ;visibility condition
                (or 
                  (> array_panel_length 3000)
                )
                (progn
                  (LM:setdynpropvalue new_obj_ "view" "2_top_view")
                  (LM:setdynpropvalue 
                    new_obj_ 
                    "fragment_left"   
                    (if (and (= (- array_panel_length array_length) 0)) ;condition for input fragment left/right value
                      (progn
                        0
                      )
                      (if (> 0 (- (/ (- array_panel_length array_length ) 2) 50) )
                        (progn
                          0
                        )
                        (+ (/ (- array_panel_length array_length ) 2) 11)
                      )
                    )
                  )
                  (LM:setdynpropvalue 
                    new_obj_ 
                    "fragment_right"   
                    (if (= (- array_panel_length array_length) 0) ;condition for input fragment left/right value
                      (progn
                        0
                      )
                      (if (> 0 (- (/ (- array_panel_length array_length ) 2) 50) )
                        (progn
                          0
                        )
                        (- (/ (- array_panel_length array_length ) 2) 50)
                      )
                    )
                  )
                )
              )
              ( ;visibility condition
                (and 
                  (< array_panel_length 3000) 
                  
                )
                (progn
                  (LM:setdynpropvalue new_obj_ "view" "7_dynamic_length_view")
                  (LM:setdynpropvalue 
                    new_obj_ 
                    "fragment_middle"   
                    (- array_panel_length 50)
                  )
                )
              )
            )
          ;
          ;
          ;insertion_HR_side_B
            (TA:vla-insertblock 
              "000 - DYNAMIC_COMBINE+VIEW_ASSCESSORIES_FAMELINE_GALV.BRACKET_FITTING_Z-PROFILE_HR-02B_COMBINE_VIEW"
              (if (= (getvar "worlducs") 0)(progn (trans HR-02B_top_point_preins_ 1 1)) HR-02B_top_point_preins_ ) 
              1
              (deg-to-rad 90)
            )
            (setq new_ename_ (entlast))
            (setq new_obj_ (vlax-ename->vla-object new_ename_))   
            (command "rotate" 
                     new_ename_
                     ""
                     (if (= (getvar "worlducs") 0) (progn (trans 300hk_obj_ins_ 0 1)) 300hk_obj_ins_ ) 
                     (rad-to-deg (vla-get-rotation 300hk_obj_))
            )
            (LM:setdynpropvalue new_obj_ "view" "2_top_view")
            ;rev
            (if (is-even-number (/ (/ (fix (LM:getdynpropvalue 300hk_obj_ "array_panel_length" )) 400 ) 2.0 ))
              (progn
                (TA:move_axis_insertionpoint new_obj_ "x" 0)
                
              )
              (TA:move_axis_insertionpoint new_obj_ "x" -200)
            )
            
            (if (and 
                  (> (- (* (fix (/ array_panel_length 2400)) 2400 ) 2400) 0)
                  (/= (is-even-number (float (/ (/ (fix (LM:getdynpropvalue 300hk_obj_ "array_panel_length" )) 400 ) 2.0))) T)
                )
              (progn
                (setq array_length (LM:setdynpropvalue new_obj_ "array_length" (- (* (fix (/ array_panel_length 2400)) 2400 ) 2400) ))
              )
              (setq array_length (LM:setdynpropvalue new_obj_ "array_length" (* (fix (/ array_panel_length 2400)) 2400 ) ))
            )
            ;
            (cond ;visibility&length condition
            ( ;visibility condition
              (and
                (/= (rtos (LM:getdynpropvalue 300HK_obj_ "array_panel_length"  ) 2 2 ) (rtos 2800 2 2))     
                (> array_panel_length 2401)
                (is-even-number (/ (/ (LM:getdynpropvalue 300hk_obj_ "array_panel_length" ) 400 ) 2.0 ))
                
              )
              (progn
                (LM:setdynpropvalue new_obj_ "view" "2_top_view")
                (LM:setdynpropvalue 
                  new_obj_ 
                  "fragment_left"   
                  (if (= (- array_panel_length array_length) 0) ;condition for input fragment left/right value
                    (progn
                      0
                    )
                    (if (< (- (/ (- array_panel_length array_length ) 2) 50) 0)
                      (progn
                        0
                      )
                      (+ 36 (- (/ (- array_panel_length array_length ) 2) 50))
                    )
                  )
                )
                (LM:setdynpropvalue 
                  new_obj_ 
                  "fragment_right"   
                  (if (= (- array_panel_length array_length) 0) ;condition for input fragment left/right value
                    (progn
                      0
                    )
                    (- (/ (- array_panel_length array_length ) 2) 14)
                  )
                )
              )
              
            )
            ( ;visibility condition no move 200
              (and
                (/= (rtos (LM:getdynpropvalue 300HK_obj_ "array_panel_length"  ) 2 2 ) (rtos 2800 2 2))     
                (> array_panel_length 2401)
                (/= (is-even-number (/ (/ (LM:getdynpropvalue 300hk_obj_ "array_panel_length" ) 400 ) 2.0 )) T)
              )
              
              (progn
                (LM:setdynpropvalue new_obj_ "view" "2_top_view")
                (LM:setdynpropvalue 
                  new_obj_ 
                  "fragment_left"   
                  (if (= (- array_panel_length array_length) 0) ;condition for input fragment left/right value
                    (progn
                      0
                    )
                    (if (< (- (/ (- array_panel_length array_length ) 2) 50) 0)
                      (progn
                        0
                      )
                      (+  (+ 36 (- (/ (- array_panel_length array_length ) 2) 50)) 200)
                    )
                  )
                )
                (LM:setdynpropvalue 
                  new_obj_ 
                  "fragment_right"   
                  (if (= (- array_panel_length array_length) 0) ;condition for input fragment left/right value
                    (progn
                      0
                    )
                    (- (- (/ (- array_panel_length array_length ) 2) 14) 200)
                  )
                )
              )
            )
            ( ;visibility condition
              (and 
                (< array_panel_length 2401)
                
              )
              (progn
                (LM:setdynpropvalue new_obj_ "view" "7_dynamic_length_view")
                (cond 
                  ((and 
                     (= (fix (LM:getdynpropvalue 300hk_obj_ "array_panel_length")) 
                        2400
                     )
                   )

                   (progn 
                     (TA:move_axis_insertionpoint new_obj_ "x" 200)
                     (LM:setdynpropvalue new_obj_ "fragment_middle_r" 1136)
                     (LM:setdynpropvalue new_obj_ "fragment_middle_L" 1136)
                   )
                  )
                  ((and 
                     (= (fix (LM:getdynpropvalue 300hk_obj_ "array_panel_length")) 
                        2000
                     )
                   )
                   (progn 
                     (LM:setdynpropvalue new_obj_ "fragment_middle_r" 736)
                     (LM:setdynpropvalue new_obj_ "fragment_middle_L" 1136)
                   )
                  )
                  ((and 
                     (= (fix (LM:getdynpropvalue 300hk_obj_ "array_panel_length")) 
                        1600
                     )
                   )
                   (progn 
                     (LM:setdynpropvalue new_obj_ "fragment_middle_r" 736)
                     (LM:setdynpropvalue new_obj_ "fragment_middle_L" 736)
                   )
                  )
                  ((and 
                     (= (fix (LM:getdynpropvalue 300hk_obj_ "array_panel_length")) 
                        1200
                     )
                   )
                   (progn 
                     (LM:setdynpropvalue new_obj_ "fragment_middle_r" 336)
                     (LM:setdynpropvalue new_obj_ "fragment_middle_L" 736)
                   )
                  )
                  ((and 
                     (= tor nil)
                     (= (fix (LM:getdynpropvalue 300hk_obj_ "array_panel_length")) 
                        800
                     )
                   )
                   (progn 
                     (LM:setdynpropvalue new_obj_ "fragment_middle_r" 336)
                     (LM:setdynpropvalue new_obj_ "fragment_middle_L" 336)
                   )
                  )
                )
                
                (LM:setdynpropvalue 
                  new_obj_ 
                  "fragment_array_length"   
                  (* (fix (/ (- array_panel_length 100)  400)) 400)
                )
                
              )
            )
            )
          ;
        )
      )

    ;
    ;return osmode
      (setvar "osmode" 1215)
    ;
  )
  (defun c:PPLINE_300HK_insHRsideview_ ()
    (setq 300HK_ename_ (car (entsel "specify Object")))
    (setq 300HK_obj_ (vlax-ename->vla-object 300HK_ename_))
    ;main_idea_coding_code
      (if (or 
            (= (LM:Effectivename 300hk_obj_) "000 - DYNAMIC_ARRAY+COMBINE+VIEW_ASSCESSORIES_FAMELINE_AL.CELL_CELING_PANEL_300HK_COMBINE_SET")
            (= (LM:Effectivename 300hk_obj_) "000 - DYNAMIC_ARRAY+COMBINE+VIEW_ASSCESSORIES_FAMELINE_AL.CELL_CELING_PANEL_300HK_@400mm_COMBINE_SET")
            (= (LM:Effectivename 300hk_obj_) "000 - DYNAMIC_ARRAY+COMBINE+VIEW_ASSCESSORIES_FAMELINE_AL.CELL_CELING_PANEL_360HK_@372mm_COMBINE_SET")
            (= (LM:Effectivename 300hk_obj_) "000 - DYNAMIC_ARRAY+COMBINE+VIEW_ASSCESSORIES_FAMELINE_AL.CELL_CELING_PANEL_300HK_@310mm_COMBINE_SET")
            (= (LM:Effectivename 300hk_obj_) "000 - DYNAMIC_ARRAY+COMBINE+VIEW_ASSCESSORIES_FAMELINE_AL.CELL_CELING_PANEL_300HK_COMBINE_SET_startpoint_")
          )
        (progn
          ;get_ex-insertion_pt_300HK
            (list 
              (setq HR-02A_top_point_x (LM:getdynpropvalue 300hk_obj_ "HR-02A_top_point x" ) )
              (setq HR-02A_top_point_y (LM:getdynpropvalue 300hk_obj_ "HR-02A_top_point y" ) )
            )
            (list 
              (setq HR-02B_top_point_x (LM:getdynpropvalue 300hk_obj_ "HR-02B_top_point x" ) ) 
              (setq HR-02B_top_point_y (LM:getdynpropvalue 300hk_obj_ "HR-02B_top_point Y" ) )
            )
            (setq 300hk_obj_ins_ (vlax-safearray->list (vlax-variant-value (vla-get-insertionpoint 300hk_obj_))))
            ; (if (= (LM:Effectivename 300hk_obj_) "000 - DYNAMIC_ARRAY+COMBINE+VIEW_ASSCESSORIES_FAMELINE_AL.CELL_CELING_PANEL_300HK_COMBINE_SET_startpoint_")
            ;   (progn
            ;     (vlax-curve-getpointatdist 300hk_obj_ )
            ;   )
            ;   (setq 300hk_obj_ins_ (vlax-safearray->list (vlax-variant-value (vla-get-insertionpoint 300hk_obj_))))
            ; )
            (setq 300hk_obj_rotation_ (TA:ModifyRotation (rad-to-deg (vla-get-rotation 300hk_obj_ ) ) 180))
          ;
          ;insertion_panel_insertion_point_
            (setq HR-02A_top_point_preins_ (list 
                                              (+ ( car 300hk_obj_ins_ ) 0  )
                                              (+ ( cadr 300hk_obj_ins_ ) 111.80  )
                                              (+ ( caddr 300hk_obj_ins_ ) 0  )
                                            )
            )
            (setq HR-02B_top_point_preins_ (list 
                                              (+ ( car 300hk_obj_ins_ ) 0  )
                                              (+ ( cadr 300hk_obj_ins_ ) 63.80  )
                                              (+ ( caddr 300hk_obj_ins_ ) 0  )
                                            )
            )
          ;
          ;get_dynamic_data_
            (setq array_panel_length (- (LM:getdynpropvalue 300hk_obj_ "array_panel_length") 100))
          ; 
          ;insertion_HR_side_A
          (if (and (= (LM:getdynpropvalue 300hk_obj_ "view") "4_side_L_view") )
            (progn
              ;insertion_HR_side_A
                (TA:vla-insertblock 
                  "000 - DYNAMIC_COMBINE+VIEW_ASSCESSORIES_FAMELINE_GALV.BRACKET_FITTING_Z-PROFILE_HR-02AA_COMBINE_VIEW"
                  (if (= (getvar "worlducs") 0)(progn (trans HR-02A_top_point_preins_ 1 1)) HR-02A_top_point_preins_ )
                  1
                  0
                ) 
                (setq new_ename_ (entlast))
                (setq new_obj_ (vlax-ename->vla-object new_ename_)) 
                (TA:move_axis_insertionpoint new_obj_ "x" -25)
                (setvar "osmode" 0)          
                (LM:setdynpropvalue new_obj_ "view" "4_side_L_view")
                (setq array_length (LM:setdynpropvalue new_obj_ "array_length" (* (fix (/ array_panel_length 2400)) 2400 ) ))
                (cond ;visibility&length condition
                  ( ;visibility condition
                    (or 
                      (> array_panel_length 3000)
                    )
                    (progn
                      (LM:setdynpropvalue new_obj_ "view" "4_side_L_view")
                      (LM:setdynpropvalue 
                        new_obj_ 
                        "fragment_left"   
                        (if (and (= (- array_panel_length array_length) 0)) ;condition for input fragment left/right value
                          (progn
                            0
                          )
                          (if (> 0 (- (/ (- array_panel_length array_length ) 2) 50) )
                            (progn
                              0
                            )
                            (- (/ (- array_panel_length array_length ) 2) 50)
                          )
                        )
                      )
                      (LM:setdynpropvalue 
                        new_obj_ 
                        "fragment_right"   
                        (if (= (- array_panel_length array_length) 0) ;condition for input fragment left/right value
                          (progn
                            0
                          )
                          (if (> 0 (- (/ (- array_panel_length array_length ) 2) 50) )
                            (progn
                              0
                            )
                            (- (/ (- array_panel_length array_length ) 2) 50)
                          )
                        )
                      )
                    )
                  )
                  ( ;visibility condition
                    (and 
                      (< array_panel_length 3000) 
                      
                    )
                    (progn
                      (LM:setdynpropvalue new_obj_ "view" "7_dynamic_length_view")
                      (LM:setdynpropvalue 
                        new_obj_ 
                        "fragment_middle"   
                        (- array_panel_length 50)
                      )
                    )
                  )
                )
              ;
            )
          )
          ;
          ;insertion_HR_side_B
          (if (and (= (LM:getdynpropvalue 300hk_obj_ "view") "4_side_R_view") )
            (progn
              ;insertion_HR_side_B
                (TA:vla-insertblock 
                  "000 - DYNAMIC_COMBINE+VIEW_ASSCESSORIES_FAMELINE_GALV.BRACKET_FITTING_Z-PROFILE_HR-02B_COMBINE_VIEW"
                  (if (= (getvar "worlducs") 0)(progn (trans HR-02B_top_point_preins_ 1 1)) HR-02B_top_point_preins_ ) 
                  1
                  0
                )
                (setq new_ename_ (entlast))
                (setq new_obj_ (vlax-ename->vla-object new_ename_))   
                (LM:setdynpropvalue new_obj_ "view" "4_side_R_view")
                (setq array_length (LM:setdynpropvalue new_obj_ "array_length" (* (fix (/ array_panel_length 2400)) 2400 ) ))
                (cond ;visibility&length condition
                  ( ;visibility condition
                    (or 
                      (> array_panel_length 2401)
                    )
                    (progn
                      (LM:setdynpropvalue new_obj_ "view" "4_side_R_view")
                      (LM:setdynpropvalue 
                        new_obj_ 
                        "fragment_left"   
                        (if (= (- array_panel_length array_length) 0) ;condition for input fragment left/right value
                          (progn
                            0
                          )
                          (if (< (- (/ (- array_panel_length array_length ) 2) 50) 0)
                            (progn
                              0
                            )
                            (- (/ (- array_panel_length array_length ) 2) 50)
                          )
                        )
                      )
                      (LM:setdynpropvalue 
                        new_obj_ 
                        "fragment_right"   
                        (if (= (- array_panel_length array_length) 0) ;condition for input fragment left/right value
                          (progn
                            0
                          )
                          (- (/ (- array_panel_length array_length ) 2) 0)
                        )
                      )
                    )
                  )
                  ( ;visibility condition
                    (and 
                      (< array_panel_length 2401)
                      
                    )
                    (progn
                      (LM:setdynpropvalue new_obj_ "view" "7_dynamic_length_view")
                      (LM:setdynpropvalue 
                        new_obj_ 
                        "fragment_middle"   
                        (- array_panel_length 100)
                      )
                      (LM:setdynpropvalue 
                        new_obj_ 
                        "fragment_array_length"   
                        (* (fix (/ (- array_panel_length 100)  400)) 400)
                      )
                      
                    )
                  )
                )
              ;
            )
          )
        )
      )
    ;
    ;return osmode
      (setvar "osmode" 1215)
    ;
  )
  (defun c:PPLINE_300HK_HREQ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000 - DYNAMIC_COMBINE+VIEW_ASSCESSORIES_FAMELINE_GALV.BRACKET_FITTING_Z-PROFILE_HR-02B_COMBINE_VIEW"))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq sss_obj_ (vlax-ename->vla-object  ss_pre_filter_set_xx_ename_))
        (if (> 
              (setq L (LM:getdynpropvalue sss_obj_ "fragment_left"))
              (setq R (LM:getdynpropvalue sss_obj_ "fragment_right"))
            )
          (progn
            (LM:setdynpropvalue sss_obj_ "fragment_left" (- L 200) )
            (LM:setdynpropvalue sss_obj_ "fragment_right" (+ R 200))
          )
        )
        (if (<
              (setq L (LM:getdynpropvalue sss_obj_ "fragment_left"))
              (setq R (LM:getdynpropvalue sss_obj_ "fragment_right"))
            )
          (progn
            (LM:setdynpropvalue sss_obj_ "fragment_left" (+ L 200) )
            (LM:setdynpropvalue sss_obj_ "fragment_right" (- R 200))
          )
        )
        (setq ss_pre_filter_set_xx_i (+ ss_pre_filter_set_xx_i 1))
      )
    ;
  )
  (defun c:PPLINE_300HK_HRL ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000 - DYNAMIC_COMBINE+VIEW_ASSCESSORIES_FAMELINE_GALV.BRACKET_FITTING_Z-PROFILE_HR-02B_COMBINE_VIEW"))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq sss_obj_ (vlax-ename->vla-object  ss_pre_filter_set_xx_ename_))
        (setq L (LM:getdynpropvalue sss_obj_ "fragment_left"))
        (setq R (LM:getdynpropvalue sss_obj_ "fragment_right"))
        (LM:setdynpropvalue sss_obj_ "fragment_left" (- L 200) )
        (LM:setdynpropvalue sss_obj_ "fragment_right" (+ R 200))
 
        (setq ss_pre_filter_set_xx_i (+ ss_pre_filter_set_xx_i 1))
      )
    ;
  )
  (defun c:PPLINE_300HK_HRR ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000 - DYNAMIC_COMBINE+VIEW_ASSCESSORIES_FAMELINE_GALV.BRACKET_FITTING_Z-PROFILE_HR-02B_COMBINE_VIEW"))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq sss_obj_ (vlax-ename->vla-object  ss_pre_filter_set_xx_ename_))
        (setq L (LM:getdynpropvalue sss_obj_ "fragment_left"))
        (setq R (LM:getdynpropvalue sss_obj_ "fragment_right"))
        (LM:setdynpropvalue sss_obj_ "fragment_left" (+ L 200) )
        (LM:setdynpropvalue sss_obj_ "fragment_right" (- R 200))
 
        (setq ss_pre_filter_set_xx_i (+ ss_pre_filter_set_xx_i 1))
      )
    ;
  )
  (defun c:sshr ()
    ;selection_set_for_fillter_blk_name
      (if  ;pre_select_ssget_or_post_select_ssget
        (= 
          (setq HRR_ (ssget "i" 
                            (list 
                              (cons 0 "INSERT") ;type of object
                              ; (cons 8 "000 - GRID")   ;kind of layer
                              ; (cons 2 "000-GRID_LINE_DYN")       ;kind of nameblock
                              ; (cons 62 1)           ;kind of color call sign with color code index
                            )
                     )
          )
          nil
        )
        (progn 
          (setq HRR_ (ssget 
                       (list 
                         (cons 0 "INSERT") ;type of object
                         ; (cons 8 "000 - GRID")   ;kind of layer
                         ; (cons 2 "000-GRID_LINE_DYN")       ;kind of nameblock
                         ; (cons 62 1)           ;kind of color call sign with color code index
                       )
                     )
          )
        )
        (sslength HRR_)
      )
      (setq HRR_ (TA:EF_Filter_ss_set_v2_ HRR_ (list "000 - DYNAMIC_COMBINE+VIEW_ASSCESSORIES_FAMELINE_GALV.BRACKET_FITTING_Z-PROFILE_HR-02B_COMBINE_VIEW" "000 - DYNAMIC_COMBINE+VIEW_ASSCESSORIES_FAMELINE_GALV.BRACKET_FITTING_Z-PROFILE_HR-02AA_COMBINE_VIEW" ))) ;
    (setq ERR_ nil)
    (while ;for keep insertion point and dist. fix length one side
      (and
        (= (vl-catch-all-error-p ERR_) nil)
      )
      (setq ERR_
        (vl-catch-all-apply
          (function
            (lambda ()
              (setq increment_num_ (cond ( (getint (strcat "\nSpecify sss_   <" (rtos (setq increment_num_ (cond (increment_num_) (1.0) ) ) ) "> : " ) ) ) (increment_num_) ) )
            )
          )
        )
      )
      ;preloop_and_while
        (setq HRR_i 0)
        (while 
          (and
            (= (vl-catch-all-error-p ERR_) nil)
            (< HRR_i (sslength HRR_))
          )
          (setq HRR_ename_ (ssname HRR_ HRR_i))
          (setq HRR_obj_ (vlax-ename->vla-object  HRR_ename_))
          (setq HRR_obj_ins_ (vlax-safearray->list (vlax-variant-value (vla-get-insertionpoint HRR_obj_))))
          (setq HRR_obj_fragment_mid_ (LM:getdynpropvalue HRR_obj_ "array_length" ))
          (setq HRR_obj_sub-fragment_mid_ (LM:getdynpropvalue HRR_obj_ "fragment_middle" ))
          
          (cond
            (;ssss_case_1
              (and
                  (= (vl-catch-all-error-p ERR_) nil)
                  (= (LM:getdynpropvalue HRR_obj_ "view") "2_top_view" )
                  (= increment_num_ 1)
              )
              (progn
                (LM:setdynpropvalue HRR_obj_ "array_length" (setq HRR_obj_fragment_mid_ (+ HRR_obj_fragment_mid_ 2400)))
                (TA:move_polar_insertionpoint  HRR_obj_ "y" -1200)
                (princ "ssss_case_1")
              )
            )
            (;ssss_case_2
              (and
                  (= (vl-catch-all-error-p ERR_) nil)
                  (= (LM:getdynpropvalue HRR_obj_ "view") "2_top_view" )
                  (= increment_num_ 0)
              )
              (progn
                (LM:setdynpropvalue HRR_obj_ "array_length" (setq HRR_obj_fragment_mid_ (- HRR_obj_fragment_mid_ 2400)))
                (TA:move_polar_insertionpoint  HRR_obj_ "y" +1200)
                (princ "ssss_case_2")
              )
            )
            (;ssss_case_3
              (and
                  (= (vl-catch-all-error-p ERR_) nil)
                  (= (LM:getdynpropvalue HRR_obj_ "view") "2_top_view" )
                  (< increment_num_ 0)
              )
              (progn
                (LM:setdynpropvalue HRR_obj_ "array_length" (setq HRR_obj_fragment_mid_ (- HRR_obj_fragment_mid_ (* increment_num_ 2400))))
                (TA:move_polar_insertionpoint  HRR_obj_ "y" (* 1200 increment_num_))
                (princ "ssss_case_3")
              )
            )
            (;ssss_case_4
              (and
                  (= (vl-catch-all-error-p ERR_) nil)
                  (= (LM:getdynpropvalue HRR_obj_ "view") "2_top_view" )
                  (> increment_num_ 1)
              )
              (progn
                (LM:setdynpropvalue HRR_obj_ "array_length" (setq HRR_obj_fragment_mid_ (+ HRR_obj_fragment_mid_ (* increment_num_ 2400))))
                (TA:move_polar_insertionpoint  HRR_obj_ "y" (- (* 1200 increment_num_)))
                (princ "ssss_case_3")
              )
            )
            
            (;ssss_case_5
              (and
                  (= (vl-catch-all-error-p ERR_) nil)
                  (= (LM:getdynpropvalue HRR_obj_ "view") "7_dynamic_length_view" )
                  (<= increment_num_ 0)
              )
              (progn
                (LM:setdynpropvalue HRR_obj_ "fragment_middle" (setq HRR_obj_sub-fragment_mid_ (+ HRR_obj_sub-fragment_mid_ (* increment_num_ 100))))
                (TA:move_polar_insertionpoint  HRR_obj_ "y" (- (* 50 increment_num_)))
                (princ "ssss_case_3")
              )
            )
            (;ssss_case_6
              (and
                  (= (vl-catch-all-error-p ERR_) nil)
                  (= (LM:getdynpropvalue HRR_obj_ "view") "7_dynamic_length_view" )
                  (>= increment_num_ 1)
              )
              (progn
                (LM:setdynpropvalue HRR_obj_ "fragment_middle" (setq HRR_obj_sub-fragment_mid_ (+ HRR_obj_sub-fragment_mid_ (* increment_num_ 100))))
                (TA:move_polar_insertionpoint  HRR_obj_ "y" (- (* 50 increment_num_)))
                (princ "ssss_case_3")
              )
            )
            
          )
          
          
          (setq HRR_i (+ HRR_i 1))
        )
      ;

    )
  )
  (defun c:ovlhr9 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000 - ASSCESSORIES_FAMELINE_GALV.BRACKET_FITTING_Z-PROFILE_HR-09B_TOP_VIEW"))
    ; 
    ;preloop_and_while
      (_StartUndo doc)
      (TA:interface_text_ T)
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (or 
              (= (rtos (rad-to-deg (vla-get-rotation ss_pre_filter_set_xx_obj_)) 2 2) "0")
              (= (rtos (rad-to-deg (vla-get-rotation ss_pre_filter_set_xx_obj_)) 2 2) "180.00")
              
            )
          (progn
            (setvar "osmode" 0)
            (setq ovl_length_ (car (nth 1 (TA:get-visible-boundingbox ss_pre_filter_set_xx_obj_))))
            ;new_blk_entlast object
              (setq newrec_ename (entlast))
              (setq newrec_obj (vlax-ename->vla-object newrec_ename))
              (vla-delete newrec_obj)
              (LM:vl-setattributevalue ss_pre_filter_set_xx_obj_ "GALV.OVL-LENGTH_" (rtos ovl_length_ 2 2))
            ;
          )
        )
        
        
        (TA:textscr_process_V2 "\nupdate dynamic" ss_pre_filter_set_xx_i ss_pre_filter_set_xx_)
        (setq ss_pre_filter_set_xx_i (+ ss_pre_filter_set_xx_i 1))
      )
      (setvar "osmode" 1215)
      (_EndUndo doc)
    ;
  )
  ;
  ;000 - DYNAMIC_LENGTH+COMBINE+VIEW_ASSCESSORIES_FAMELINE_BK-08_HANGING_SYSTEM_300HK_COMBINE_SET
  (defun c:PPLINE_300HK_insHanging_ ()
    ;selection_set_for_fillter_blk_name
      (if  ;pre_select_ssget_or_post_select_ssget
        (=
          (setq ss_pre_filter_set_xx_ (ssget "i"
                                            (list
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "LWPOLYLINE,LINE") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ;get-rotaton_object_
        (setq angle_ename_ (car (entsel "specify Object")))
        (setq angle_obj_ (vlax-ename->vla-object angle_ename_))
      ;
    
      (foreach x (LM:intersectionsinset ss_pre_filter_set_xx_)
        (TA:vla-insertblock 
          "000 - DYNAMIC_LENGTH+COMBINE+VIEW_ASSCESSORIES_FAMELINE_BK-08_HANGING_SYSTEM_300HK_COMBINE_SET"
          x
          1
          (cond ;get rotate condition
            (;Line PLine condition 
              (or
                (= "AcDbLine" (vla-get-objectname angle_obj_))
                (= "AcDbPolyline" (vla-get-objectname angle_obj_ ))   
              )
              (progn
                (vla-get-angle angle_obj_)
              )
            )
            (;BLK condition 
              (and
                (= "AcDbBlockReference" (vla-get-objectname angle_obj_))
                (= "AcDbBlockReference" (vla-get-objectname angle_obj_ ))   
              )
              (progn
                (vla-get-rotation angle_obj_)
              )
            )
          )
        )
          ;new_blk_entlast object
          (setq new_hanging_ename (entlast))
          (setq new_hanging_obj_ (vlax-ename->vla-object new_hanging_ename))
          (LM:setdynpropvalue new_hanging_obj_ (LM:getvisibilityparametername new_hanging_obj_) "2_top_view" )
          ;
        
        
      )
    ;
  )
  (defun c:PPLINE_300HK_insCHanging_ ()
    ;selection_set_for_fillter_blk_name
      (if  ;pre_select_ssget_or_post_select_ssget
        (=
          (setq ss_pre_filter_set_xx_ (ssget "i"
                                            (list
                                              (cons 0 "LWPOLYLINE,LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "LWPOLYLINE,LINE") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ;user_input_
        (setq distance_measure_ 1200)
      ;
      ;preloop_and_while
        (setq ss_pre_filter_set_xx_i 0)
        (while (< ss_pre_filter_set_xx_i (sslength ss_pre_filter_set_xx_))
          ;main Line PLine Properties
            (setq ss_pre_filter_set_xx_ename_ (ssname ss_pre_filter_set_xx_ ss_pre_filter_set_xx_i))
            (setq ss_pre_filter_set_xx_obj_ (vlax-ename->vla-object ss_pre_filter_set_xx_ename_))
            (setq ss_pre_filter_set_xx_obj_angle  (vla-get-angle ss_pre_filter_set_xx_obj_))
            (setq ss_pre_filter_set_xx_obj_length (vla-get-length ss_pre_filter_set_xx_obj_))
            (setq distance_measure_ (if (< ss_pre_filter_set_xx_obj_length 1200) (progn (fix (- ss_pre_filter_set_xx_obj_length 100 ))) distance_measure_)) 
            (setq ss_pre_filter_set_xx_obj_fragment_length_ (/ (- ss_pre_filter_set_xx_obj_length (* (fix (/ ss_pre_filter_set_xx_obj_length distance_measure_)) distance_measure_) ) 2))
            (setq ss_pre_filter_set_xx_obj_time_full_length_ (fix (/ ss_pre_filter_set_xx_obj_length distance_measure_)))
            (if (= ss_pre_filter_set_xx_obj_fragment_length_ 0) ;incase for number spcaing distance
              (progn
                (setq ss_pre_filter_set_xx_obj_time_full_length_ ss_pre_filter_set_xx_obj_time_full_length_ )
              )
              (setq ss_pre_filter_set_xx_obj_time_full_length_ (+ 2 ss_pre_filter_set_xx_obj_time_full_length_) )
            )
            ;preloop_and_while measure_spcaing_distance
              (setq measure_length_ ())
              (setq time_i 0)
              (while (< time_i ss_pre_filter_set_xx_obj_time_full_length_)
                (if 
                  (or (= time_i 0) (= time_i (- ss_pre_filter_set_xx_obj_time_full_length_ 1)) )
                  (progn
                    (setq measure_length_ (cons ss_pre_filter_set_xx_obj_fragment_length_ measure_length_))
                  )
                  (setq measure_length_ (cons distance_measure_ measure_length_))
                )
                (setq time_i (+ time_i 1))
              )       
            ;
            ;preloop_and_while measure_val_distance
              (setq measure_length_i 0)
              (setq finish_measure_length_ 0)
              (setq finish_measure_length_result ())
              (while (< measure_length_i (length measure_length_))
                (setq measure_length_ename_ (nth  measure_length_i measure_length_))
                (setq finish_measure_length_ (+ finish_measure_length_ measure_length_ename_)) 
                (setq finish_measure_length_result (cons finish_measure_length_ finish_measure_length_result))
                (setq measure_length_i (+ measure_length_i 1))
              )
            ;
          ;
          ;insertion_process
            (foreach x (vl-remove (nth (- (length finish_measure_length_result) 1) (reverse finish_measure_length_result) ) (reverse finish_measure_length_result) )
              (TA:vla-insertblock 
                "000 - DYNAMIC_LENGTH+COMBINE+VIEW_ASSCESSORIES_FAMELINE_BK-08_HANGING_SYSTEM_300HK_COMBINE_SET"
                (vlax-curve-getpointatdist ss_pre_filter_set_xx_obj_ x)
                1
                ss_pre_filter_set_xx_obj_angle
              )
              ;new_blk_entlast object
                (setq newblk_ename (entlast))
                (setq newblk_obj (vlax-ename->vla-object newblk_ename))
                (LM:setdynpropvalue newblk_obj (LM:getvisibilityparametername newblk_obj) "2_top_view" )
              ;
            )
          ;
          (setq ss_pre_filter_set_xx_i (+ ss_pre_filter_set_xx_i 1))
        )
      ;
    ;
  )
  (defun c:PPLINE_CKST_sel-ceilng-layer-CLlayer ()
    ;selection_set_for_fillter_blk_name
      (if  ;pre_select_ssget_or_post_select_ssget
        (=
          (setq ss_pre_filter_set_xx_ (ssget "i"
                                            (list
                                              ; (cons 0 "INSERT") ;type of object
                                              (cons 8 "A-GLAZ-CURT,A-CLNG")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              (cons 8 "A-GLAZ-CURT,A-CLNG")   ;kind of layer
                                              ; (cons 2 "000-GRID_LINE_DYN")       ;kind of nameblock
                                              ; (cons 62 1)           ;kind of color call sign with color code index
                                            )
                                      )
          )
        )
        (sslength ss_pre_filter_set_xx_)
      )
    ;
    (command "pselect"  ss_pre_filter_set_xx_ "" )
  )
  (defun c:PPLINE-CKST-insinter ()
    ;presetting_
      (setq intersection_mode_ 0)
      (if (= intersection_mode_ 1) (progn (setq inter_blk_name_ "000 - TRANSFER" ) ) )
      (if (= intersection_mode_ 2) (progn (setq inter_blk_name_ "000 - CIRCLE" ) ) )
    
    ;
    ;selection_set_for_fillter_blk_name
      (if  ;pre_select_ssget_or_post_select_ssget
        (=
          (setq ss_pre_filter_set_xx_ (ssget "i"
                                            (list
                                              (cons 0 "INSERT") ;type of object
                                              (cons 8 "000 - GRID,001 - ASCESSORIES")   ;kind of layer
                                              ; (cons 2 "000-GRID_LINE_DYN")       ;kind of nameblock
                                              (cons 62 256)           ;kind of color call sign with color code index
                                            )
                                      )
          )
          nil
        )
        (progn
          (setq ss_pre_filter_set_xx_ (ssget
                                            (list
                                              (cons 0 "INSERT") ;type of object
                                              (cons 8 "000 - GRID,001 - ASCESSORIES")   ;kind of layer
                                              ; (cons 2 "000-GRID_LINE_DYN")       ;kind of nameblock
                                              (cons 62 256)           ;kind of color call sign with color code index
                                            )
                                      )
          )
        )
        (sslength ss_pre_filter_set_xx_)
      )
      (setq ss_pre_filter_set_xx_ (TA:EF_Filter_ss_set_ ss_pre_filter_set_xx_ "000 - DYNAMIC_COMBINE+VIEW_ASSCESSORIES_FAMELINE_GALV.BRACKET_FITTING_U-PROFILE_CC-01-4_COMBINE_VIEW"))
    ;
    ;preloop_and_while
      (setvar "osmode" 0)
      (setq ss_pre_filter_set_xx_i 0)
      (setq cc-01_inters_list_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_rotation_ (rad-to-deg (vla-get-rotation ss_pre_filter_set_xx_obj_)))
        (vla-put-color ss_pre_filter_set_xx_obj_ 1)
        (setq cc-01_inters_list_ 
          (cons 
            (list
              ss_pre_filter_set_xx_obj_ins_
              (polar ss_pre_filter_set_xx_obj_ins_  
                    (vla-get-rotation ss_pre_filter_set_xx_obj_) 
                    (if (= (LM:getdynpropvalue ss_pre_filter_set_xx_obj_ "view" ) "7_dynamic_length_view")
                      (progn
                        (LM:getdynpropvalue ss_pre_filter_set_xx_obj_ "fragment_start" )
                      )
                      (+
                        (LM:getdynpropvalue ss_pre_filter_set_xx_obj_ "array_length" )
                        (LM:getdynpropvalue ss_pre_filter_set_xx_obj_ "fragment_length" )
                      )
                    )
              
              )
            )
            cc-01_inters_list_
          )
        )  
        
        (setq ss_pre_filter_set_xx_i (+ ss_pre_filter_set_xx_i 1))
      )
    ;
    (setq Er-msg_ nil)
    (setq new_tranfer_ss_ (ssadd))
    
    (while
      (and (/= (vl-catch-all-error-p Er-msg_) T) )
      (setq Er-msg_ (vl-catch-all-apply (function (lambda () 
                                                    
                                                    (setq ss_line_ename_ (ssname  (ssget  (list (cons 0 "line") ) ) 0) ) 
                                                  ) 
                                        ) 
                    ) 
      )
      (if (and 
            (/= (vl-catch-all-error-p Er-msg_) T)
            (= (vla-get-objectname (vlax-ename->vla-object ss_line_ename_)) "AcDbLine")
          )

        (progn
          (TA:interface_text_ T)
          (setq ss_line_obj_ (vlax-ename->vla-object ss_line_ename_))
          (setq ss_line_obj_start_end_pt_ (list
                                          (setq ss_line_obj_startpt_ (vlax-safearray->list
                                                                    (vlax-variant-value ( vla-get-startpoint ss_line_obj_ ))
                                                                  )
                                          )
                                          (setq ss_line_obj_endpt_ (vlax-safearray->list
                                                                    (vlax-variant-value ( vla-get-endpoint ss_line_obj_ ))
                                                                )
                                          )
                                        )
          )
        )
        
      )
      ;preloop_and_while
        (setq cc-01_inters_list_i 0)
        (TA:interface_text_ T)
        (while (and
                (/= (vl-catch-all-error-p Er-msg_) T)
                (< cc-01_inters_list_i (length cc-01_inters_list_) )
              )
          (setq cc-01_inters_list_val_1 (car (nth  cc-01_inters_list_i cc-01_inters_list_)))
          (setq cc-01_inters_list_val_2 (cadr (nth  cc-01_inters_list_i cc-01_inters_list_)))
          
          (if (/= (inters ss_line_obj_startpt_ ss_line_obj_endpt_ cc-01_inters_list_val_1 cc-01_inters_list_val_2 ) nil)
            (progn
              (cond 
                ( ;intersection_mode_case_1
                  (and 
                    (= intersection_mode_ 0)
                  )
                  (progn 
                    (command "circle" 
                              (if (= (getvar "worlducs") 0) 
                                (progn 
                                  (trans (inters ss_line_obj_startpt_ ss_line_obj_endpt_ cc-01_inters_list_val_1 cc-01_inters_list_val_2 ) 0 1 )
                                )
                                (inters ss_line_obj_startpt_ ss_line_obj_endpt_ cc-01_inters_list_val_1 cc-01_inters_list_val_2 )
                              )
                              120
                    )
                    
                    ;new_blk_entlast object
                      (setq new_ename (entlast))
                      (setq new_obj_ (vlax-ename->vla-object new_ename))
                      (vla-put-color new_obj_ 256)
                      (vla-put-layer new_obj_ "001 - ASCESSORIES_HANGING")
                      ; (TA:move_axis_insertionpoint new_obj_ "x" -17)
                      ; (LM:setdynpropvalue new_obj_  "view" "2_top_view")
                    ;
                    (princ "intersection_mode_case_1")
                  )
                )
                ( ;intersection_mode_case_1
                  (and 
                    (= intersection_mode_ 1)
                  )
                  (progn 
                    (TA:vla-insertblock 
                      inter_blk_name_
                      (if (= (getvar "worlducs") 1) 
                        (progn 
                          (trans (inters ss_line_obj_startpt_ ss_line_obj_endpt_ cc-01_inters_list_val_1 cc-01_inters_list_val_2 ) 0 1 )
                        )
                        (inters ss_line_obj_startpt_ ss_line_obj_endpt_ cc-01_inters_list_val_1 cc-01_inters_list_val_2 )
                      )
                      1
                      (angle cc-01_inters_list_val_1 cc-01_inters_list_val_2)
                    )
                    ;new_blk_entlast object
                      (setq new_ename (entlast))
                      (setq new_obj_ (vlax-ename->vla-object new_ename))
                      (vla-put-color new_obj_ 3)
                      (TA:move_axis_insertionpoint new_obj_ "y" 50)
                      ; (LM:setdynpropvalue new_obj_  "view" "2_top_view")
                      (setq new_tranfer_ss_ (ssadd new_ename new_tranfer_ss_))
                    ; 

                    (princ "intersection_mode_case_1")
                  )
                )
                ( ;intersection_mode_case_2
                  (and 
                    (= intersection_mode_ 2)
                  )
                  (progn 
                    (TA:vla-insertblock 
                      inter_blk_name_
                      (if (= (getvar "worlducs") 1) 
                        (progn 
                          (trans (inters ss_line_obj_startpt_ ss_line_obj_endpt_ cc-01_inters_list_val_1 cc-01_inters_list_val_2 ) 0 1 )
                        )
                        (inters ss_line_obj_startpt_ ss_line_obj_endpt_ cc-01_inters_list_val_1 cc-01_inters_list_val_2 )
                      )
                      1
                      (angle cc-01_inters_list_val_1 cc-01_inters_list_val_2)
                    )
                    ;new_blk_entlast object
                      (setq new_ename (entlast))
                      (setq new_obj_ (vlax-ename->vla-object new_ename))
                      (vla-put-color new_obj_ 3)
                      (TA:move_axis_insertionpoint new_obj_ "y" 50)
                      ; (LM:setdynpropvalue new_obj_  "view" "2_top_view")
                      (setq new_tranfer_ss_ (ssadd new_ename new_tranfer_ss_))
                    ; 

                    (princ "intersection_mode_case_2")
                  )
                )
              )
            )
          )

          (TA:textscr_process "insertion process " cc-01_inters_list_i cc-01_inters_list_)
      
          (setq cc-01_inters_list_i (+ cc-01_inters_list_i 1))
        )
      ;
      
    )
    (command "pselect"  new_tranfer_ss_ "" )
    (setvar "osmode" 1215)
  )
  (defun c:hang_count_HAC ()
    ;selection_set_for_fillter_blk_name
      (if  ;pre_select_ssget_or_post_select_ssget
        (=
          (setq ss_pre_filter_set_xx_ (ssget "i"
                                            (list
                                              (cons 0 "insert,circle") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "insert,circle") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_) 
      )
    ; 
    (setq count_circle_ (sslength (TA:Prop_Filter_ss_set_ ss_pre_filter_set_xx_ 'ObjectName "AcDbCircle" )))
    (setq target_ename_ (ssname 
                          (TA:EF_Filter_ss_set_v2_ ss_pre_filter_set_xx_ 
                            (list "000 - DYNAMIC_COMBINE+VIEW_ASSCESSORIES_FAMELINE_GALV.BRACKET_FITTING_U-PROFILE_CC-01-4_COMBINE_VIEW")
                          ) 
                          0
                        )
    )
    (setq target_fastern_ (TA:EF_Filter_ss_set_v2_ ss_pre_filter_set_xx_ 
                            (list "000 - FASTERN SYMBOL")
                          )
    )
    
    (setq new_zone_val (LM:vl-getattributevalue (vlax-ename->vla-object target_ename_) "GALV-TYPE_"  ))
    ; (setq zone_val_
    ;   (substr 
    ;     (LM:vl-getattributevalue (vlax-ename->vla-object target_ename_) "NAME")
    ;     (+ (vl-string-search "ZONE-" (LM:vl-getattributevalue (vlax-ename->vla-object target_ename_) "NAME" ) 0 ) 6)
    ;     1
    ;   )
    ; )
    
    (setq count_box_ename_ (car (entsel "specify Object")))
    (setq count_box_obj_ (vlax-ename->vla-object count_box_ename_))
    (LM:vl-setattributevalue count_box_obj_ "NAME" "HANGING")
    ; (LM:vl-setattributevalue 
    ;   count_box_obj_
    ;   "ZONE"
    ;   (strcat "ZONE-" (if (>= (setq zone_val_ (atoi zone_val_)) 10) (progn (strcat (rtos zone_val_ 2 0)) ) (strcat "0" (rtos zone_val_ 2 0)) ) )
    ; )
    (LM:vl-setattributevalue 
      count_box_obj_
      "ZONE"
      new_zone_val
    )
    (LM:vl-setattributevalue count_box_obj_ "TOTAL" count_circle_)
    (LM:vl-setattributevalue count_box_obj_ "UNIT" 
      (if (and (= (type target_fastern_ ) 'pickset) (/= (sslength target_fastern_ ) 0) )
        (progn
          (sslength target_fastern_ )
        )
        "0"
      )
    )
    ; (LM:vl-setattributevalue count_box_obj_ "UNIT" )
    
  )
  ;
  ;000 - DYNAMIC_LENGTH+COMBINE+VIEW_ASSCESSORIES_FAMELINE_BK-08_HANGING_SYSTEM_300HK_COMBINE_SET
  (defun c:selallhang ()
    ;selection_set_for_fillter_blk_name
      (if  ;pre_select_ssget_or_post_select_ssget
        (=
          (setq ss_pre_filter_set_xx_ (ssget "x"
                                            (list
                                              (cons 0 "INSERT") ;type of object
                                              (cons 410 (getvar "CTAB"))
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              (cons 410 (getvar "CTAB"))
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_v2_ ss_pre_filter_set_xx_ (list "000 - DYNAMIC_LENGTH+COMBINE+VIEW_ASSCESSORIES_FAMELINE_BK-08_HANGING_SYSTEM_300HK_COMBINE_SET")))
      (command "pselect"  ss_pre_filter_set_xx_ "" )
    ;

  )
  ;
  ;000 - DYNAMIC_ARRAY+COMBINE+VIEW_ASSCESSORIES_PLAN_AL.SOLID_SHEET_HAT-PROFILE-TYPE-R_COMBINE_SET
  ;000 - DYNAMIC_ARRAY+COMBINE+VIEW_ASSCESSORIES_PLAN_AL.SOLID_SHEET_HAT-PROFILE-TYPE-C_COMBINE_SET
  ;
  (defun c:PPLINE_CKST_HatRVaries ()
    (setq ucsedit nil)
    (if (= (getvar "worlducs") 0)(progn (command "ucs" "WORLD") (setq ucsedit 0))  )
    (TA:vla-insertblock 
      ; "000 - DYNAMIC_ARRAY+COMBINE+VIEW_ASSCESSORIES_PLAN_AL.SOLID_SHEET_HAT-PROFILE_VA_COMBINE_SET" ;original
      "000 - DYNAMIC_LENGTH+COMBINE+VIEW_ASSCESSORIES_FAMELINE_AL.SOLID_SHEET_HAT-PROFILE-TYPE-R_non_code_COMBINE_SET"
      (setq newpt_ (getpoint))
      1
      (getangle newpt_)
    )
    (setq ss_ename_ (entlast))
    (setq ss_obj_ (vlax-ename->vla-object ss_ename_))
    (setq ss_obj_ins_ (vlax-safearray->list (vlax-variant-value (vla-get-insertionpoint ss_obj_))))
    (vla-put-layer ss_obj_ "A11_ALU.SOLID SHEET")
    (vla-put-color ss_obj_ 0 )
    (setq ss_obj_ins_ro (TA:ModifyRotation (rad-to-deg (vla-get-rotation ss_obj_)) 90))
    
    (setq Lpt1_ (polar ss_obj_ins_ (deg-to-rad ss_obj_ins_ro) 150) ) ;300 = 150 , 275 = 137.5
    (setq Lpt1_1 (polar Lpt1_ (deg-to-rad (TA:ModifyRotation ss_obj_ins_ro -90)) (LM:setdynpropvalue ss_obj_ "L" (getdist Lpt1_ "specify length 1"  ) )) )
    (setq Lpt4_ (polar ss_obj_ins_ (deg-to-rad (TA:ModifyRotation ss_obj_ins_ro 180)) 150) ) ;300 = 150 , 275 = 137.5
    (setq Lpt4_1 (polar Lpt4_ (deg-to-rad (TA:ModifyRotation ss_obj_ins_ro -90)) (LM:setdynpropvalue ss_obj_ "L4" (getdist Lpt4_ "specify length 1"  ) )) )
    
    (setq Lpt2_ (polar ss_obj_ins_ (deg-to-rad ss_obj_ins_ro) 98.8) ) ;300 = 98.8 , 275 = 86.3
    (setq Lpt2_1 (polar Lpt2_ (deg-to-rad (TA:ModifyRotation ss_obj_ins_ro -90)) 2000) ) 
    (LM:setdynpropvalue ss_obj_ "L2" (distance Lpt2_ (inters Lpt1_1 Lpt4_1   Lpt2_ Lpt2_1 )) )
    (command "point" Lpt2_1)
    (setq Lpt3_ (polar ss_obj_ins_ (deg-to-rad (TA:ModifyRotation ss_obj_ins_ro 180)) 98.8) ) ;300 = 98.8 , 275 = 86.3
    (setq Lpt3_1 (polar Lpt3_ (deg-to-rad (TA:ModifyRotation ss_obj_ins_ro -90)) 2000) )
    (LM:setdynpropvalue ss_obj_ "L3" (distance Lpt3_ (inters Lpt1_1 Lpt4_1   Lpt3_ Lpt3_1 )) )
    (LM:setdynpropvalue ss_obj_ "view" "6_bottom_view" )
    (if (= ucsedit 0)(progn (command "ucs" "p") )  )
  )
  (defun c:PPLINE_CKST_HatCVaries ()
    (setq ucsedit nil)
    (if (= (getvar "worlducs") 0)(progn (command "ucs" "WORLD") (setq ucsedit 0))  )
    (TA:vla-insertblock 
      ; "000 - DYNAMIC_ARRAY+COMBINE+VIEW_ASSCESSORIES_PLAN_AL.SOLID_SHEET_HAT-PROFILE_VA_COMBINE_SET" ;original
      "000 - DYNAMIC_LENGTH+COMBINE+VIEW_ASSCESSORIES_FAMELINE_AL.SOLID_SHEET_HAT-PROFILE-TYPE-C_non_code_COMBINE_SET"
      (setq newpt_ (getpoint))
      1
      (getangle newpt_)  
    )
    (setq ss_ename_ (entlast))
    (setq ss_obj_ (vlax-ename->vla-object ss_ename_))
    (setq ss_obj_ins_ (vlax-safearray->list (vlax-variant-value (vla-get-insertionpoint ss_obj_))))
    (vla-put-layer ss_obj_ "A11_ALU.SOLID SHEET")
    (vla-put-color ss_obj_ 0 )
    (setq ss_obj_ins_ro (TA:ModifyRotation (rad-to-deg (vla-get-rotation ss_obj_)) 90))
    (LM:setdynpropvalue ss_obj_ "view" "2_top_view")
    
    (setq Lpt1_ (polar ss_obj_ins_ (deg-to-rad ss_obj_ins_ro) 104.8) ) ;300 = 104.8 , 275 = 137.5
    (setq Lpt1_1 (polar Lpt1_ (deg-to-rad (TA:ModifyRotation ss_obj_ins_ro -90)) (LM:setdynpropvalue ss_obj_ "L" (getdist Lpt1_ "specify length 1"  ) )) )
    (setq Lpt4_ (polar ss_obj_ins_ (deg-to-rad (TA:ModifyRotation ss_obj_ins_ro 180)) 104.8) ) ;300 = 150 , 275 = 137.5
    (setq Lpt4_1 (polar Lpt4_ (deg-to-rad (TA:ModifyRotation ss_obj_ins_ro -90)) (LM:setdynpropvalue ss_obj_ "L4" (getdist Lpt4_ "specify length 1"  ) )) )
    
    (setq Lpt2_ (polar ss_obj_ins_ (deg-to-rad ss_obj_ins_ro) 98.8) ) ;300 = 98.8 , 275 = 86.3
    (setq Lpt2_1 (polar Lpt2_ (deg-to-rad (TA:ModifyRotation ss_obj_ins_ro -90)) 2000) )
    (LM:setdynpropvalue ss_obj_ "L2" (distance Lpt2_ (inters Lpt1_1 Lpt4_1   Lpt2_ Lpt2_1 )) )
    (setq Lpt3_ (polar ss_obj_ins_ (deg-to-rad (TA:ModifyRotation ss_obj_ins_ro 180)) 98.8) ) ;300 = 98.8 , 275 = 86.3
    (setq Lpt3_1 (polar Lpt3_ (deg-to-rad (TA:ModifyRotation ss_obj_ins_ro -90)) 2000) )
    (LM:setdynpropvalue ss_obj_ "L3" (distance Lpt3_ (inters Lpt1_1 Lpt4_1   Lpt3_ Lpt3_1 )) )
    
    (setq Lpt5_ (polar ss_obj_ins_ (deg-to-rad (TA:ModifyRotation ss_obj_ins_ro 0)) 100) ) ;300 = 106.25 , 275 = 86.3
    (setq Lpt5_1 (polar Lpt5_ (deg-to-rad (TA:ModifyRotation ss_obj_ins_ro -90)) 2000) )
    (LM:setdynpropvalue ss_obj_ "L5" (distance Lpt5_ (inters Lpt1_1 Lpt4_1   Lpt5_ Lpt5_1 )) )
    
    (setq Lpt6_ (polar ss_obj_ins_ (deg-to-rad (TA:ModifyRotation ss_obj_ins_ro 180)) 100) ) ;300 = 106.25 , 275 = 86.3
    (setq Lpt6_1 (polar Lpt6_ (deg-to-rad (TA:ModifyRotation ss_obj_ins_ro -90)) 2000) )
    (LM:setdynpropvalue ss_obj_ "L6" (distance Lpt6_ (inters Lpt1_1 Lpt4_1   Lpt6_ Lpt6_1 )) )
    
    
    
    (LM:setdynpropvalue ss_obj_ "view" "6_bottom_view" )
    (if (= ucsedit 0)(progn (command "ucs" "p") )  )
  )

  ;
  ;Extrusion PPLINE below ground
    ;update Func.
      (defun c:updateovl ()
        ;selection_set_for_fillter_blk_name
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        ;preloop_and_while
        ;switch window
              (textscr)
              (vla-put-WindowState (vlax-get-acad-object) acmin)
            ; 
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (if (or 
                  (= (LM:effectivename ss_pre_filter_set_xx_obj_ ) "000 - DYNAMIC_COMBINE+VIEW_ASSCESSORIES_FAMELINE_AL.EXTR._C-PROFILE_50x100mm._non-code_COMBINE_VIEW")
                  (= (LM:effectivename ss_pre_filter_set_xx_obj_ ) "000 - DYNAMIC_COMBINE+VIEW_ASSCESSORIES_FAMELINE_AL.EXTR._REC-PROFILE_50x100mm._non-code_COMBINE_VIEW")
                )
              (progn
                (if (or 
                      (= (LM:getdynpropvalue ss_pre_filter_set_xx_obj_ "view") "2_top_view")
                      (= (LM:getdynpropvalue ss_pre_filter_set_xx_obj_ "view") "6_bottom_view")
                    )
                  (progn
                    (LM:vl-setattributevalue ss_pre_filter_set_xx_obj_ "EXTR.OVL-LENGTH_" (rtos (car (vl-sort (cadr (TA:get-visible-boundingbox ss_pre_filter_set_xx_obj_) ) '>) ) 2 2))
                    (command "erase" "l" "")
                  )
                )
              )
            )
            (TA:textscr_process "insertion process " ss_pre_filter_set_xx_i ss_pre_filter_set_xx_)
            (setq ss_pre_filter_set_xx_i (+ ss_pre_filter_set_xx_i 1))
          )
        ;
      )
    ;
    ;000 - DYNAMIC_COMBINE+VIEW_ASSCESSORIES_FAMELINE_AL.EXTR._C-PROFILE_50x100mm._non-code_COMBINE_VIEW
    (defun c:PPLINE_CKST_EXTR-CVaries ()
      (setq ucsedit nil)
      (if (= (getvar "worlducs") 0)(progn (command "ucs" "WORLD") (setq ucsedit 0))  )
      (TA:vla-insertblock 
        ; "000 - DYNAMIC_ARRAY+COMBINE+VIEW_ASSCESSORIES_PLAN_AL.SOLID_SHEET_HAT-PROFILE_VA_COMBINE_SET" ;original
        "000 - DYNAMIC_COMBINE+VIEW_ASSCESSORIES_FAMELINE_AL.EXTR._C-PROFILE_50x100mm._non-code_COMBINE_VIEW"
        (setq newpt_ (getpoint "input point"))
        1
        (setq new_ang (angle newpt_ (setq newpt2_ (getpoint newpt_ "input angle")) ) )  
      )
      (setq ss_ename_ (entlast))
      (setq ss_obj_ (vlax-ename->vla-object ss_ename_))
      (setq ss_obj_ins_ (vlax-safearray->list (vlax-variant-value (vla-get-insertionpoint ss_obj_))))
      (vla-put-rotation ss_obj_ (deg-to-rad (TA:ModifyRotation (rad-to-deg new_ang) 270)))
      (vla-put-layer ss_obj_ "A04_TUBE SERIES")
      (vla-put-color ss_obj_ 0 )
      (setq ss_obj_ins_ro (TA:ModifyRotation (rad-to-deg (vla-get-rotation ss_obj_)) 0))
      (LM:setdynpropvalue ss_obj_ "view" "2_top_view")
      
      (setq Lpt1_ (polar ss_obj_ins_ (deg-to-rad ss_obj_ins_ro) 25) )
      
      (setq ERR nil)
      (setq ERR
        (vl-catch-all-apply
          (function
            (lambda ()
              (setq Lpt1_1 (polar Lpt1_ (deg-to-rad (TA:ModifyRotation ss_obj_ins_ro 90)) (LM:setdynpropvalue ss_obj_ "Hsub" (getdist Lpt1_ "specify length 1"  ) )) )
            )
          )
        )
      )
      
      (if (= (vl-catch-all-error-p ERR ) nil)
        (progn
          (setq Lpt4_ (polar ss_obj_ins_ (deg-to-rad (TA:ModifyRotation ss_obj_ins_ro 180)) 25) )
          (setq Lpt4_1 (polar Lpt4_ (deg-to-rad (TA:ModifyRotation ss_obj_ins_ro 90)) (LM:setdynpropvalue ss_obj_ "H" (getdist Lpt4_ "specify length 1"  ) )) )

          (setq Lpt2_ (polar ss_obj_ins_ (deg-to-rad ss_obj_ins_ro) 3.1) )
          (setq Lpt2_1 (polar Lpt2_ (deg-to-rad (TA:ModifyRotation ss_obj_ins_ro 90)) 200000) )
          (LM:setdynpropvalue ss_obj_ "Rail_2" (distance Lpt2_ (inters Lpt1_1 Lpt4_1   Lpt2_ Lpt2_1 )) )
          (setq Lpt3_ (polar ss_obj_ins_ (deg-to-rad (TA:ModifyRotation ss_obj_ins_ro 180)) 3.1) )
          (setq Lpt3_1 (polar Lpt3_ (deg-to-rad (TA:ModifyRotation ss_obj_ins_ro 90)) 200000) )
          (LM:setdynpropvalue ss_obj_ "Rail_1" (distance Lpt3_ (inters Lpt1_1 Lpt4_1   Lpt3_ Lpt3_1 )) )
        )
      )
      (if (= (vl-catch-all-error-p ERR ) T)
        (progn
          (LM:setdynpropvalue ss_obj_ "Hsub" (distance newpt_ newpt2_) )
          (LM:setdynpropvalue ss_obj_ "H" (distance newpt_ newpt2_) )
          (LM:setdynpropvalue ss_obj_ "Rail_2" (distance newpt_ newpt2_) )
          (LM:setdynpropvalue ss_obj_ "Rail_1" (distance newpt_ newpt2_) )
        )
      )
      (LM:setdynpropvalue ss_obj_ "view" "6_bottom_view" )
      (if (= ucsedit 0)(progn (command "ucs" "p") )  )
    )
    ;
    ;000 - DYNAMIC_COMBINE+VIEW_ASSCESSORIES_FAMELINE_AL.EXTR._REC-PROFILE_50x100mm._non-code_COMBINE_VIEW
    (defun c:PPLINE_CKST_EXTR-RECVaries ()
      (setq ucsedit nil)
      (if (= (getvar "worlducs") 0)(progn (command "ucs" "WORLD") (setq ucsedit 0))  )
      (TA:vla-insertblock 
        ; "000 - DYNAMIC_ARRAY+COMBINE+VIEW_ASSCESSORIES_PLAN_AL.SOLID_SHEET_HAT-PROFILE_VA_COMBINE_SET" ;original
        "000 - DYNAMIC_COMBINE+VIEW_ASSCESSORIES_FAMELINE_AL.EXTR._REC-PROFILE_50x100mm._non-code_COMBINE_VIEW"
        (setq newpt_ (getpoint "input point"))
        1
        (setq new_ang (angle newpt_ (setq newpt2_ (getpoint newpt_ "input angle")) ) )  
      )
      (setq ss_ename_ (entlast))
      (setq ss_obj_ (vlax-ename->vla-object ss_ename_))
      (setq ss_obj_ins_ (vlax-safearray->list (vlax-variant-value (vla-get-insertionpoint ss_obj_))))
      (vla-put-rotation ss_obj_ (deg-to-rad (TA:ModifyRotation (rad-to-deg new_ang) 270)))
      (vla-put-layer ss_obj_ "A04_TUBE SERIES")
      (vla-put-color ss_obj_ 0 )
      (setq ss_obj_ins_ro (TA:ModifyRotation (rad-to-deg (vla-get-rotation ss_obj_)) 0))
      (LM:setdynpropvalue ss_obj_ "view" "2_top_view")
      
      (setq Lpt1_ (polar ss_obj_ins_ (deg-to-rad ss_obj_ins_ro) 25) )
      
      (setq ERR nil)
      (setq ERR
        (vl-catch-all-apply
          (function
            (lambda ()
              (setq Lpt1_1 (polar Lpt1_ (deg-to-rad (TA:ModifyRotation ss_obj_ins_ro 90)) (LM:setdynpropvalue ss_obj_ "Hsub" (getdist Lpt1_ "specify length 1"  ) )) )
            )
          )
        )
      )
      
      (if (= (vl-catch-all-error-p ERR ) nil)
        (progn
          (setq Lpt4_ (polar ss_obj_ins_ (deg-to-rad (TA:ModifyRotation ss_obj_ins_ro 180)) 25) )
          (setq Lpt4_1 (polar Lpt4_ (deg-to-rad (TA:ModifyRotation ss_obj_ins_ro 90)) (LM:setdynpropvalue ss_obj_ "H" (getdist Lpt4_ "specify length 1"  ) )) )

          (setq Lpt2_ (polar ss_obj_ins_ (deg-to-rad ss_obj_ins_ro) 3.1) )
          (setq Lpt2_1 (polar Lpt2_ (deg-to-rad (TA:ModifyRotation ss_obj_ins_ro 90)) 200000) )
          (LM:setdynpropvalue ss_obj_ "Rail_2" (distance Lpt2_ (inters Lpt1_1 Lpt4_1   Lpt2_ Lpt2_1 )) )
          (setq Lpt3_ (polar ss_obj_ins_ (deg-to-rad (TA:ModifyRotation ss_obj_ins_ro 180)) 3.1) )
          (setq Lpt3_1 (polar Lpt3_ (deg-to-rad (TA:ModifyRotation ss_obj_ins_ro 90)) 200000) )
          (LM:setdynpropvalue ss_obj_ "Rail_1" (distance Lpt3_ (inters Lpt1_1 Lpt4_1   Lpt3_ Lpt3_1 )) )
        )
      )
      (if (= (vl-catch-all-error-p ERR ) T)
        (progn
          (LM:setdynpropvalue ss_obj_ "Hsub" (distance newpt_ newpt2_) )
          (LM:setdynpropvalue ss_obj_ "H" (distance newpt_ newpt2_) )
          (LM:setdynpropvalue ss_obj_ "Rail_2" (distance newpt_ newpt2_) )
          (LM:setdynpropvalue ss_obj_ "Rail_1" (distance newpt_ newpt2_) )
        )
      )
      (LM:setdynpropvalue ss_obj_ "view" "6_bottom_view" )
      (if (= ucsedit 0)(progn (command "ucs" "p") )  )
    )
    (defun c:Extr9 ()
      (TA:vla-insertblock 
        "000 - DYNAMIC_COMBINE+VIEW_ASSCESSORIES_FAMELINE_AL.EXTR._REC-PROFILE_50x100mm._non-code_COMBINE_VIEW"
        (setq pt1 (getpoint))
        1
        (setq new_rad (angle pt1 (setq pt2 (getpoint pt1) )))
      ) 
      ;new_blk_entlast object
        (setq sss_ename (entlast))
        (setq sss_obj_ (vlax-ename->vla-object sss_ename))
        (vla-put-rotation  sss_obj_ (deg-to-rad (TA:ModifyRotation (rad-to-deg new_rad) -90)))
        (LM:setdynpropvalue sss_obj_ "view" "6_bottom_view")
        (setq sss_ename (entlast))
        (setq sss_obj_ (vlax-ename->vla-object sss_ename))
        (setq H (LM:setdynpropvalue sss_obj_ "H" (- (distance pt1 pt2) 25)))
        (setq Hsub (LM:setdynpropvalue sss_obj_ "Hsub" (+ (distance pt1 pt2) 25)))
        
        (setq time_x 5)
      ;
      (while
        (= (vl-catch-all-error-p (setq Er-msg_detectloop (vl-catch-all-apply (function (lambda () (setq detectloop (getstring "enter to change length Object")) ) ) ) )) nil )
        (cond
          ( (and 
                ; (= H Hsub )
                (= time_x 5)
            )
            (progn
              (LM:setdynpropvalue sss_obj_ "H" (- (distance pt1 pt2) 50))
              (LM:setdynpropvalue sss_obj_ "Hsub" (+ (distance pt1 pt2) 50))
              (setq time_x 2)
            )
          )
          ( (and 
                ; (/= H Hsub )
                (= time_x 2)
              )
            (progn
              (LM:setdynpropvalue sss_obj_ "H" (+ (distance pt1 pt2) 0))
              (LM:setdynpropvalue sss_obj_ "Hsub" (- (distance pt1 pt2) 0))
              (setq time_x 3)
            )
          )
          ( (and 
                ; (/= H Hsub )
                (= time_x 3)
              )
            (progn
              (LM:setdynpropvalue sss_obj_ "H" (- (distance pt1 pt2) 0))
              (LM:setdynpropvalue sss_obj_ "Hsub" (+ (distance pt1 pt2) 50))
              (setq time_x 4)
            )
          )
          ( (and 
                ; (/= H Hsub )
                (= time_x 4)
              )
            (progn
              (LM:setdynpropvalue sss_obj_ "H" (- (distance pt1 pt2) 50))
              (LM:setdynpropvalue sss_obj_ "Hsub" (- (distance pt1 pt2) 0))
              (setq time_x 5)
            )
          )
        )
      )
      
    )
    ;
    (defun c:PPLINE_CKST_EXTR-LENGTH_RCLENGTH_RCL1 ()
      ;presetting
        (setq offset_length 0 )
      ;
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      (setq ss_pre_filter_set_xx_ (TA:EF_Filter_ss_set_v2_ ss_pre_filter_set_xx_ (list 
                                                                                    "000 - DYNAMIC_COMBINE+VIEW_ASSCESSORIES_FAMELINE_AL.EXTR._C-PROFILE_50x100mm._non-code_COMBINE_VIEW"
                                                                                    "000 - DYNAMIC_COMBINE+VIEW_ASSCESSORIES_FAMELINE_AL.EXTR._REC-PROFILE_50x100mm._non-code_COMBINE_VIEW"
                                                                                 ) 
                                  )
      )
      ;user_input
      (setq dyn_val_ (cond ( (getreal (strcat "\nspecify dyn_val_ <" (rtos (setq dyn_val_ (cond (dyn_val_) (10) ) ) ) "> : " ) ) ) (dyn_val_) ) )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_dynlist_ (LM:getdynprops ss_pre_filter_set_xx_obj_) )
          
          ;preloop_and_while
            (setq ss_pre_filter_set_xx_obj_dynlist_i 0)
            (while (< ss_pre_filter_set_xx_obj_dynlist_i (length ss_pre_filter_set_xx_obj_dynlist_))
              (setq ss_pre_filter_set_xx_obj_dynlist_list_ (nth  ss_pre_filter_set_xx_obj_dynlist_i ss_pre_filter_set_xx_obj_dynlist_))
              (if 
                (and 
                  (/= (car ss_pre_filter_set_xx_obj_dynlist_list_) "Origin")
                  (/= (car ss_pre_filter_set_xx_obj_dynlist_list_) "view")
                )
                (progn 
                  (LM:setdynpropvalue 
                    ss_pre_filter_set_xx_obj_
                    (car ss_pre_filter_set_xx_obj_dynlist_list_)
                    (+ 100 offset_length)
                  )
                )
              )
              (setq ss_pre_filter_set_xx_obj_dynlist_i (+ ss_pre_filter_set_xx_obj_dynlist_i 1))
            )
          ;
          
          (setq ss_pre_filter_set_xx_i (+ ss_pre_filter_set_xx_i 1))
        )
      ;
    )
  ;
  ;000 - DYNAMIC_COMBINE+VIEW_ASSCESSORIES_FAMELINE_BRACKET-L-PROFILE_50x68mm.+HEX_BOLT-M5-SET_non-code_COMBINE_SET
    (defun c:PPLINE-CKST-INSBK5068 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:EF_Filter_ss_set_ ss_pre_filter_set_xx_ "000 - DYNAMIC_COMBINE+VIEW_ASSCESSORIES_FAMELINE_GALV.BRACKET_FITTING_U-PROFILE_CC-01_COMBINE_VIEW"))
      ;
      
      ;preloop_and_while
        (setq ss_pre_filter_set_xx_i 0)
        (setq cc-01_inters_list_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_rotation_ (rad-to-deg (vla-get-rotation ss_pre_filter_set_xx_obj_)))
          (setq cc-01_inters_list_ 
            (cons 
              (list
                (polar ss_pre_filter_set_xx_obj_ins_  (deg-to-rad (TA:ModifyRotation ss_pre_filter_set_xx_obj_rotation_ 180)) (+ (LM:getdynpropvalue ss_pre_filter_set_xx_obj_ "fragment_left") (/ (LM:getdynpropvalue ss_pre_filter_set_xx_obj_ "array_length") 2)))
                (polar ss_pre_filter_set_xx_obj_ins_ 
                      (deg-to-rad (TA:ModifyRotation ss_pre_filter_set_xx_obj_rotation_ 0) )
                      (+ (/ (LM:getdynpropvalue ss_pre_filter_set_xx_obj_ "array_length") 2 ) (LM:getdynpropvalue ss_pre_filter_set_xx_obj_ "fragment_right") )
                )
              )
              cc-01_inters_list_
            )
          )  
          
          (setq ss_pre_filter_set_xx_i (+ ss_pre_filter_set_xx_i 1))
        )
      ;
      (setq Er-msg_ nil)
      (setvar "osmode" 0)
      (while
        (and (/= (vl-catch-all-error-p Er-msg_) T) )
        (graphscr)
        (setq Er-msg_ (vl-catch-all-apply (function (lambda () (setq ss_extr_ename_ (ssname  (ssget ":S" (list (cons 0 "INSERT") ) ) 0)) ) ) ) )
        (if (and 
              (/= (vl-catch-all-error-p Er-msg_) T)
              (or
                (= (LM:effectivename (vlax-ename->vla-object ss_extr_ename_)) "000 - DYNAMIC_COMBINE+VIEW_ASSCESSORIES_FAMELINE_AL.EXTR._C-PROFILE_50x100mm._non-code_COMBINE_VIEW")
                (= (LM:effectivename (vlax-ename->vla-object ss_extr_ename_)) "000 - DYNAMIC_COMBINE+VIEW_ASSCESSORIES_FAMELINE_AL.EXTR._REC-PROFILE_50x100mm._non-code_COMBINE_VIEW")
              )
            )
          (progn
            ;switch window
              (textscr)
              (vla-put-WindowState (vlax-get-acad-object) acmin)
            ; 

            (setq ss_extr_obj_ (vlax-ename->vla-object ss_extr_ename_))
            (setq ss_extr_ (TA:get-visible-boundingbox ss_extr_obj_))
            (command "erase" (entlast) "")
            (setq ssextr_ptmid1-4 (TA:midpoint (car (car ss_extr_)) (cadddr (car ss_extr_)) ) )
            (setq ssextr_ptmid2-3 (TA:midpoint (cadr (car ss_extr_)) (caddr (car ss_extr_)) ) )
          )
          (graphscr)
        )
        ;preloop_and_while
          (setq cc-01_inters_list_i 0)
          (while (and
                   (/= (vl-catch-all-error-p Er-msg_) T)
                   (< cc-01_inters_list_i (length cc-01_inters_list_) )
                 )
            (setq cc-01_inters_list_val_1 (car (nth  cc-01_inters_list_i cc-01_inters_list_)))
            (setq cc-01_inters_list_val_2 (cadr (nth  cc-01_inters_list_i cc-01_inters_list_)))
            
            (if (/= (inters ssextr_ptmid1-4 ssextr_ptmid2-3 cc-01_inters_list_val_1 cc-01_inters_list_val_2 ) nil)
              (progn
                (TA:vla-insertblock 
                  "000 - DYNAMIC_COMBINE+VIEW_ASSCESSORIES_FAMELINE_BRACKET-L-PROFILE_50x68mm.+HEX_BOLT-M5-SET_non-code_COMBINE_SET"
                  (inters ssextr_ptmid1-4 ssextr_ptmid2-3 cc-01_inters_list_val_1 cc-01_inters_list_val_2 )
                  1
                  0
                )
                ;new_blk_entlast object
                  (setq new_ename (entlast))
                  (setq new_obj_ (vlax-ename->vla-object new_ename))
                  (TA:move_axis_insertionpoint new_obj_ "x" -17)
                  (LM:setdynpropvalue new_obj_  "view" "2_top_view")
                ; 
              )
            )
   
            (TA:textscr_process "insertion process " cc-01_inters_list_i cc-01_inters_list_)
        
            (setq cc-01_inters_list_i (+ cc-01_inters_list_i 1))
          )
        ;
        
      )
      (setvar "osmode" 1215)
    )
    (defun c:PPLINE-CKST-INSBK5045 ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx_ (TA:EF_Filter_ss_set_ ss_pre_filter_set_xx_ "000 - DYNAMIC_COMBINE+VIEW_ASSCESSORIES_FAMELINE_GALV.BRACKET_FITTING_U-PROFILE_CC-01_COMBINE_VIEW"))
      ;
      ;preloop_and_while
        (setq ss_pre_filter_set_xx_i 0)
        (setq cc-01_inters_list_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_rotation_ (rad-to-deg (vla-get-rotation ss_pre_filter_set_xx_obj_)))
          (setq cc-01_inters_list_ 
            (cons 
              (list
                (polar ss_pre_filter_set_xx_obj_ins_  (deg-to-rad (TA:ModifyRotation ss_pre_filter_set_xx_obj_rotation_ 180)) (+ (LM:getdynpropvalue ss_pre_filter_set_xx_obj_ "fragment_left") (/ (LM:getdynpropvalue ss_pre_filter_set_xx_obj_ "array_length") 2)))
                (polar ss_pre_filter_set_xx_obj_ins_ 
                      (deg-to-rad (TA:ModifyRotation ss_pre_filter_set_xx_obj_rotation_ 0) )
                      (+ (/ (LM:getdynpropvalue ss_pre_filter_set_xx_obj_ "array_length") 2 ) (LM:getdynpropvalue ss_pre_filter_set_xx_obj_ "fragment_right") )
                )
              )
              cc-01_inters_list_
            )
          )  
          
          (setq ss_pre_filter_set_xx_i (+ ss_pre_filter_set_xx_i 1))
        )
      ;
      (setq Er-msg_ nil)
      (setvar "osmode" 0)
      (while
        (and (/= (vl-catch-all-error-p Er-msg_) T) )
        (graphscr)
        (setq Er-msg_ (vl-catch-all-apply (function (lambda () (setq ss_extr_ename_ (ssname  (ssget ":S" (list (cons 0 "INSERT") ) ) 0)) ) ) ) )
        
        (if (and 
              (/= (vl-catch-all-error-p Er-msg_) T)
              (or
                (= (LM:effectivename (vlax-ename->vla-object ss_extr_ename_)) "000 - DYNAMIC_COMBINE+VIEW_ASSCESSORIES_FAMELINE_AL.EXTR._C-PROFILE_50x100mm._non-code_COMBINE_VIEW")
                (= (LM:effectivename (vlax-ename->vla-object ss_extr_ename_)) "000 - DYNAMIC_COMBINE+VIEW_ASSCESSORIES_FAMELINE_AL.EXTR._REC-PROFILE_50x100mm._non-code_COMBINE_VIEW") 
              )
            )

          (progn
            ;switch window
              (textscr)
              (vla-put-WindowState (vlax-get-acad-object) acmin)
            ; 
            (setq ss_extr_obj_ (vlax-ename->vla-object ss_extr_ename_))
            (setq ss_extr_ (TA:get-visible-boundingbox ss_extr_obj_))
            (command "erase" (entlast) "")
            (setq ssextr_ptmid1-4 (TA:midpoint (car (car ss_extr_)) (cadddr (car ss_extr_)) ) )
            (setq ssextr_ptmid2-3 (TA:midpoint (cadr (car ss_extr_)) (caddr (car ss_extr_)) ) )
          )
          (graphscr)
        )
        ;preloop_and_while
          (setq cc-01_inters_list_i 0)
          (while (and
                   (/= (vl-catch-all-error-p Er-msg_) T)
                   (< cc-01_inters_list_i (length cc-01_inters_list_) )
                 )
            (setq cc-01_inters_list_val_1 (car (nth  cc-01_inters_list_i cc-01_inters_list_)))
            (setq cc-01_inters_list_val_2 (cadr (nth  cc-01_inters_list_i cc-01_inters_list_)))
            
            (if (/= (inters ssextr_ptmid1-4 ssextr_ptmid2-3 cc-01_inters_list_val_1 cc-01_inters_list_val_2 ) nil)
              (progn
                (TA:vla-insertblock 
                  "000 - DYNAMIC_COMBINE+VIEW_ASSCESSORIES_FAMELINE_BRACKET-L-PROFILE_50x45mm.+HEX_BOLT-M5-SET_non-code_COMBINE_SET"
                  (inters ssextr_ptmid1-4 ssextr_ptmid2-3 cc-01_inters_list_val_1 cc-01_inters_list_val_2 )
                  1
                  0
                )
                ;new_blk_entlast object
                  (setq new_ename (entlast))
                  (setq new_obj_ (vlax-ename->vla-object new_ename))
                  (TA:move_axis_insertionpoint new_obj_ "x" -17)
                  (LM:setdynpropvalue new_obj_  "view" "2_top_view")
                ; 
              )
            )
   
            (TA:textscr_process "insertion process " cc-01_inters_list_i cc-01_inters_list_)
        
            (setq cc-01_inters_list_i (+ cc-01_inters_list_i 1))
          )
        ;
        
      )
      (setvar "osmode" 1215)
    )

    (defun TA:Switch_lookup (ss_pre_filter_set_xx_ blk_fitter_name_ blk_filter_tag_)
      ;presetting
        ; (setq blk_fitter_name_ "000 - TRANSFER")
        ; (setq blk_filter_tag_ "lookup1")
      ;
      ;selection_set_for_fillter_blk_name
        ; (if  ;pre_select_ssget_or_post_select_ssget
        ;   (=
        ;     (setq ss_pre_filter_set_xx_ (ssget "i"
        ;                                       (list
        ;                                         (cons 0 "INSERT") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;     nil
        ;   )
        ;   (progn
        ;     (setq ss_pre_filter_set_xx_ (ssget
        ;                                       (list
        ;                                         (cons 0 "INSERT") ;type of object
        ;                                         ; (cons 8 "000 - GRID")   ;kind of layer
        ;                                         ; (cons 2 "000-GRID_LINE_DYN")       ;kind of nameblock
        ;                                         ; (cons 62 1)           ;kind of color call sign with color code index
        ;                                       )
        ;                                 )
        ;     )
        ;   )
        ;   (sslength ss_pre_filter_set_xx_)
        ; )
        ; (setq ss_pre_filter_set_xx_ (TA:EF_Filter_ss_set_ ss_pre_filter_set_xx_ blk_fitter_name_))
      ;
      ;presetting dynamic tag&val
        (setq ss_pre_filter_set_xx_ename_ (ssname ss_pre_filter_set_xx_ 0))
        (setq ss_pre_filter_set_xx_obj_ (vlax-ename->vla-object  ss_pre_filter_set_xx_ename_))
        (setq ss_pre_filter_set_xx_obj_vis-value_ (LM:getdynpropallowedvalues ss_pre_filter_set_xx_obj_ blk_filter_tag_))
        (setq ss_pre_filter_set_xx_obj_vis-length_ (length ss_pre_filter_set_xx_obj_vis-value_))
        (setq ERR_ nil)
        (while 
          (and
            (= (vl-catch-all-error-p ERR_) nil)
          )
          (setq ERR_
            (vl-catch-all-apply
              (function
                (lambda ()
                  (setq vis_value (cond 
                                    ((getint 
                                       (strcat "\n0 = previous \n1 = next \n<" (rtos (setq vis_value (cond (vis_value) (1.0) ) ) ) "> : " )
                                     )
                                    )
                                    (vis_value)
                                  )
                  )
                )
              )
            )
          )
          ;preloop_and_while
            (setq ss_pre_filter_set_xx_i 0)
            (while (and 
                     (= (vl-catch-all-error-p ERR_) nil)
                     (< ss_pre_filter_set_xx_i (sslength ss_pre_filter_set_xx_))
                   ) 
              (setq ss_pre_filter_set_xx_ename_ (ssname ss_pre_filter_set_xx_ ss_pre_filter_set_xx_i))
              (setq ss_pre_filter_set_xx_obj_ (vlax-ename->vla-object  ss_pre_filter_set_xx_ename_))
              (setq ss_pre_filter_set_xx_obj_vis-value_ (LM:getdynpropallowedvalues ss_pre_filter_set_xx_obj_ "lookup1"))
              (setq ss_pre_filter_set_xx_obj_currrent_vis_val_ 
                      (car 
                         (TA:find-all-indexes 
                           (LM:getdynpropvalue ss_pre_filter_set_xx_obj_ "lookup1")
                           ss_pre_filter_set_xx_obj_vis-value_
                         )
                       )
              )
              (if (or 
                    (>= (+ ss_pre_filter_set_xx_obj_currrent_vis_val_ vis_value) ss_pre_filter_set_xx_obj_vis-length_)
                  )
                (progn
                  (LM:setdynpropvalue ss_pre_filter_set_xx_obj_ 
                    blk_filter_tag_ 
                    (nth 0 ss_pre_filter_set_xx_obj_vis-value_)
                  )
                )
                (cond
                  ((and ;plus cond
                    (/= (+ ss_pre_filter_set_xx_obj_currrent_vis_val_ vis_value) ss_pre_filter_set_xx_obj_vis-length_)
                    (>= vis_value 1)
                  )
                    (progn
                      (LM:setdynpropvalue ss_pre_filter_set_xx_obj_ 
                        blk_filter_tag_ 
                        (nth (fix (+ ss_pre_filter_set_xx_obj_currrent_vis_val_ vis_value )) ss_pre_filter_set_xx_obj_vis-value_)
                      )
                    )
                  )
                  ((and ;minus cond
                     (< (- ss_pre_filter_set_xx_obj_currrent_vis_val_ 1) 0)
                     (< vis_value 1)
                   )
                    (progn
                      (LM:setdynpropvalue ss_pre_filter_set_xx_obj_ 
                        blk_filter_tag_ 
                        (nth (fix (- ss_pre_filter_set_xx_obj_vis-length_ 1 )) ss_pre_filter_set_xx_obj_vis-value_)
                      )
                    )
                  )
                  ((and ;minus cond
                     (>= (- ss_pre_filter_set_xx_obj_currrent_vis_val_ 1) 0)
                     (< vis_value 1)
                   )
                    (progn
                      (LM:setdynpropvalue ss_pre_filter_set_xx_obj_ 
                        blk_filter_tag_ 
                        (nth (fix (- ss_pre_filter_set_xx_obj_currrent_vis_val_ 1 )) ss_pre_filter_set_xx_obj_vis-value_)
                      )
                    )
                  )
                )
              )
              
              (setq ss_pre_filter_set_xx_i (+ ss_pre_filter_set_xx_i 1))
            )
          ;
          
        )
      ;

        
      ;
      
    )
    (defun c:tranfer_length_TFL ()
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        (setq ss_pre_filter_set_xx (TA:EF_Filter_ss_set_ ss_pre_filter_set_xx_ "000 - TRANSFER"))
      ;
      (TA:Switch_lookup ss_pre_filter_set_xx "000 - TRANSFER" "lookup1")
    )
    (defun c:rectangle_to_transfer ()
      (setq rectangle_ename_ (car (entsel "specify Object")))
      (setq rectangle_obj_ (vlax-ename->vla-object rectangle_ename_))
      (TA:assembly_coordinate_coner (TA:Find_boundary_line_ rectangle_ename_))
    )
  ;
  ;000 - DYNAMIC_COMBINE+VIEW_ASSCESSORIES_FAMELINE_GALV.BRACKET_FITTING_U-PROFILE_CC-01_COMBINE_VIEW
  ; (defun c:PPLINE_300HK_inscc01_ ()
  ;   ;selection_set_for_fillter_blk_name
  ;     (if  ;pre_select_ssget_or_post_select_ssget
  ;       (=
  ;         (setq ss_pre_filter_set_xx_ (ssget "i"
  ;                                           (list
  ;                                             (cons 0 "LINE") ;type of object
  ;                                             ; (cons 8 "000 - GRID")   ;kind of layer
  ;                                             ; (cons 2 "000-GRID_LINE_DYN")       ;kind of nameblock
  ;                                             ; (cons 62 1)           ;kind of color call sign with color code index
  ;                                           )
  ;                                     )
  ;         )
  ;         nil
  ;       )
  ;       (progn
  ;         (setq ss_pre_filter_set_xx_ (ssget
  ;                                           (list
  ;                                             (cons 0 "LINE") ;type of object
  ;                                             ; (cons 8 "000 - GRID")   ;kind of layer
  ;                                             ; (cons 2 "000-GRID_LINE_DYN")       ;kind of nameblock
  ;                                             ; (cons 62 1)           ;kind of color call sign with color code index
  ;                                           )
  ;                                     )
  ;         )
  ;       )
  ;       (sslength ss_pre_filter_set_xx_)
  ;     )
  ;   ;
  ;   ;
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object ss_pre_filter_set_xx_ename_))
  ;       (setq obj_ ss_pre_filter_set_xx_obj_)
  ;       ;get-propertie_data
  ;         (setq ss_pre_filter_set_xx_obj_angle_ (vla-get-angle ss_pre_filter_set_xx_obj_))  
  ;         (setq ss_pre_filter_set_xx_obj_length_ (vla-get-length ss_pre_filter_set_xx_obj_))
  ;         (setq ss_pre_filter_set_xx_obj_start_end_pt_ (list
  ;                                         (setq ss_pre_filter_set_xx_obj_startpt_ (vlax-safearray->list
  ;                                                                    (vlax-variant-value ( vla-get-startpoint ss_pre_filter_set_xx_obj_ ))
  ;                                                                  )
  ;                                         )
  ;                                         (setq ss_pre_filter_set_xx_obj_endpt_ (vlax-safearray->list
  ;                                                                   (vlax-variant-value ( vla-get-endpoint ss_pre_filter_set_xx_obj_ ))
  ;                                                                )
  ;                                         )
  ;                                       )
  ;         )
        
  ;       ;
  ;       (TA:vla-insertblock
  ;         "000 - DYNAMIC_COMBINE+VIEW_ASSCESSORIES_FAMELINE_GALV.BRACKET_FITTING_U-PROFILE_CC-01_COMBINE_VIEW" 
  ;         (TA:midpoint ss_pre_filter_set_xx_obj_startpt_ ss_pre_filter_set_xx_obj_endpt_ )
  ;         1
  ;         ss_pre_filter_set_xx_obj_angle_
  ;       )
  ;       ;new_blk_entlast object
  ;         (setq newinsert_ename (entlast))
  ;         (setq newinsert_obj_ (vlax-ename->vla-object newinsert_ename))
  ;         (LM:setdynpropvalue newinsert_obj_ (LM:getvisibilityparametername newinsert_obj_) "2_top_view" )
  ;         (LM:setdynpropvalue newinsert_obj_ "array_length" (* 3000 (fix (/ ss_pre_filter_set_xx_obj_length_ 3000))) )
  ;         (LM:setdynpropvalue newinsert_obj_ "fragment_left" (/ (- ss_pre_filter_set_xx_obj_length_ (* 3000 (fix (/ ss_pre_filter_set_xx_obj_length_ 3000))) ) 2 ) )
  ;         (LM:setdynpropvalue newinsert_obj_ "fragment_right" (/ (- ss_pre_filter_set_xx_obj_length_ (* 3000 (fix (/ ss_pre_filter_set_xx_obj_length_ 3000))) ) 2 ) )
  ;       ;
  ;       (setq ss_pre_filter_set_xx_i (+ ss_pre_filter_set_xx_i 1))
  ;     )
  ;   ;
    
  ;   ;
  ; )
  (defun c:PPLINE_300HK_inscc01_ ()
    ;selection_set_for_fillter_blk_name
      (if  ;pre_select_ssget_or_post_select_ssget
        (=
          (setq ss_pre_filter_set_xx_ (ssget "i"
                                            (list
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "LINE") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;while_select_block_on_condition_
        (setq direction_ename_ nil)
        (while (= direction_ename_ nil)
          (setq direction_ename_ (car (entsel "specify direction_ename Object")))
          (if
            (and ;conditional_rule_for_select_object
              (/= direction_ename_ nil)
              (setq direction_ename_obj_ (vlax-ename->vla-object direction_ename_))
              (= (vla-get-objectname direction_ename_obj_ ) "AcDbLine")
            )
            (progn
              (setq direction_ename_obj_angle_ (vla-get-angle direction_ename_obj_) )
            )
            (alert "Object invalid Please try again")
          )
        )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (setq obj_ ss_pre_filter_set_xx_obj_)
        ;get-propertie_data
          (setq ss_pre_filter_set_xx_obj_angle_ (vla-get-angle ss_pre_filter_set_xx_obj_))  
          (setq ss_pre_filter_set_xx_obj_length_ (vla-get-length ss_pre_filter_set_xx_obj_))
          (setq ss_pre_filter_set_xx_obj_start_end_pt_ (list
                                          (setq ss_pre_filter_set_xx_obj_startpt_ (vlax-safearray->list
                                                                     (vlax-variant-value ( vla-get-startpoint ss_pre_filter_set_xx_obj_ ))
                                                                   )
                                          )
                                          (setq ss_pre_filter_set_xx_obj_endpt_ (vlax-safearray->list
                                                                    (vlax-variant-value ( vla-get-endpoint ss_pre_filter_set_xx_obj_ ))
                                                                 )
                                          )
                                        )
          )
        
        ;
        (TA:vla-insertblock
          "000 - DYNAMIC_COMBINE+VIEW_ASSCESSORIES_FAMELINE_GALV.BRACKET_FITTING_U-PROFILE_CC-01_COMBINE_VIEW" 
          (TA:midpoint ss_pre_filter_set_xx_obj_startpt_ ss_pre_filter_set_xx_obj_endpt_ )
          1
          ss_pre_filter_set_xx_obj_angle_
        )
        ;new_blk_entlast object
          (setq newinsert_ename (entlast))
          (setq newinsert_obj_ (vlax-ename->vla-object newinsert_ename))
          (cond ;visibility&length condition
            ( (> ss_pre_filter_set_xx_obj_length_ 3000 ) ;visibility&length condition
              (progn
                (LM:setdynpropvalue newinsert_obj_ (LM:getvisibilityparametername newinsert_obj_) "2_top_view" )
                (LM:setdynpropvalue newinsert_obj_ "array_length" (* 3000 (fix (/ ss_pre_filter_set_xx_obj_length_ 3000))) )
                (LM:setdynpropvalue newinsert_obj_ "fragment_left" (/ (- ss_pre_filter_set_xx_obj_length_ (* 3000 (fix (/ ss_pre_filter_set_xx_obj_length_ 3000))) ) 2 ) )
                (LM:setdynpropvalue newinsert_obj_ "fragment_right" (/ (- ss_pre_filter_set_xx_obj_length_ (* 3000 (fix (/ ss_pre_filter_set_xx_obj_length_ 3000))) ) 2 ) )
              )
            )
            ( (<= ss_pre_filter_set_xx_obj_length_ 3000 ) ;visibility&length condition
              (progn
                (LM:setdynpropvalue newinsert_obj_ (LM:getvisibilityparametername newinsert_obj_) "7_dynamic_length_view" )
                (LM:setdynpropvalue newinsert_obj_ "fragment_middle" ss_pre_filter_set_xx_obj_length_ )
              )
            )
          )
          
        ;
        (setq ss_pre_filter_set_xx_i (+ ss_pre_filter_set_xx_i 1))
      )
    ;
    
    ;
  )
  (defun c:PPLINE_300HK_inscc011_ ()
    ;selection_set_for_fillter_blk_name
      (if  ;pre_select_ssget_or_post_select_ssget
        (=
          (setq ss_pre_filter_set_xx_ (ssget "i"
                                            (list
                                              (cons 0 "LINE") ;type of object
                                              ; (cons 8 "000 - GRID")   ;kind of layer
                                              ; (cons 2 "000-GRID_LINE_DYN")       ;kind of nameblock
                                              (cons 62 6)           ;kind of color call sign with color code index
                                            )
                                      )
          )
          nil
        )
        (progn
          (setq ss_pre_filter_set_xx_ (ssget
                                            (list
                                              (cons 0 "LINE") ;type of object
                                              ; (cons 8 "000 - GRID")   ;kind of layer
                                              ; (cons 2 "000-GRID_LINE_DYN")       ;kind of nameblock
                                              (cons 62 6)           ;kind of color call sign with color code index
                                            )
                                      )
          )
        )
        (sslength ss_pre_filter_set_xx_)
      )
    ;
    ;while_select_block_on_condition_
        (setq direction_ename_ nil)
        
        (while (= direction_ename_ nil)
          (setq direction_ename_ (car (entsel "specify direction_ename Object")))
          (if
            (and ;conditional_rule_for_select_object
              (/= direction_ename_ nil)
              (setq direction_ename_obj_ (vlax-ename->vla-object direction_ename_))
              (= (vla-get-objectname direction_ename_obj_ ) "AcDbLine")
            )
            (progn
              (setq direction_ename_obj_angle_ (vla-get-angle direction_ename_obj_) )
            )
            (alert "Object invalid Please try again")
          )
        )
        
    ;
    ;preloop_and_while
      (setq ss_pre_filter_set_xx_i 0)
      (setq lasted_cc01_ssset (ssadd))
      ; (TA:interface_text_ T)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (setq obj_ ss_pre_filter_set_xx_obj_)
        ;get-propertie_data
          (setq ss_pre_filter_set_xx_obj_angle_ (vla-get-angle ss_pre_filter_set_xx_obj_))  
          (setq ss_pre_filter_set_xx_obj_length_ (vla-get-length ss_pre_filter_set_xx_obj_))
          (setq ss_pre_filter_set_xx_obj_start_end_pt_ (list
                                          (setq ss_pre_filter_set_xx_obj_startpt_ (vlax-safearray->list
                                                                     (vlax-variant-value ( vla-get-startpoint ss_pre_filter_set_xx_obj_ ))
                                                                   )
                                          )
                                          (setq ss_pre_filter_set_xx_obj_endpt_ (vlax-safearray->list
                                                                    (vlax-variant-value ( vla-get-endpoint ss_pre_filter_set_xx_obj_ ))
                                                                 )
                                          )
                                        )
          )
          (setq array_length (* (fix (/ ss_pre_filter_set_xx_obj_length_ 3000 )) 3000))
          (setq ins_stamp (- (/ (* (fix (/ ss_pre_filter_set_xx_obj_length_ 3000 )) 3000) 2) 25))
          (if (<= ins_stamp 0)
            (progn
              (setq ins_stamp (* (fix (/ (/ ss_pre_filter_set_xx_obj_length_ 2)  25)) 25))
              (setq main_fragment_length_ (* (fix (/ ss_pre_filter_set_xx_obj_length_ 100)) 100))
              (setq sub_fragment_length_ (LM:roundup (/ (- ss_pre_filter_set_xx_obj_length_ main_fragment_length_) ) 100))
              (setq total_frament_length_ (+ (+ main_fragment_length_ sub_fragment_length_ ) 50) ) ;50 คือเผื่อ
              
            )
            ins_stamp
          )
        ;
        (TA:vla-insertblock
          "000 - DYNAMIC_COMBINE+VIEW_ASSCESSORIES_FAMELINE_GALV.BRACKET_FITTING_U-PROFILE_CC-01_COMBINE_VIEW" 
          (vlax-curve-getpointatdist ss_pre_filter_set_xx_obj_  ins_stamp) ;คำนวณเพื่อ ins ลง ตามตำแหน่งของ line โดยให้ยืด array_length พอแค่ฝั่งเดียว
          1
          ss_pre_filter_set_xx_obj_angle_
        )
        ;new_blk_entlast object
          (setq newinsert_ename (entlast))
          (setq newinsert_obj_ (vlax-ename->vla-object newinsert_ename))
          (setq lasted_cc01_ssset (ssadd newinsert_ename lasted_cc01_ssset))
          (cond ;visibility&length condition
            ( (> ss_pre_filter_set_xx_obj_length_ 3000 ) ;visibility&length condition
              (progn
                (LM:setdynpropvalue newinsert_obj_ (LM:getvisibilityparametername newinsert_obj_) "2_top_view" )
                (LM:setdynpropvalue newinsert_obj_ "array_length" array_length )
                (LM:setdynpropvalue newinsert_obj_ "fragment_left" 0 )
                (LM:setdynpropvalue newinsert_obj_ "fragment_right" (+ (+ (fix (- ss_pre_filter_set_xx_obj_length_ array_length )) 25) 45) )
              )
            )
              ((<= ss_pre_filter_set_xx_obj_length_ 3000)  ;visibility&length condition
                (progn 
                  (LM:setdynpropvalue 
                    newinsert_obj_
                    (LM:getvisibilityparametername newinsert_obj_)
                    "7_dynamic_length_view"
                  )
                  (LM:setdynpropvalue 
                    newinsert_obj_
                    "fragment_middle"
                    total_frament_length_
                  )
                )
              )
          )
          
        ;
        (TA:textscr_process_V2 "inserting subfame" ss_pre_filter_set_xx_i ss_pre_filter_set_xx_)
        (setq ss_pre_filter_set_xx_i (+ ss_pre_filter_set_xx_i 1))
      )
    ;
      (command "pselect"  ss_pre_filter_set_xx_ "" )
    ;
    (TA:interface_text_ Nil)
  )
  (defun c:call_lasted_ssset_cc01_lscc01 ()
    (command "pselect"  lasted_cc01_ssset "" )
  )
  (defun c:ssc011 ()
    ;selection_set_for_fillter_blk_name
      (if  ;pre_select_ssget_or_post_select_ssget
        (=
          (setq c011_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq c011_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength c011_)
      )
      (setq c011_ (TA:EF_Filter_ss_set_V2_  c011_ (list 
                                                    "000 - DYNAMIC_COMBINE+VIEW_ASSCESSORIES_FAMELINE_GALV.BRACKET_FITTING_U-PROFILE_CC-01_COMBINE_VIEW" 
                                                    "000 - DYNAMIC_COMBINE+VIEW_ASSCESSORIES_FAMELINE_GALV.BRACKET_FITTING_U-PROFILE_CC-01-4_COMBINE_VIEW"
                                                  )
                  )
      )
    ;
    (setq ERR_ nil)
    (while ;for keep insertion point and dist. fix length one side
      (and
        (= (vl-catch-all-error-p ERR_) nil)
      )
      (setq ERR_
        (vl-catch-all-apply
          (function
            (lambda ()
              (setq increment_num_ (cond ( (getint (strcat "\nSpecify sss_   <" (rtos (setq increment_num_ (cond (increment_num_) (1.0) ) ) ) "> : " ) ) ) (increment_num_) ) )
            )
          )
        )
      )
      ;preloop_and_while
        (setq c011_i 0)
        (while 
          (and
            (= (vl-catch-all-error-p ERR_) nil)
            (< c011_i (sslength c011_))
          )
          (setq c011_ename_ (ssname c011_ c011_i)) 
          (setq c011_obj_ (vlax-ename->vla-object  c011_ename_))
          (setq c011_obj_ins_ (vlax-safearray->list (vlax-variant-value (vla-get-insertionpoint c011_obj_))))
          (setq c011_obj_fragment_mid_ (LM:getdynpropvalue c011_obj_ "fragment_middle" ))
          (setq c011_obj_array_length_ (LM:getdynpropvalue c011_obj_ "array_length" ))
          
          (cond
            (;ssss_case_1
              (and
                  (= (vl-catch-all-error-p ERR_) nil)
                  (= (LM:getdynpropvalue c011_obj_ "view") "7_dynamic_length_view" )
                  (= increment_num_ 1)
              )
              (progn
                (LM:setdynpropvalue c011_obj_ "fragment_middle" (setq c011_obj_fragment_mid_ (+ c011_obj_fragment_mid_ 25)))
                (TA:move_polar_insertionpoint  c011_obj_ "Y" -12.5)
                (princ "ssss_case_1")
              )
            )
            (;ssss_case_2
              (and
                  (= (vl-catch-all-error-p ERR_) nil)
                  (= (LM:getdynpropvalue c011_obj_ "view") "7_dynamic_length_view" )
                  (= increment_num_ 0)
              )
              (progn
                (LM:setdynpropvalue c011_obj_ "fragment_middle" (setq c011_obj_fragment_mid_ (- c011_obj_fragment_mid_ 25)))
                (TA:move_polar_insertionpoint  c011_obj_ "Y" 12.5)
                (princ "ssss_case_2")
              )
            )
            (;ssss_case_2-1
              (and
                  (= (vl-catch-all-error-p ERR_) nil)
                  (= (LM:getdynpropvalue c011_obj_ "view") "7_dynamic_length_view" )
                  (< increment_num_ 0)
                  (> (fix c011_obj_fragment_mid_)   )
              )
              (progn
                (LM:setdynpropvalue c011_obj_ "fragment_middle" (setq c011_obj_fragment_mid_ (- c011_obj_fragment_mid_ (* 25 (abs increment_num_)))))
                (TA:move_polar_insertionpoint  c011_obj_ "Y" (* 12.5 (abs increment_num_)) )
                (princ "ssss_case_2")
              )
            )
            (;ssss_case_2-2
              (and
                  (= (vl-catch-all-error-p ERR_) nil)
                  (= (LM:getdynpropvalue c011_obj_ "view") "7_dynamic_length_view" )      
                  (> increment_num_ 0)
                  (<  (fix c011_obj_fragment_mid_) 3000)
                  (< (+ c011_obj_fragment_mid_ (* 25 increment_num_ ) ) 3000 )
              )
              (progn
                (LM:setdynpropvalue c011_obj_ "fragment_middle" (setq c011_obj_fragment_mid_ (+ c011_obj_fragment_mid_ (* 25 increment_num_))))
                (TA:move_polar_insertionpoint  c011_obj_ "Y" (* 12.5 (- increment_num_)) )
                (princ "ssss_case_2")
              )
            )
            (;ssss_case_3
              (and
                  (= (vl-catch-all-error-p ERR_) nil)
                  (= (LM:getdynpropvalue c011_obj_ "view") "2_top_view" )
                  (= increment_num_ 1)
              )
              (progn
                (LM:setdynpropvalue c011_obj_ "array_length" (setq c011_obj_array_length_ (+ c011_obj_array_length_ 3000)))
                (TA:move_polar_insertionpoint  c011_obj_ "Y" -1500)
                (princ "ssss_case_3")
              )
            )
            (;ssss_case_4
              (and
                  (= (vl-catch-all-error-p ERR_) nil)
                  (= (LM:getdynpropvalue c011_obj_ "view") "2_top_view" )
                  (/= (LM:getdynpropvalue c011_obj_ "array_length") 3000 )
                  (= increment_num_ 0)
              )
              (progn
                (LM:setdynpropvalue c011_obj_ "array_length" (setq c011_obj_array_length_ (- c011_obj_array_length_ 3000)))
                (TA:move_polar_insertionpoint  c011_obj_ "Y" 1500)
                (princ "ssss_case_4")
              )
            )
          )
          
          
          (setq c011_i (+ c011_i 1))
        )
      ;
    )
  )
  ;
  ;000 - DYNAMIC_COMBINE+VIEW_ASSCESSORIES_FAMELINE_GALV.BRACKET_FITTING_U-PROFILE_CC-01-4_COMBINE_VIEW
  (defun c:PPLINE_300HK_inscc012_ ()
    ;selection_set_for_fillter_blk_name
      (if  ;pre_select_ssget_or_post_select_ssget
        (=
          (setq ss_pre_filter_set_xx_ (ssget "i"
                                            (list
                                              (cons 0 "line") ;type of object
                                              ; (cons 8 "000 - GRID")   ;kind of layer
                                              ; (cons 2 "000-GRID_LINE_DYN")       ;kind of nameblock
                                              (cons 62 6)           ;kind of color call sign with color code index
                                            )
                                      )
          )
          nil
        )
        (progn
          (setq ss_pre_filter_set_xx_ (ssget
                                            (list
                                              (cons 0 "line") ;type of object
                                              ; (cons 8 "000 - GRID")   ;kind of layer
                                              ; (cons 2 "000-GRID_LINE_DYN")       ;kind of nameblock
                                              (cons 62 6)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_angle (TA:ModifyRotation (rad-to-deg (vla-get-angle  ss_pre_filter_set_xx_obj_)) -270))
        (setq ss_pre_filter_set_xx_obj_start_end_pt_ (list
                                        (setq ss_pre_filter_set_xx_obj_startpt_ (vlax-safearray->list
                                                                   (vlax-variant-value ( vla-get-startpoint ss_pre_filter_set_xx_obj_ ))
                                                                 )
                                        )
                                        (setq ss_pre_filter_set_xx_obj_endpt_ (vlax-safearray->list
                                                                  (vlax-variant-value ( vla-get-endpoint ss_pre_filter_set_xx_obj_ ))
                                                               )
                                        )
                                      )
        )
        (cond 
          ( ;_case_1
           (and 
             (> (distance (car ss_pre_filter_set_xx_obj_start_end_pt_) (cadr ss_pre_filter_set_xx_obj_start_end_pt_) ) 4001)
           )
           (progn 
             ;cal part
              (setq fullsize_length (* (fix (/ (distance (car ss_pre_filter_set_xx_obj_start_end_pt_) (cadr ss_pre_filter_set_xx_obj_start_end_pt_) ) 4000)) 4000))
              (setq fragment_length (- (distance (car ss_pre_filter_set_xx_obj_start_end_pt_) (cadr ss_pre_filter_set_xx_obj_start_end_pt_) )  fullsize_length))
             ;
             (TA:vla-insertblock 
               "000 - DYNAMIC_COMBINE+VIEW_ASSCESSORIES_FAMELINE_GALV.BRACKET_FITTING_U-PROFILE_CC-01-4_COMBINE_VIEW"
               ss_pre_filter_set_xx_obj_startpt_
               1
               ss_pre_filter_set_xx_obj_angle
             )
             ;new_blk_entlast object
              (setq c0112_ename (entlast))
              (setq c0112_obj_ (vlax-ename->vla-object c0112_ename))
              (LM:setdynpropvalue c0112_obj_ "view" "2_top_view")
              (LM:setdynpropvalue c0112_obj_ "array_length" fullsize_length)
              (LM:setdynpropvalue c0112_obj_ "fragment_length" fragment_length)
              
             ;
             (princ "_case_1")
           )
          )
          ( ;_case_2
           (and 
             ()
             ()
           )
           (progn 
             ()
             (princ "_case_2")
           )
          )
          ( ;_case_3
           (and 
             ()
             ()
           )
           (progn 
             ()
             (princ "_case_3")
           )
          )
          ( ;_case_4
           (and 
             ()
             ()
           )
           (progn 
             ()
             (princ "_case_4")
           )
          )
        )
        
        (setq ss_pre_filter_set_xx_i (+ ss_pre_filter_set_xx_i 1))
      )
      (command "pselect"  ss_pre_filter_set_xx_ "" )
    ;
  )
  (defun c:PPLINE_300HK_grid_to_cc012_g012 ()
    ;selection_set_for_fillter_blk_name
      (if  ;pre_select_ssget_or_post_select_ssget
        (=
          (setq ss_pre_filter_set_xx_ (ssget "i"
                                            (list
                                              (cons 0 "insert") ;type of object
                                              ; (cons 8 "000 - GRID")   ;kind of layer
                                              ; (cons 2 "000-GRID_LINE_DYN")       ;kind of nameblock
                                              ; (cons 62 6)           ;kind of color call sign with color code index
                                            )
                                      )
          )
          nil
        )
        (progn
          (setq ss_pre_filter_set_xx_ (ssget
                                            (list
                                              (cons 0 "insert") ;type of object
                                              ; (cons 8 "000 - GRID")   ;kind of layer
                                              ; (cons 2 "000-GRID_LINE_DYN")       ;kind of nameblock
                                              ; (cons 62 6)           ;kind of color call sign with color code index
                                            )
                                      )
          )
        )
        (sslength ss_pre_filter_set_xx_)
      )
    ;
    (setq ss_pre_filter_set_xx_ (TA:EF_Filter_ss_set_ ss_pre_filter_set_xx_ "000-GRID_LINE_DYN_V2-FOR-CC012"))
    (_StartUndo doc)
    (TA:interface_text_ T)
    ;preloop_and_while
      (setq ss_pre_filter_set_xx_i 0)
      (setq new_ss_c012_ (ssadd)) 
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_rotation_ (rad-to-deg (vla-get-rotation  ss_pre_filter_set_xx_obj_)))
        
        
        (setq ss_pre_filter_set_xx_obj_dyn_inner_length (* 25 (atoi (rtos (/ (LM:getdynpropvalue ss_pre_filter_set_xx_obj_ "H") 25) 2 1)))) ;normal fix
        ; (setq ss_pre_filter_set_xx_obj_dyn_inner_length (- (LM:getdynpropvalue ss_pre_filter_set_xx_obj_ "H") 17)) ;unfix specific target
        (setq ss_pre_filter_set_xx_obj_dyn_offset_length (* 25 (LM:round (atoi (rtos (/ (LM:getdynpropvalue ss_pre_filter_set_xx_obj_ "OFFSET") 25) 2 1)) )))
        (setq ss_pre_filter_set_xx_obj_dyn_all_length (+ 
                                                        ss_pre_filter_set_xx_obj_dyn_inner_length
                                                        ss_pre_filter_set_xx_obj_dyn_offset_length
                                                      )
        )
        (setq ss_pre_filter_set_xx_obj_dyn_time_length (* 4000 (fix (/ ss_pre_filter_set_xx_obj_dyn_all_length 4000))))
        (setq ss_pre_filter_set_xx_obj_dyn_fragment_length (- ss_pre_filter_set_xx_obj_dyn_all_length ss_pre_filter_set_xx_obj_dyn_time_length))
        (setq ss_pre_filter_set_xx_obj_ins_ (vlax-safearray->list (vlax-variant-value (vla-get-insertionpoint ss_pre_filter_set_xx_obj_))))
        (cond 
          ( ;_case_1
           (and 
             (>= ss_pre_filter_set_xx_obj_dyn_all_length 4000)
           )
           (progn 
              (TA:vla-insertblock
                "000 - DYNAMIC_COMBINE+VIEW_ASSCESSORIES_FAMELINE_GALV.BRACKET_FITTING_U-PROFILE_CC-01-4_COMBINE_VIEW"
                ss_pre_filter_set_xx_obj_ins_
                1
                (deg-to-rad (+ ss_pre_filter_set_xx_obj_rotation_ 180))
              )
              ;new_blk_entlast object
                (setq new_ename (entlast))
                (setq new_obj_ (vlax-ename->vla-object new_ename))

                (TA:move_polar_insertionpoint new_obj_ "Y" ss_pre_filter_set_xx_obj_dyn_offset_length)
                (LM:setdynpropvalue new_obj_ "view" "2_top_view")
                (LM:setdynpropvalue new_obj_ "array_length" ss_pre_filter_set_xx_obj_dyn_time_length)
                (LM:setdynpropvalue new_obj_ "fragment_length" ss_pre_filter_set_xx_obj_dyn_fragment_length)
                (LM:setdynpropvalue new_obj_ "fragment_start" 4000)
             
                
              ;
              (princ "_case_1")
            )
          )
          ( ;_case_2
            (and 
              (< ss_pre_filter_set_xx_obj_dyn_all_length 4000)
            )
            (progn 
              (TA:vla-insertblock
                "000 - DYNAMIC_COMBINE+VIEW_ASSCESSORIES_FAMELINE_GALV.BRACKET_FITTING_U-PROFILE_CC-01-4_COMBINE_VIEW"
                ss_pre_filter_set_xx_obj_ins_
                1
                (deg-to-rad (+ ss_pre_filter_set_xx_obj_rotation_ 180))
              )
              ;new_blk_entlast object
                (setq new_ename (entlast))
                (setq new_obj_ (vlax-ename->vla-object new_ename))
                (TA:move_polar_insertionpoint new_obj_ "Y" ss_pre_filter_set_xx_obj_dyn_offset_length)
                (LM:setdynpropvalue new_obj_ "view" "7_dynamic_length_view")
                (LM:setdynpropvalue new_obj_ "fragment_start" ss_pre_filter_set_xx_obj_dyn_all_length)
              ;
              (princ "_case_2")
            )
          )
          ( ;_case_3
           (and 
             ()
             ()
           )
           (progn 
             ()
             (princ "_case_3")
           )
          )
          ( ;_case_4
           (and 
             ()
             ()
           )
           (progn 
             ()
             (princ "_case_4")
           )
          )
        )
        (setq new_ss_c012_ (ssadd new_ename new_ss_c012_ ))
        (TA:textscr_process_V2 "insert" ss_pre_filter_set_xx_i ss_pre_filter_set_xx_ )
        (setq ss_pre_filter_set_xx_i (+ ss_pre_filter_set_xx_i 1))
      )
      (TA:interface_text_ nil)
      (command "pselect"  ss_pre_filter_set_xx_ "" )
      (setq ERR_
        (vl-catch-all-apply
          (function
            (lambda ()
              ;enter for delete mtext 
                (if (and 
                      (= (setq detectloop (getstring "enter to change length Object")) "")
                    )
                  (progn
                    (command "pselect"  new_ss_c012_ "" )
                  )
                )
              ;
            )
          )
        )
      )
      (sslength new_ss_c012_)
    ;
    (_EndUndo doc)
  )
  (defun c:call_lasted_ssset_cc01_lscc01 ()
    (command "pselect"  lasted_cc01_ssset "" )
  )
  (defun TA:PPLINE_300HK_HR-02B_assembly_coordinate (obj_)
    (setq offset_tor_ 25)
    ; (setq ename_ (car (entsel "specify Object")))
    ; (setq obj_ (vlax-ename->vla-object ename_))
    (setq obj_ro_ (vla-get-rotation obj_))
    (setq obj_ins_ (vlax-safearray->list (vlax-variant-value (vla-get-insertionpoint obj_))))
    (cond
    ( (and 
        (= (LM:effectivename obj_) "000 - DYNAMIC_COMBINE+VIEW_ASSCESSORIES_FAMELINE_GALV.BRACKET_FITTING_Z-PROFILE_HR-02B_COMBINE_VIEW")
        (= (LM:getdynpropvalue obj_ "view") "7_dynamic_length_view")
      )
      (progn
        (setq dynlist_ (list 
                        (LM:getdynpropvalue obj_ "fragment_middle_L")
                        (LM:getdynpropvalue obj_ "fragment_middle_R")
                       )
        )
        (setq HR_insset_ (list 
                           (setq base_pt_ (polar obj_ins_ (deg-to-rad (TA:ModifyRotation (rad-to-deg obj_ro_) 270 ) ) 10 ) )
                           (setq pt_left_ (polar base_pt_ (deg-to-rad (TA:ModifyRotation (rad-to-deg obj_ro_) 180 ) ) (+ (car dynlist_) offset_tor_) ) )
                           (setq pt_right_ (polar base_pt_ (deg-to-rad (TA:ModifyRotation (rad-to-deg obj_ro_) 0 ) ) (+ (cadr dynlist_) offset_tor_) ) )
                         )
        )
      )
    )
    ( (and 
        (= (LM:effectivename obj_) "000 - DYNAMIC_COMBINE+VIEW_ASSCESSORIES_FAMELINE_GALV.BRACKET_FITTING_Z-PROFILE_HR-02B_COMBINE_VIEW")
        (= (LM:getdynpropvalue obj_ "view") "2_top_view")
      )
      (progn
        (setq dynlist_ (list 
                        (LM:getdynpropvalue obj_ "array_length")
                        (LM:getdynpropvalue obj_ "fragment_left")
                        (LM:getdynpropvalue obj_ "fragment_right")
                       )
        )
        (setq HR_insset_ (list 
                           (setq base_pt_ (polar obj_ins_ (deg-to-rad (TA:ModifyRotation (rad-to-deg obj_ro_) 270 ) ) 10 ) )
                           (setq pt_left_ (polar base_pt_ (deg-to-rad (TA:ModifyRotation (rad-to-deg obj_ro_) 180 ) ) (+ (+ (/ (car dynlist_) 2) (cadr dynlist_)) offset_tor_) ) )
                           (setq pt_right_ (polar base_pt_ (deg-to-rad (TA:ModifyRotation (rad-to-deg obj_ro_) 0 ) ) (+ (+ (/ (car dynlist_) 2) (caddr dynlist_)) offset_tor_) ) )
                          ;  (command "point" pt_right_)
                          ;  (command "point" pt_left_)
                         )
        )
      )
    )
    )
  )
  (defun TA:PPLINE_300HK_HR-02A_assembly_coordinate (obj_)
    (setq offset_tor_ 25)
    ; (setq ename_ (car (entsel "specify Object")))
    ; (setq obj_ (vlax-ename->vla-object ename_))
    (setq obj_ro_ (vla-get-rotation obj_))
    (setq obj_ins_ (vlax-safearray->list (vlax-variant-value (vla-get-insertionpoint obj_))))
    (cond
    ( (and 
        (= (LM:effectivename obj_ ) "000 - DYNAMIC_COMBINE+VIEW_ASSCESSORIES_FAMELINE_GALV.BRACKET_FITTING_Z-PROFILE_HR-02AA_COMBINE_VIEW")
        (= (LM:getdynpropvalue obj_ "view") "7_dynamic_length_view")
      )
      (progn
        (setq dynlist_ (list 
                        (LM:getdynpropvalue obj_ "fragment_middle")
                        
                      )
        )
        (setq HR_insset_ (list 
                          (setq base_pt_ (polar obj_ins_ (deg-to-rad (TA:ModifyRotation (rad-to-deg obj_ro_) 90 ) ) 10 ) )
                          (setq pt_left_ (polar base_pt_ (deg-to-rad (TA:ModifyRotation (rad-to-deg obj_ro_) 180 ) ) (+ (/ (car dynlist_) 2) offset_tor_) ) )
                          (setq pt_right_ (polar base_pt_ (deg-to-rad (TA:ModifyRotation (rad-to-deg obj_ro_) 0 ) ) (+ (/ (car dynlist_) 2) offset_tor_ ) ) )
                        )
        )
      )
    )
    ( (and 
        (= (LM:effectivename obj_ ) "000 - DYNAMIC_COMBINE+VIEW_ASSCESSORIES_FAMELINE_GALV.BRACKET_FITTING_Z-PROFILE_HR-02AA_COMBINE_VIEW")
        (= (LM:getdynpropvalue obj_ "view") "2_top_view")
      )
      (progn
        (setq dynlist_ (list 
                        (LM:getdynpropvalue obj_ "array_length")
                        (LM:getdynpropvalue obj_ "fragment_left")
                        (LM:getdynpropvalue obj_ "fragment_right")
                      )
        )
        (setq HR_insset_ (list 
                          (setq base_pt_ (polar obj_ins_ (deg-to-rad (TA:ModifyRotation (rad-to-deg obj_ro_) 90 ) ) 10 ) )
                          (setq pt_left_ (polar base_pt_ (deg-to-rad (TA:ModifyRotation (rad-to-deg obj_ro_) 180 ) ) (+ (+ (/ (car dynlist_) 2) (cadr dynlist_)) offset_tor_) ) )
                          (setq pt_right_ (polar base_pt_ (deg-to-rad (TA:ModifyRotation (rad-to-deg obj_ro_) 0 ) ) (+ (/ (car dynlist_) 2) (caddr dynlist_) offset_tor_ ) ) )
                          ; (command "point" base_pt_)
                        )
        )
      )
    )
    )
  )
  (defun TA:PPLINE_300HK_HR-09B_assembly_coordinate (obj_)
    (setq offset_tor_ 25)
    ; (setq ename_ (car (entsel "specify Object")))
    ; (setq obj_ (vlax-ename->vla-object ename_))
    (setq obj_ro_ (vla-get-rotation obj_))
    (setq obj_ins_ (vlax-safearray->list (vlax-variant-value (vla-get-insertionpoint obj_))))
    (cond
    ( (and 
        (or 
          (= (LM:effectivename obj_ ) "000 - ASSCESSORIES_FAMELINE_GALV.BRACKET_FITTING_Z-PROFILE_HR-09B_TOP_VIEW")
          (= (LM:effectivename obj_ ) "000 - ASSCESSORIES_FAMELINE_GALV.BRACKET_FITTING_Z-PROFILE_HR-09C_TOP_VIEW")
          (= (LM:effectivename obj_ ) "000 - ASSCESSORIES_FAMELINE_GALV.BRACKET_FITTING_Z-PROFILE_HR-09D_TOP_VIEW")
        )
        (and 
          (/= (LM:vl-getattributevalue obj_ "GALV.OVL-LENGTH_") nil)
        )
      )
      (progn
        (setq dynlist_ (list 
                        (atof (LM:vl-getattributevalue obj_ "GALV.OVL-LENGTH_"))
                      )
        )
        (setq HR_insset_ (list 
                          (setq base_pt_ (polar obj_ins_ (deg-to-rad (TA:ModifyRotation (rad-to-deg obj_ro_) 270 ) ) 10 ) )
                          (setq pt_left_ (polar base_pt_ (deg-to-rad (TA:ModifyRotation (rad-to-deg obj_ro_) 180 ) ) (+ (/ (car dynlist_) 2) offset_tor_) ) )
                          (setq pt_right_ (polar base_pt_ (deg-to-rad (TA:ModifyRotation (rad-to-deg obj_ro_) 0 ) ) (+ (/ (car dynlist_) 2) offset_tor_) ) )
                        )
        )
      )
    )
    )
  )
  (defun c:c012dim ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq new_ss_cc014 (TA:EF_Filter_ss_set_ ss_pre_filter_set_xx_ "000 - DYNAMIC_COMBINE+VIEW_ASSCESSORIES_FAMELINE_GALV.BRACKET_FITTING_U-PROFILE_CC-01-4_COMBINE_VIEW"))
    
    
  )

  (defun c:PPLINE_300HK_CC-01_intersect_HR_CCinHR ()
      ;presetting_
        (setq intersection_mode_ 3)
        (if (= intersection_mode_ 1) (progn (setq inter_blk_name_ "000 - TRANSFER" ) ) )
        (if (= intersection_mode_ 2) (progn (setq inter_blk_name_ "000 - CIRCLE" ) ) )
        (if (= intersection_mode_ 3) (progn (setq inter_blk_name_ "000 - FASTERN SYMBOL" ) ) )
      
      ;
      (_StartUndo doc)
      ;selection_set_for_fillter_blk_name
        (if  ;pre_select_ssget_or_post_select_ssget
          (=
            (setq ss_pre_filter_set_xx_ (ssget "i"
                                              (list
                                                (cons 0 "INSERT") ;type of object
                                                (cons 8 "000 - GRID,001 - ASCESSORIES,001 - ASCESSORIES_FOR_C09")   ;kind of layer
                                                ; (cons 2 "000-GRID_LINE_DYN")       ;kind of nameblock
                                                ; (cons 62 256)           ;kind of color call sign with color code index
                                              )
                                        )
            )
            nil
          )
          (progn
            (setq ss_pre_filter_set_xx_ (ssget
                                              (list
                                                (cons 0 "INSERT") ;type of object
                                                (cons 8 "000 - GRID,001 - ASCESSORIES,001 - ASCESSORIES_FOR_C09")   ;kind of layer
                                                ; (cons 2 "000-GRID_LINE_DYN")       ;kind of nameblock
                                                ; (cons 62 256)           ;kind of color call sign with color code index
                                              )
                                        )
            )
          )
          (sslength ss_pre_filter_set_xx_)
        )
        (setq ss_pre_filter_set_xx_ (TA:EF_Filter_ss_set_ ss_pre_filter_set_xx_ "000 - DYNAMIC_COMBINE+VIEW_ASSCESSORIES_FAMELINE_GALV.BRACKET_FITTING_U-PROFILE_CC-01-4_COMBINE_VIEW"))
      ;
      ;preloop_and_while
        (setvar "osmode" 0)
        (setq ss_pre_filter_set_xx_i 0)
        (setq cc-01_inters_list_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_rotation_ (rad-to-deg (vla-get-rotation ss_pre_filter_set_xx_obj_)))
          (vla-put-color ss_pre_filter_set_xx_obj_ 1)
          (setq cc-01_inters_list_ 
            (cons 
              (list
                ss_pre_filter_set_xx_obj_ins_
                (polar ss_pre_filter_set_xx_obj_ins_  
                      (vla-get-rotation ss_pre_filter_set_xx_obj_) 
                      (if (= (LM:getdynpropvalue ss_pre_filter_set_xx_obj_ "view" ) "7_dynamic_length_view")
                        (progn
                          (LM:getdynpropvalue ss_pre_filter_set_xx_obj_ "fragment_start" )
                        )
                        (+
                          (LM:getdynpropvalue ss_pre_filter_set_xx_obj_ "array_length" )
                          (LM:getdynpropvalue ss_pre_filter_set_xx_obj_ "fragment_length" )
                        )
                      )
                
                )
              )
              cc-01_inters_list_
            )
          )  
          
          (setq ss_pre_filter_set_xx_i (+ ss_pre_filter_set_xx_i 1))
        )
      ;
      (setq Er-msg_ nil)
      (setq new_tranfer_ss_ (ssadd))
      
      (while
        (and (/= (vl-catch-all-error-p Er-msg_) T) )
        (setq Er-msg_ (vl-catch-all-apply (function (lambda () 
                                                      ; (setq ss_line_ename_ (ssname  (ssget  (list (cons 0 "insert")  (cons 8 "001 - ASCESSORIES") (cons 62 256)) ) 0) ) 
                                                      (if  ;pre_select_ssget_or_post_select_ssget
                                                        (=
                                                          (setq ss_pre_filter_set_xx_ (ssget 
                                                                                            (list
                                                                                              (cons 0 "INSERT") ;type of object
                                                                                              (cons 8 "000 - GRID,001 - ASCESSORIES,001 - ASCESSORIES_FOR_C09")   ;kind of layer
                                                                                              ; (cons 2 "000-GRID_LINE_DYN")       ;kind of nameblock
                                                                                              (cons 62 256)           ;kind of color call sign with color code index
                                                                                            )
                                                                                      )
                                                          )
                                                          nil
                                                        )
                                                        (progn
                                                          (setq ss_pre_filter_set_xx_ (ssget
                                                                                            (list
                                                                                              (cons 0 "INSERT") ;type of object
                                                                                              (cons 8 "000 - GRID,001 - ASCESSORIES,001 - ASCESSORIES_FOR_C09")   ;kind of layer
                                                                                              ; (cons 2 "000-GRID_LINE_DYN")       ;kind of nameblock
                                                                                              (cons 62 256)           ;kind of color call sign with color code index
                                                                                            )
                                                                                      )
                                                          )
                                                        )
                                                        (sslength ss_pre_filter_set_xx_)
                                                      )
                                                      (setq ss_pre_filter_set_xx_ (TA:EF_Filter_ss_set_v2_ 
                                                                                   ss_pre_filter_set_xx_ 
                                                                                   (list 
                                                                                     "000 - DYNAMIC_COMBINE+VIEW_ASSCESSORIES_FAMELINE_GALV.BRACKET_FITTING_Z-PROFILE_HR-02B_COMBINE_VIEW"
                                                                                     "000 - DYNAMIC_COMBINE+VIEW_ASSCESSORIES_FAMELINE_GALV.BRACKET_FITTING_Z-PROFILE_HR-02AA_COMBINE_VIEW"
                                                                                     "000 - ASSCESSORIES_FAMELINE_GALV.BRACKET_FITTING_Z-PROFILE_HR-09B_TOP_VIEW"
                                                                                   )
                                                                                 )
                                                      )
                                                   ) 
                                          ) 
                        ) 
        )
        (setq ss_pre_filter_set_xx_i 0)
        (while (and
                  (/= (vl-catch-all-error-p Er-msg_) T)
                  (= (type ss_pre_filter_set_xx_) 'PICKSET)
                  (/= (sslength ss_pre_filter_set_xx_) 0)
                  (< ss_pre_filter_set_xx_i (sslength ss_pre_filter_set_xx_) )
               )
          (setq ss_line_ename_ (ssname ss_pre_filter_set_xx_ ss_pre_filter_set_xx_i))
          (if (and 
                (/= (vl-catch-all-error-p Er-msg_) T)
                (= (vla-get-objectname (vlax-ename->vla-object ss_line_ename_)) "AcDbBlockReference")
              )

            (progn
              (TA:interface_text_ T)
              (setq ss_line_obj_ (vlax-ename->vla-object ss_line_ename_))
              ; (vla-put-color ss_line_obj_ 1)
              (cond
                (;_case_1
                  (and
                      (= (LM:effectivename ss_line_obj_) "000 - DYNAMIC_COMBINE+VIEW_ASSCESSORIES_FAMELINE_GALV.BRACKET_FITTING_Z-PROFILE_HR-02AA_COMBINE_VIEW")
                  )
                  (progn
                    (setq coord_set_ (TA:PPLINE_300HK_HR-02A_assembly_coordinate ss_line_obj_))
                    (princ "_case_1")
                  )
                )
                (;_case_2
                  (and
                      (= (LM:effectivename ss_line_obj_) "000 - DYNAMIC_COMBINE+VIEW_ASSCESSORIES_FAMELINE_GALV.BRACKET_FITTING_Z-PROFILE_HR-02B_COMBINE_VIEW")
                  )
                  (progn
                    (setq coord_set_ (TA:PPLINE_300HK_HR-02B_assembly_coordinate ss_line_obj_))
                    (princ "_case_2")
                  )
                )
                (;_case_3
                  (and
                      (or 
                        (= (LM:effectivename ss_line_obj_ ) "000 - ASSCESSORIES_FAMELINE_GALV.BRACKET_FITTING_Z-PROFILE_HR-09B_TOP_VIEW")
                        (= (LM:effectivename ss_line_obj_ ) "000 - ASSCESSORIES_FAMELINE_GALV.BRACKET_FITTING_Z-PROFILE_HR-09C_TOP_VIEW")
                        (= (LM:effectivename ss_line_obj_ ) "000 - ASSCESSORIES_FAMELINE_GALV.BRACKET_FITTING_Z-PROFILE_HR-09D_TOP_VIEW")
                      )
                  )
                  (progn
                    (setq coord_set_ (TA:PPLINE_300HK_HR-09B_assembly_coordinate ss_line_obj_))
                    (princ "_case_3")
                  )
                )
              )
              (setq ss_line_obj_start_end_pt_ (list
                                              (setq ss_line_obj_startpt_ (cadr coord_set_) )
                                              (setq ss_line_obj_endpt_ (caddr coord_set_) )
                                              ; (command "point" ss_line_obj_startpt_)
                                              ; (command "point" ss_line_obj_endpt_)
                                              
                                            )
              )
            )
            
          )
          ;preloop_and_while
            (setq cc-01_inters_list_i 0)
            (TA:interface_text_ T)
            (while (and
                    (/= (vl-catch-all-error-p Er-msg_) T)
                    (< cc-01_inters_list_i (length cc-01_inters_list_) )
                  )
              (setq cc-01_inters_list_val_1 (car (nth  cc-01_inters_list_i cc-01_inters_list_)))
              (setq cc-01_inters_list_val_2 (cadr (nth  cc-01_inters_list_i cc-01_inters_list_))) 
              (if (/= (inters ss_line_obj_startpt_ ss_line_obj_endpt_ cc-01_inters_list_val_1 cc-01_inters_list_val_2 ) nil)
                (progn
                  (cond 
                    ( ;intersection_mode_case_0
                      (and 
                        (= intersection_mode_ 0)
                      )
                      (progn 
                        (command "circle" 
                                  (if (= (getvar "worlducs") 0) 
                                    (progn 
                                      (trans (inters ss_line_obj_startpt_ ss_line_obj_endpt_ cc-01_inters_list_val_1 cc-01_inters_list_val_2 ) 0 1 )
                                    )
                                    (inters ss_line_obj_startpt_ ss_line_obj_endpt_ cc-01_inters_list_val_1 cc-01_inters_list_val_2 )
                                  )
                                  120
                        )
                        
                        ;new_blk_entlast object
                          (setq new_ename (entlast))
                          (setq new_obj_ (vlax-ename->vla-object new_ename))
                          (vla-put-color new_obj_ 256)
                          (vla-put-layer new_obj_ "001 - ASCESSORIES_HANGING")
                          ; (TA:move_axis_insertionpoint new_obj_ "x" -17)
                          ; (LM:setdynpropvalue new_obj_  "view" "2_top_view")
                        ;
                        (princ "intersection_mode_case_1")
                      )
                    )
                    ( ;intersection_mode_case_1
                      (and 
                        (= intersection_mode_ 1)
                      )
                      (progn 
                        (TA:vla-insertblock 
                          inter_blk_name_
                          (if (= (getvar "worlducs") 1) 
                            (progn 
                              (trans (inters ss_line_obj_startpt_ ss_line_obj_endpt_ cc-01_inters_list_val_1 cc-01_inters_list_val_2 ) 0 1 )
                            )
                            (inters ss_line_obj_startpt_ ss_line_obj_endpt_ cc-01_inters_list_val_1 cc-01_inters_list_val_2 )
                          )
                          1
                          (angle cc-01_inters_list_val_1 cc-01_inters_list_val_2)
                        )
                        ;new_blk_entlast object
                          (setq new_ename (entlast))
                          (setq new_obj_ (vlax-ename->vla-object new_ename))
                          (vla-put-color new_obj_ 3)
                          (TA:move_axis_insertionpoint new_obj_ "y" 50)
                          ; (LM:setdynpropvalue new_obj_  "view" "2_top_view")
                          (setq new_tranfer_ss_ (ssadd new_ename new_tranfer_ss_))
                        ; 

                        (princ "intersection_mode_case_1")
                      )
                    )
                    ( ;intersection_mode_case_2
                      (and 
                        (= intersection_mode_ 2)
                      )
                      (progn 
                        (TA:vla-insertblock 
                          inter_blk_name_
                          (if (= (getvar "worlducs") 1) 
                            (progn 
                              (trans (inters ss_line_obj_startpt_ ss_line_obj_endpt_ cc-01_inters_list_val_1 cc-01_inters_list_val_2 ) 0 1 )
                            )
                            (inters ss_line_obj_startpt_ ss_line_obj_endpt_ cc-01_inters_list_val_1 cc-01_inters_list_val_2 )
                          )
                          1
                          (angle cc-01_inters_list_val_1 cc-01_inters_list_val_2)
                        )
                        ;new_blk_entlast object
                          (setq new_ename (entlast))
                          (setq new_obj_ (vlax-ename->vla-object new_ename))
                          (vla-put-color new_obj_ 3)
                          (TA:move_axis_insertionpoint new_obj_ "y" 50)
                          ; (LM:setdynpropvalue new_obj_  "view" "2_top_view")
                          (setq new_tranfer_ss_ (ssadd new_ename new_tranfer_ss_))
                        ; 

                        (princ "intersection_mode_case_2")
                      )
                    )
                    ( ;intersection_mode_case_3
                      (and 
                        (= intersection_mode_ 3)
                      )
                      (progn 
                        (TA:vla-insertblock 
                          inter_blk_name_
                          (if (= (getvar "worlducs") 1) 
                            (progn 
                              (trans (inters ss_line_obj_startpt_ ss_line_obj_endpt_ cc-01_inters_list_val_1 cc-01_inters_list_val_2 ) 0 1 )
                            )
                            (inters ss_line_obj_startpt_ ss_line_obj_endpt_ cc-01_inters_list_val_1 cc-01_inters_list_val_2 ) 
                          )
                          1
                          (angle cc-01_inters_list_val_1 cc-01_inters_list_val_2)
                        )
                        ;new_blk_entlast object
                          (setq new_ename (entlast))
                          (setq new_obj_ (vlax-ename->vla-object new_ename))
                          (vla-put-color new_obj_ 3)
                          (vla-put-layer new_obj_ "000_FASTERN_ACESSORIES_MAIN_COLOR_1")
                          ; (TA:move_axis_insertionpoint new_obj_ "y" 50)
                          ; (LM:setdynpropvalue new_obj_  "view" "2_top_view")
                          (setq new_tranfer_ss_ (ssadd new_ename new_tranfer_ss_))
                        ; 

                        (princ "intersection_mode_case_3")
                      )
                    )
                  )
                )
              )

              (TA:textscr_process "insertion process " cc-01_inters_list_i cc-01_inters_list_)
          
              (setq cc-01_inters_list_i (+ cc-01_inters_list_i 1))
            )
          ;
          (setq ss_pre_filter_set_xx_i (+ ss_pre_filter_set_xx_i 1))
        )
      )
      (command "pselect"  new_tranfer_ss_ "" )
      ; (vla-regen (vla-get-ActiveDocument (vlax-get-acad-object)) acAllViewports)
      (setvar "osmode" 1215)
      (_endUndo doc)
  )
  ;
  (defun c:inshang1 ()
    ;presetting
      (setq hanging_dist_var_ 1300)
      (setq hanging_offset_start_ 75)
      (setq hanging_offset_end_ 150)
      (setq hanging_fragment_offset_end_ 75)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "000 - DYNAMIC_COMBINE+VIEW_ASSCESSORIES_FAMELINE_GALV.BRACKET_FITTING_U-PROFILE_CC-01_COMBINE_VIEW"))
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_ins_rotation_ (vla-get-rotation ss_pre_filter_set_xx_obj_))
        (cond
          (;_case_0
            (and
                (= (LM:getdynpropvalue ss_pre_filter_set_xx_obj_ "view" ) "2_top_view_2-way")
                (/= ss_pre_filter_set_xx_obj_ins_rotation_ 0)
                (/= (rad-to-deg ss_pre_filter_set_xx_obj_ins_rotation_) 180)
            )
            (progn
              (setq array_length_full (LM:getdynpropvalue ss_pre_filter_set_xx_obj_ "array_length"))
              (setq array_length_half_ (/ (LM:getdynpropvalue ss_pre_filter_set_xx_obj_ "array_length") 2))
              (setq fragment_left (* (fix (/ (LM:getdynpropvalue ss_pre_filter_set_xx_obj_ "fragment_left") 25)) 25))
              (setq fragment_right (* (fix (/ (LM:getdynpropvalue ss_pre_filter_set_xx_obj_ "fragment_right") 25)) 25))
              (setq total_full_length_ (+ fragment_right (+ fragment_left (+ array_length_full ))))
              (setq start_pt (list 
                                (car ss_pre_filter_set_xx_obj_ins_)
                                (- (+ (cadr ss_pre_filter_set_xx_obj_ins_) (+ fragment_left array_length_half_))  hanging_offset_start_) 
                                (caddr ss_pre_filter_set_xx_obj_ins_)
                            )
              )
              (setq last_pt (list 
                                (car ss_pre_filter_set_xx_obj_ins_)
                                (- (+ (cadr ss_pre_filter_set_xx_obj_ins_) (+ fragment_left array_length_half_)) total_full_length_)
                                (caddr ss_pre_filter_set_xx_obj_ins_)
                            )
              )
              (setq hanging_dist_time_ (fix (/ total_full_length_ hanging_dist_var_))) ;finding distance time for insert hanging
              ;preloop_and_while
                (setq hanging_dist_time_i 0)
                (while (< hanging_dist_time_i (+ 1 hanging_dist_time_))
                  (setq new_start_pt (list 
                                      (car ss_pre_filter_set_xx_obj_ins_)
                                      (- (+ (- (cadr ss_pre_filter_set_xx_obj_ins_) hanging_offset_start_ ) (+ fragment_left array_length_half_)) (* hanging_dist_time_i hanging_dist_var_) )
                                      (caddr ss_pre_filter_set_xx_obj_ins_)
                                    )
                  )
                  (TA:vla-insertblock ;insert loop * dist. time (hanging_dist_time_i by hanging_dist_time_i)
                    "000 - DYNAMIC_LENGTH+COMBINE+VIEW_ASSCESSORIES_FAMELINE_BK-08_HANGING_SYSTEM_300HK_COMBINE_SET"
                    (if (= (getvar "worlducs") 0)(progn (trans new_start_pt 1 1)) new_start_pt )
                    1
                    (deg-to-rad 0)
                  )
                  ;new_blk_entlast object
                    (setq newhang_ename (entlast))
                    (setq newhang_obj_ (vlax-ename->vla-object newhang_ename))
                    (setq newhang_obj_ins_ (vlax-safearray->list (vlax-variant-value (vla-get-insertionpoint newhang_obj_))))
                    (vla-put-layer newhang_obj_ "001 - ASCESSORIES")
                    (vla-put-color newhang_obj_ 256)
                    (vla-put-linetype newhang_obj_ "byblock")
                    (LM:setdynpropvalue newhang_obj_ "view" "2_top_view")
                  ;
                  
                  (setq hanging_dist_time_i (+ hanging_dist_time_i 1))
                )
                (if (> (distance new_start_pt last_pt ) 150)
                  (progn
                    (TA:vla-insertblock ;insert loop * dist. time last position of CC01
                      "000 - DYNAMIC_LENGTH+COMBINE+VIEW_ASSCESSORIES_FAMELINE_BK-08_HANGING_SYSTEM_300HK_COMBINE_SET"
                      (if (= (getvar "worlducs") 0)(progn (trans last_pt 1 1)) last_pt )
                      1
                      (deg-to-rad 0)
                    )
                    ;new_blk_entlast object
                      (setq newhang_ename (entlast))
                      (setq newhang_obj_ (vlax-ename->vla-object newhang_ename))
                      (setq newhang_obj_ins_ (vlax-safearray->list (vlax-variant-value (vla-get-insertionpoint newhang_obj_))))
                      (TA:move_axis_insertionpoint newhang_obj_ "y" hanging_offset_end_)
                      (vla-put-layer newhang_obj_ "001 - ASCESSORIES")
                      (vla-put-color newhang_obj_ 256)
                      (vla-put-linetype newhang_obj_ "byblock")
                      (LM:setdynpropvalue newhang_obj_ "view" "2_top_view")
                    ;
                  )
                  ; (TA:move_axis_insertionpoint newhang_obj_ "y" hanging_offset_end_)
                  ; (TA:move_axis_insertionpoint newhang_obj_ "y" 0)
                )
              ;
              (princ "_case_1")
            )
          )
          (;_case_1
            (and
                (= (LM:getdynpropvalue ss_pre_filter_set_xx_obj_ "view" ) "2_top_view")
                (/= ss_pre_filter_set_xx_obj_ins_rotation_ 0)
                (/= (rad-to-deg ss_pre_filter_set_xx_obj_ins_rotation_) 180)
            )
            (progn
              (setq array_length_full (LM:getdynpropvalue ss_pre_filter_set_xx_obj_ "array_length"))
              (setq array_length_half_ (/ (LM:getdynpropvalue ss_pre_filter_set_xx_obj_ "array_length") 2))
              (setq fragment_left (* (fix (/ (LM:getdynpropvalue ss_pre_filter_set_xx_obj_ "fragment_left") 25)) 25))
              (setq fragment_right (* (fix (/ (LM:getdynpropvalue ss_pre_filter_set_xx_obj_ "fragment_right") 25)) 25))
              (setq total_full_length_ (+ fragment_right (+ fragment_left (+ array_length_full ))))
              (setq start_pt (list 
                                (car ss_pre_filter_set_xx_obj_ins_)
                                (- (+ (cadr ss_pre_filter_set_xx_obj_ins_) (+ fragment_left array_length_half_))  hanging_offset_start_) 
                                (caddr ss_pre_filter_set_xx_obj_ins_)
                            )
              )
              (setq last_pt (list 
                                (car ss_pre_filter_set_xx_obj_ins_)
                                (- (+ (cadr ss_pre_filter_set_xx_obj_ins_) (+ fragment_left array_length_half_)) total_full_length_)
                                (caddr ss_pre_filter_set_xx_obj_ins_)
                            )
              )
              (setq hanging_dist_time_ (fix (/ total_full_length_ hanging_dist_var_))) ;finding distance time for insert hanging
              ;preloop_and_while
                (setq hanging_dist_time_i 0)
                (while (< hanging_dist_time_i (+ 1 hanging_dist_time_))
                  (setq new_start_pt (list 
                                      (car ss_pre_filter_set_xx_obj_ins_)
                                      (- (+ (- (cadr ss_pre_filter_set_xx_obj_ins_) hanging_offset_start_ ) (+ fragment_left array_length_half_)) (* hanging_dist_time_i hanging_dist_var_) )
                                      (caddr ss_pre_filter_set_xx_obj_ins_)
                                    )
                  )
                  (TA:vla-insertblock ;insert loop * dist. time (hanging_dist_time_i by hanging_dist_time_i)
                    "000 - DYNAMIC_LENGTH+COMBINE+VIEW_ASSCESSORIES_FAMELINE_BK-08_HANGING_SYSTEM_300HK_COMBINE_SET"
                    (if (= (getvar "worlducs") 0)(progn (trans new_start_pt 1 1)) new_start_pt )
                    1
                    (deg-to-rad 0)
                  )
                  ;new_blk_entlast object
                    (setq newhang_ename (entlast))
                    (setq newhang_obj_ (vlax-ename->vla-object newhang_ename))
                    (setq newhang_obj_ins_ (vlax-safearray->list (vlax-variant-value (vla-get-insertionpoint newhang_obj_))))
                    (vla-put-layer newhang_obj_ "001 - ASCESSORIES")
                    (vla-put-color newhang_obj_ 256)
                    (vla-put-linetype newhang_obj_ "byblock")
                    (LM:setdynpropvalue newhang_obj_ "view" "2_top_view")
                  ;
                  
                  (setq hanging_dist_time_i (+ hanging_dist_time_i 1))
                )
                (if (> (distance new_start_pt last_pt ) 150)
                  (progn
                    (TA:vla-insertblock ;insert loop * dist. time last position of CC01
                      "000 - DYNAMIC_LENGTH+COMBINE+VIEW_ASSCESSORIES_FAMELINE_BK-08_HANGING_SYSTEM_300HK_COMBINE_SET"
                      (if (= (getvar "worlducs") 0)(progn (trans last_pt 1 1)) last_pt )
                      1
                      (deg-to-rad 0)
                    )
                    ;new_blk_entlast object
                      (setq newhang_ename (entlast))
                      (setq newhang_obj_ (vlax-ename->vla-object newhang_ename))
                      (setq newhang_obj_ins_ (vlax-safearray->list (vlax-variant-value (vla-get-insertionpoint newhang_obj_))))
                      (TA:move_axis_insertionpoint newhang_obj_ "y" hanging_offset_end_)
                      (vla-put-layer newhang_obj_ "001 - ASCESSORIES")
                      (vla-put-color newhang_obj_ 256)
                      (vla-put-linetype newhang_obj_ "byblock")
                      (LM:setdynpropvalue newhang_obj_ "view" "2_top_view")
                    ;
                  )
                  ; (TA:move_axis_insertionpoint newhang_obj_ "y" hanging_offset_end_)
                  ; (TA:move_axis_insertionpoint newhang_obj_ "y" 0)
                )
              ;
              (princ "_case_1")
            )
          )
          (;_case_2
            (and
                (= (LM:getdynpropvalue ss_pre_filter_set_xx_obj_ "view" ) "7_dynamic_length_view")
                (/= ss_pre_filter_set_xx_obj_ins_rotation_ 0)
                ; (> (LM:getdynpropvalue ss_pre_filter_set_xx_obj_ "fragment_middle") 1500)
                ; (= (substr (rtos (/ (LM:getdynpropvalue ss_pre_filter_set_xx_obj_ "fragment_middle") 50 ) 2 2 ) (+ (vl-string-search "." (rtos (/ (LM:getdynpropvalue ss_pre_filter_set_xx_obj_ "fragment_middle" ) 50 ) 2 2 ) ) 2 ) 1 ) "0" )
            )
            (progn
              (setq hanging_dist_val_ (fix (/ (LM:getdynpropvalue ss_pre_filter_set_xx_obj_ "fragment_middle" ) hanging_dist_var_)))
              (setq hanging_dist_time_ (/ (fix (/ (LM:getdynpropvalue ss_pre_filter_set_xx_obj_ "fragment_middle" ) hanging_dist_var_)) 2))
              (setq fragment_middle_full_ (- (LM:getdynpropvalue ss_pre_filter_set_xx_obj_ "fragment_middle" ) 50))
              (setq fragment_middle_half_ (/ fragment_middle_full_ 2))
              (setq start_pt (list 
                              (+ (car ss_pre_filter_set_xx_obj_ins_) 0)
                              (+ (+ (cadr ss_pre_filter_set_xx_obj_ins_) fragment_middle_half_) 0)
                              (+ (caddr ss_pre_filter_set_xx_obj_ins_) 0)
                            )
              )
              (setq last_pt (list 
                              (+ (car ss_pre_filter_set_xx_obj_ins_) 0)
                              (- (+ (cadr ss_pre_filter_set_xx_obj_ins_) fragment_middle_half_) fragment_middle_full_)
                              (+ (caddr ss_pre_filter_set_xx_obj_ins_) 0)
                            )
              )
              ; (command "point" start_pt )
              ; (command "point" last_pt )
              (setq hanging_dist_time_ 2)
              (if (<= (distance start_pt last_pt ) 1451)
                (progn
                  (setq varies_dist_ (/ (distance start_pt last_pt ) 1))
                  (setq hanging_dist_time_ 2)
                )
                (setq varies_dist_ (/ (distance start_pt last_pt ) 2)
                      hanging_dist_time_ (+ hanging_dist_time_ 1)
                )
              )
              ;preloop_and_while
                (setq hanging_dist_time_i 0)
                (setq hanging_ssset ())
                (while (< hanging_dist_time_i hanging_dist_time_)
                  (setq new_start_pt (list 
                                      (car ss_pre_filter_set_xx_obj_ins_)
                                      (- (- (+ (cadr ss_pre_filter_set_xx_obj_ins_) fragment_middle_half_) hanging_offset_start_ ) (* hanging_dist_time_i varies_dist_) )
                                      (caddr ss_pre_filter_set_xx_obj_ins_)
                                    )
                  )
                  (TA:vla-insertblock 
                    "000 - DYNAMIC_LENGTH+COMBINE+VIEW_ASSCESSORIES_FAMELINE_BK-08_HANGING_SYSTEM_300HK_COMBINE_SET"
                    (if (= (getvar "worlducs") 0) (progn (trans new_start_pt 1 1)) new_start_pt )
                    1
                    (deg-to-rad 0)
                  )
                  ;new_blk_entlast object
                    (setq newhang_ename (entlast))
                    (setq newhang_obj_ (vlax-ename->vla-object newhang_ename))
                    (setq newhang_obj_ins_ (vlax-safearray->list (vlax-variant-value (vla-get-insertionpoint newhang_obj_))))
                    (vla-put-layer newhang_obj_ "001 - ASCESSORIES")
                    (vla-put-color newhang_obj_ 256)
                    (vla-put-linetype newhang_obj_ "byblock")
                    (LM:setdynpropvalue newhang_obj_ "view" "2_top_view")
                    (setq hanging_ssset (cons newhang_ename hanging_ssset))
                  ;
                  (if (/= hanging_dist_time_i 0)
                    (progn
                      (TA:move_axis_insertionpoint (vlax-ename->vla-object (setq newhang_ename (entlast))) "y" hanging_offset_start_)
                      (command "pselect"  (nth 0 hanging_ssset) "" )
                    )
                  )
                  (if (= hanging_dist_time_i 2)
                    (progn
                      (TA:move_axis_insertionpoint (vlax-ename->vla-object (nth 0 hanging_ssset)) "y" hanging_offset_start_)
                      
                    )
                  )
                  (setq hanging_dist_time_i (+ hanging_dist_time_i 1))
                )
                ; (if (= hanging_dist_time_ 3)
                ;   (progn
                ;     (TA:move_axis_insertionpoint (vlax-ename->vla-object (nth 1 hanging_ssset)) "y" -12.5)
                    
                ;   )
                ; )
              ;
              (princ "_case_2")
            )
          )
          (;case_3
            (and
                (= (LM:getdynpropvalue ss_pre_filter_set_xx_obj_ "view" ) "7_dynamic_length_view")
                (= (rtos ss_pre_filter_set_xx_obj_ins_rotation_ 2 1) "0.0")
                ; (> (LM:getdynpropvalue ss_pre_filter_set_xx_obj_ "fragment_middle") 1500)
                ; (= (substr (rtos (/ (LM:getdynpropvalue ss_pre_filter_set_xx_obj_ "fragment_middle") 50 ) 2 2 ) (+ (vl-string-search "." (rtos (/ (LM:getdynpropvalue ss_pre_filter_set_xx_obj_ "fragment_middle" ) 50 ) 2 2 ) ) 2 ) 1 ) "0" )
            )
            (TA:vla-insertblock 
              "000 - DYNAMIC_LENGTH+COMBINE+VIEW_ASSCESSORIES_FAMELINE_BK-08_HANGING_SYSTEM_300HK_COMBINE_SET"
              (if (= (getvar "worlducs") 0) (progn (trans ss_pre_filter_set_xx_obj_ins_ 1 1)) ss_pre_filter_set_xx_obj_ins_ )
              1
              (deg-to-rad 0)
            )
            ;new_blk_entlast object
              (setq newhang_ename (entlast))
              (setq newhang_obj_ (vlax-ename->vla-object newhang_ename))
              (setq newhang_obj_ins_ (vlax-safearray->list (vlax-variant-value (vla-get-insertionpoint newhang_obj_))))
              (vla-put-layer newhang_obj_ "001 - ASCESSORIES")
              (vla-put-color newhang_obj_ 256)
              (vla-put-linetype newhang_obj_ "byblock")
              (LM:setdynpropvalue newhang_obj_ "view" "2_top_view")
              (setq hanging_ssset (cons newhang_ename hanging_ssset))
            ;
          )
        )
        (setq ss_pre_filter_set_xx_i (+ ss_pre_filter_set_xx_i 1))
      )
    ;
  )
  (defun c:PPLINE-CKST-INTERhang ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000 - DYNAMIC_COMBINE+VIEW_ASSCESSORIES_FAMELINE_GALV.BRACKET_FITTING_U-PROFILE_CC-01_COMBINE_VIEW"))
    ;
    
    ;preloop_and_while
      (setq ss_pre_filter_set_xx_i 0)
      (setq cc-01_inters_list_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_rotation_ (rad-to-deg (vla-get-rotation ss_pre_filter_set_xx_obj_)))
        (setq cc-01_inters_list_ 
          (cons 
            (list
              (polar ss_pre_filter_set_xx_obj_ins_  (deg-to-rad (TA:ModifyRotation ss_pre_filter_set_xx_obj_rotation_ 180)) (+ (LM:getdynpropvalue ss_pre_filter_set_xx_obj_ "fragment_left") (/ (LM:getdynpropvalue ss_pre_filter_set_xx_obj_ "array_length") 2)))
              (polar ss_pre_filter_set_xx_obj_ins_ 
                    (deg-to-rad (TA:ModifyRotation ss_pre_filter_set_xx_obj_rotation_ 0) )
                    (+ (/ (LM:getdynpropvalue ss_pre_filter_set_xx_obj_ "array_length") 2 ) (LM:getdynpropvalue ss_pre_filter_set_xx_obj_ "fragment_right") )
              )
            )
            cc-01_inters_list_
          )
        )  
        
        (setq ss_pre_filter_set_xx_i (+ ss_pre_filter_set_xx_i 1))
      )
    ;
    (setq Er-msg_ nil)
    (setvar "osmode" 0)
    (while
      (and (/= (vl-catch-all-error-p Er-msg_) T) )
      (graphscr)
      (setq Er-msg_ (vl-catch-all-apply (function (lambda () (setq ss_extr_ename_ (ssname  (ssget ":S" (list (cons 0 "line") (cons 62 6)) ) 0)) ) ) ) )
      (if (and 
            (/= (vl-catch-all-error-p Er-msg_) T)
            (and
              (= (vla-get-objectname (vlax-ename->vla-object ss_extr_ename_)) "AcDbLine")
            )
          )
        (progn
          ;switch window
            (textscr)
            (vla-put-WindowState (vlax-get-acad-object) acmin)
          ; 

          (setq ss_extr_obj_ (vlax-ename->vla-object ss_extr_ename_))
          (setq ss_extr_obj_start_end_pt_ (list
                                          (setq ss_extr_obj_startpt_ (vlax-safearray->list
                                                                     (vlax-variant-value ( vla-get-startpoint ss_extr_obj_ ))
                                                                   )
                                          )
                                          (setq ss_extr_obj_endpt_ (vlax-safearray->list
                                                                    (vlax-variant-value ( vla-get-endpoint ss_extr_obj_ ))
                                                                 )
                                          )
                                        )
          )
          (setq ssextr_ptmid1-4 (car ss_extr_obj_start_end_pt_) )
          (setq ssextr_ptmid2-3 (cadr ss_extr_obj_start_end_pt_) )
        )
        (graphscr)
      )
      ;preloop_and_while
        (setq cc-01_inters_list_i 0)
        (while (and
                  (/= (vl-catch-all-error-p Er-msg_) T)
                  (< cc-01_inters_list_i (length cc-01_inters_list_) )
                )
          (setq cc-01_inters_list_val_1 (car (nth  cc-01_inters_list_i cc-01_inters_list_)))
          (setq cc-01_inters_list_val_2 (cadr (nth  cc-01_inters_list_i cc-01_inters_list_)))
          
          (if (/= (inters ssextr_ptmid1-4 ssextr_ptmid2-3 cc-01_inters_list_val_1 cc-01_inters_list_val_2 ) nil)
            (progn
              (TA:vla-insertblock 
                "000 - DYNAMIC_LENGTH+COMBINE+VIEW_ASSCESSORIES_FAMELINE_BK-08_HANGING_SYSTEM_300HK_COMBINE_SET"
                (inters ssextr_ptmid1-4 ssextr_ptmid2-3 cc-01_inters_list_val_1 cc-01_inters_list_val_2 )
                1
                0
              )
              ;new_blk_entlast object
                (setq new_ename (entlast))
                (setq new_obj_ (vlax-ename->vla-object new_ename))
                (LM:setdynpropvalue new_obj_  "view" "2_top_view")
              ; 
            )
          )
  
          (TA:textscr_process "insertion process " cc-01_inters_list_i cc-01_inters_list_)
      
          (setq cc-01_inters_list_i (+ cc-01_inters_list_i 1))
        )
      ;
      
    )
    (setvar "osmode" 1215)
  )
  (defun c:lineinter_Lit0_ ()

    (setq new_ss_ (ssadd))
    (setq new_ss_ (ssget "_+.:E:S" 
                          (list 
                            (cons 0 "line") ;type of object
                            ; (cons 8 "000 - GRID")   ;kind of layer
                            ; (cons 2 "000-GRID_LINE_DYN")       ;kind of nameblock
                            ;  (cons 62 4)             ;kind of color call sign with color code index
                          )
                    )
    )
    (setq new_obj_ (vlax-ename->vla-object (ssname  new_ss_ 0)))
    (setq new_obj_ro_ (vla-get-angle new_obj_))
    (while
      (/=
        (vl-princ-to-string
          (setq Er-msg_new_ename_
            (vl-catch-all-apply 
              (function 
                (lambda () 
                  ;selection_set_for_fillter_blk_name
                    (if  ;pre_select_ssget_or_post_select_ssget
                      (=
                        (setq ss_pre_filter_set_xx_ (ssget "i"
                                                          (list
                                                            (cons 0 "line") ;type of object
                                                            ; (cons 8 "000 - GRID")   ;kind of layer
                                                            ; (cons 2 "000-GRID_LINE_DYN")       ;kind of nameblock
                                                            (cons 62 4)           ;kind of color call sign with color code index
                                                          )
                                                    )
                        )
                        nil
                      )
                      (progn
                        (setq ss_pre_filter_set_xx_ (ssget
                                                          (list
                                                            (cons 0 "line") ;type of object
                                                            ; (cons 8 "000 - GRID")   ;kind of layer
                                                            ; (cons 2 "000-GRID_LINE_DYN")       ;kind of nameblock
                                                            (cons 62 4)             ;kind of color call sign with color code index
                                                          )
                                                    )
                        )
                      )
                      (sslength ss_pre_filter_set_xx_)
                    )
                  ;
                )
              )
            )
          )
        )
        "#<%catch-all-apply-error%>"
      )
      (setvar "CMDECHO" 0)
      (TA:interface_text_ T) 
      (setq new-lee_ (TA:Combine-SS new_ss_ ss_pre_filter_set_xx_ ) )
      (setq inter_hang_list_ (LM:intersectionsinset+0 new-lee_))
      ;preloop_and_while
        (setq inter_hang_list_i 0)
        (while (< inter_hang_list_i (length inter_hang_list_))
          (setq inter_hang_list_val_ (nth  inter_hang_list_i inter_hang_list_))
          (TA:vla-insertblock ;insert loop * dist. time (hanging_dist_time_i by hanging_dist_time_i)
            "000 - DYNAMIC_LENGTH+COMBINE+VIEW_ASSCESSORIES_FAMELINE_BK-08_HANGING_SYSTEM_300HK_COMBINE_SET"
            inter_hang_list_val_
            1
            new_obj_ro_
          )
          ;new_blk_entlast object
            (setq newhang_ename (entlast))
            (setq newhang_obj_ (vlax-ename->vla-object newhang_ename))
            (setq newhang_obj_ins_ (vlax-safearray->list (vlax-variant-value (vla-get-insertionpoint newhang_obj_))))
            (vla-put-layer newhang_obj_ "001 - ASCESSORIES")
            (vla-put-color newhang_obj_ 256)
            (vla-put-linetype newhang_obj_ "byblock")
            (LM:setdynpropvalue newhang_obj_ "view" "2_top_view")
          ;
          (TA:textscr_process_V2 "insert" inter_hang_list_i inter_hang_list_ )
          (setq inter_hang_list_i (+ inter_hang_list_i 1))
        )
      ;
      (setvar "CMDECHO" 0)
      (TA:interface_text_ nil) 
    )
  )
  (defun c:lineinter_Lit_ ()
    ;selection_set_for_fillter_blk_name
      (if  ;pre_select_ssget_or_post_select_ssget
        (=
          (setq ss_pre_filter_set_xx_ (ssget "i"
                                            (list
                                              (cons 0 "line") ;type of object
                                              ; (cons 8 "000 - GRID")   ;kind of layer
                                              ; (cons 2 "000-GRID_LINE_DYN")       ;kind of nameblock
                                              (cons 62 4)           ;kind of color call sign with color code index
                                            )
                                      )
          )
          nil
        )
        (progn
          (setq ss_pre_filter_set_xx_ (ssget
                                            (list
                                              (cons 0 "line") ;type of object
                                              ; (cons 8 "000 - GRID")   ;kind of layer
                                              ; (cons 2 "000-GRID_LINE_DYN")       ;kind of nameblock
                                              (cons 62 4)             ;kind of color call sign with color code index
                                            )
                                      )
          )
        )
        (sslength ss_pre_filter_set_xx_)
      )
    ;
    (while
      (/=
        (vl-princ-to-string
          (setq Er-msg_new_ename_
            (vl-catch-all-apply 
              (function 
                (lambda () 
                  (setq new_ss_ (ssadd))
                  (setq new_ss_ (ssget  
                                        (list 
                                          (cons 0 "line") ;type of object
                                          ; (cons 8 "000 - GRID")   ;kind of layer
                                          ; (cons 2 "000-GRID_LINE_DYN")       ;kind of nameblock
                                           (cons 62 2)             ;kind of color call sign with color code index
                                        )
                                  )
                  )
                  (setq new_obj_ (vlax-ename->vla-object (ssname  new_ss_ 0)))
                  (setq new_obj_ro_ (vla-get-angle new_obj_))
                )
              )
            )
          )
        )
        "#<%catch-all-apply-error%>"
      )
      (setvar "CMDECHO" 0)
      (TA:interface_text_ T) 
      (setq new-lee_ (TA:Combine-SS new_ss_ ss_pre_filter_set_xx_ ) )
      (setq inter_hang_list_ (LM:intersectionsinset+0 new-lee_))
      ;preloop_and_while
        (setq inter_hang_list_i 0)
        (while (< inter_hang_list_i (length inter_hang_list_))
          (setq inter_hang_list_val_ (nth  inter_hang_list_i inter_hang_list_))
          (TA:vla-insertblock ;insert loop * dist. time (hanging_dist_time_i by hanging_dist_time_i)
            "000 - DYNAMIC_LENGTH+COMBINE+VIEW_ASSCESSORIES_FAMELINE_BK-08_HANGING_SYSTEM_300HK_COMBINE_SET"
            inter_hang_list_val_
            1
            new_obj_ro_
          )
          ;new_blk_entlast object
            (setq newhang_ename (entlast))
            (setq newhang_obj_ (vlax-ename->vla-object newhang_ename))
            (setq newhang_obj_ins_ (vlax-safearray->list (vlax-variant-value (vla-get-insertionpoint newhang_obj_))))
            (vla-put-layer newhang_obj_ "001 - ASCESSORIES")
            (vla-put-color newhang_obj_ 256)
            (vla-put-linetype newhang_obj_ "byblock")
            (LM:setdynpropvalue newhang_obj_ "view" "2_top_view")
          ;
          (TA:textscr_process_V2 "insert" inter_hang_list_i inter_hang_list_ )
          (setq inter_hang_list_i (+ inter_hang_list_i 1))
        )
      ;
      (setvar "CMDECHO" 0)
      (TA:interface_text_ nil) 
    )
  )
  (defun c:lineinter_Lity_ ()
    (setvar "SELECTIONPREVIEW" 0)
    (while
      (/=
        (vl-princ-to-string
          (setq Er-msg_new_ename_
            (vl-catch-all-apply 
              (function 
                (lambda () 
                  (setq new_ss_ (ssadd))
                  ;selection_set_for_fillter_blk_name
                    (if  ;pre_select_ssget_or_post_select_ssget
                      (= 
                        (setq new_ss_ (ssget "i"
                                        (list 
                                          (cons 0 "line") ;type of object
                                          ; (cons 8 "000 - GRID")   ;kind of layer
                                          ; (cons 2 "000-GRID_LINE_DYN")       ;kind of nameblock
                                          '(-4 . "<OR")
                                          ; (cons 62 1) ; สีเบอร์ 2
                                          (cons 62 2) ; สีเบอร์ 3
                                          ; (cons 62 3) ; สีเบอร์ 3
                                          (cons 62 4) ; สีเบอร์ 3
                                          '(-4 . "OR>")
                                        )
                                      )
                        )
                        nil
                      )
                      (progn 
                        (setq new_ss_ (ssget 
                                        (list 
                                          (cons 0 "line") ;type of object
                                          ; (cons 8 "000 - GRID")   ;kind of layer
                                          ; (cons 2 "000-GRID_LINE_DYN")       ;kind of nameblock
                                          '(-4 . "<OR")
                                          ; (cons 62 1) ; สีเบอร์ 2
                                          (cons 62 2) ; สีเบอร์ 3
                                          ; (cons 62 3) ; สีเบอร์ 3
                                          (cons 62 4) ; สีเบอร์ 3
                                          '(-4 . "OR>")
                                        )
                                      )
                        )
                      )
                      (sslength new_ss_)
                    )
                  ;
                )
              )
            )
          )
        )
        "#<%catch-all-apply-error%>"
      )
      (setvar "CMDECHO" 0)
      (setvar "osmode" 0)
      ; (TA:interface_text_ T) 
      (setq inter_hang_list_ (LM:intersectionsinset+0 new_ss_))
      ;preloop_and_while
        (setq inter_hang_list_i 0)
        (setq new_ss_line_ (ssadd))
        (while (and 
                 
                 (< inter_hang_list_i (length inter_hang_list_))
               )
          (setq inter_hang_list_val_ (nth  inter_hang_list_i inter_hang_list_))
          (TA:vla-insertblock ;insert loop * dist. time (hanging_dist_time_i by hanging_dist_time_i)
            "000-GRID_LINE_DYN_V2-FOR-CC012"
            inter_hang_list_val_
            1
            (deg-to-rad 90)
          )
          ;new_blk_entlast object
            ; (command "circle" inter_hang_list_val_  100 )
            (setq newhang_ename (entlast))
            (setq new_ss_line_ (ssadd newhang_ename new_ss_line_))
            (setq newhang_obj_ (vlax-ename->vla-object newhang_ename))
            ; (setq newhang_obj_ins_ (vlax-safearray->list (vlax-variant-value (vla-get-insertionpoint newhang_obj_))))
            (vla-put-layer newhang_obj_ "001 - ASCESSORIES")
            (vla-put-color newhang_obj_ 3)
            ; (vla-put-linetype newhang_obj_ "byblock")
            ; (LM:setdynpropvalue newhang_obj_ "view" "2_top_view")
          ;
          (TA:textscr_process_V2 "insert" inter_hang_list_i inter_hang_list_ )
          (setq inter_hang_list_i (+ inter_hang_list_i 1))
        )
      ;
      (setvar "CMDECHO" 0)
      ; (TA:interface_text_ nil)
      
    )
    ; (setvar "SELECTIONPREVIEW" 3)
    (setvar "osmode" 1215)
    (command "erase"  new_ss_ "" )
    (command "pselect"  new_ss_line_ "" )
  )
  (defun c:lineinter_Litr ()
    (setvar "SELECTIONPREVIEW" 0)
    (while
      (/=
        (vl-princ-to-string
          (setq Er-msg_new_ename_
            (vl-catch-all-apply 
              (function 
                (lambda () 
                  (setq new_ss_ (ssadd))
                  ;selection_set_for_fillter_blk_name
                    (if  ;pre_select_ssget_or_post_select_ssget
                      (= 
                        (setq new_ss_ (ssget "i"
                                        (list 
                                          (cons 0 "line") ;type of object
                                          ; (cons 8 "000 - GRID")   ;kind of layer
                                          ; (cons 2 "000-GRID_LINE_DYN")       ;kind of nameblock
                                          '(-4 . "<OR")
                                          (cons 62 1) ; สีเบอร์ 2
                                          ; (cons 62 2) ; สีเบอร์ 3
                                          ; (cons 62 3) ; สีเบอร์ 3
                                          (cons 62 4) ; สีเบอร์ 3
                                          '(-4 . "OR>")
                                        )
                                      )
                        )
                        nil
                      )
                      (progn 
                        (setq new_ss_ (ssget 
                                        (list 
                                          (cons 0 "line") ;type of object
                                          ; (cons 8 "000 - GRID")   ;kind of layer
                                          ; (cons 2 "000-GRID_LINE_DYN")       ;kind of nameblock
                                          '(-4 . "<OR")
                                          (cons 62 1) ; สีเบอร์ 2
                                          ; (cons 62 2) ; สีเบอร์ 3
                                          ; (cons 62 3) ; สีเบอร์ 3
                                          (cons 62 4) ; สีเบอร์ 3
                                          '(-4 . "OR>")
                                        )
                                      )
                        )
                      )
                      (sslength new_ss_)
                    )
                  ;
                )
              )
            )
          )
        )
        "#<%catch-all-apply-error%>"
      )
      (setvar "CMDECHO" 0)
      (setvar "osmode" 0)
      ; (TA:interface_text_ T) 
      (setq inter_hang_list_ (LM:intersectionsinset+0 new_ss_))
      ;preloop_and_while
        (setq inter_hang_list_i 0)
        (while (< inter_hang_list_i (length inter_hang_list_))
          (setq inter_hang_list_val_ (nth  inter_hang_list_i inter_hang_list_))
          ; (TA:vla-insertblock ;insert loop * dist. time (hanging_dist_time_i by hanging_dist_time_i)
          ;   "000 - DYNAMIC_LENGTH+COMBINE+VIEW_ASSCESSORIES_FAMELINE_BK-08_HANGING_SYSTEM_300HK_COMBINE_SET"
          ;   inter_hang_list_val_
          ;   1
          ;   new_obj_ro_
          ; )
          ;new_blk_entlast object
            (command "circle" inter_hang_list_val_  100 )
            (setq newhang_ename (entlast))
            (setq newhang_obj_ (vlax-ename->vla-object newhang_ename))
            ; (setq newhang_obj_ins_ (vlax-safearray->list (vlax-variant-value (vla-get-insertionpoint newhang_obj_))))
            (vla-put-layer newhang_obj_ "001 - ASCESSORIES")
            (vla-put-color newhang_obj_ 3)
            ; (vla-put-linetype newhang_obj_ "byblock")
            ; (LM:setdynpropvalue newhang_obj_ "view" "2_top_view")
          ;
          (TA:textscr_process_V2 "insert" inter_hang_list_i inter_hang_list_ )
          (setq inter_hang_list_i (+ inter_hang_list_i 1))
        )
      ;
      (setvar "CMDECHO" 0)
      ; (TA:interface_text_ nil) 
    )
    (setvar "SELECTIONPREVIEW" 3)
    (setvar "osmode" 1215)
  )
  (defun c:gridinter_ligi ()
    (setvar "SELECTIONPREVIEW" 0)
    (setvar "CMDECHO" 0)
    (while
      (/=
        (vl-princ-to-string
          (setq ERR_
            (vl-catch-all-apply
              (function
                (lambda ()
                  ;selection_set_for_fillter_blk_name
                    (if  ;pre_select_ssget_or_post_select_ssget
                      (=
                        (setq ss_pre_filter_set_xx_ (ssget "i"
                                                          (list
                                                            (cons 0 "INSERT,line") ;type of object
                                                            ; (cons 8 "000 - GRID")   ;kind of layer
                                                            ; (cons 2 "000-GRID_LINE_DYN")       ;kind of nameblock
                                                            '(-4 . "<OR")
                                                              (cons 62 4) ; สีเบอร์ 4
                                                              (cons 62 2) ; สีเบอร์ 3
                                                            '(-4 . "OR>")
                                                          )
                                                    )
                        )
                        nil
                      )
                      (progn
                        (setq ss_pre_filter_set_xx_ (ssget
                                                          (list
                                                            (cons 0 "INSERT,line") ;type of object
                                                            ; (cons 8 "000 - GRID")   ;kind of layer
                                                            ; (cons 2 "000-GRID_LINE_DYN")       ;kind of nameblock
                                                            '(-4 . "<OR")
                                                              (cons 62 4) ; สีเบอร์ 4
                                                              (cons 62 2) ; สีเบอร์ 3
                                                            '(-4 . "OR>")
                                                          )
                                                    )
                        )
                      )
                      (sslength ss_pre_filter_set_xx_)
                    )
                  ;
                )
              )
            )
          )
        )
        "#<%catch-all-apply-error%>"
      )
      ;preloop_and_while
        (setq ss_pre_filter_set_xx_i 0)
        (setq inter_for_list_ ())
        (while (< ss_pre_filter_set_xx_i (sslength ss_pre_filter_set_xx_))
          (setq ss_pre_filter_set_xx_ename1_ (ssname ss_pre_filter_set_xx_ ss_pre_filter_set_xx_i))
          (setq ss_pre_filter_set_xx_obj1_ (vlax-ename->vla-object  ss_pre_filter_set_xx_ename1_))
          (if (or 
                (= (vla-get-objectname ss_pre_filter_set_xx_obj1_ ) "AcDbLine")
                (and 
                  (= (vla-get-objectname ss_pre_filter_set_xx_obj1_ ) "AcDbBlockReference")
                  (or
                    (= (LM:effectivename ss_pre_filter_set_xx_obj1_)  "000-GRID_LINE_DYN_V2-FOR-CC012")
                    (= (LM:effectivename ss_pre_filter_set_xx_obj1_)  "000 - DYNAMIC_COMBINE+VIEW_ASSCESSORIES_FAMELINE_GALV.BRACKET_FITTING_U-PROFILE_CC-01-4_COMBINE_VIEW")
                  )
                )
              )
            (progn
              (setq inter_for_list_ (cons  ss_pre_filter_set_xx_obj1_ inter_for_list_))
            )
          )
          (TA:textscr_process_V2 "insert" ss_pre_filter_set_xx_i ss_pre_filter_set_xx_ )
          (setq ss_pre_filter_set_xx_i (+ ss_pre_filter_set_xx_i 1))
        )
        
        (setq xxxx (LM:intersectionsinobjlist inter_for_list_))
        (foreach x xxxx
          (command "circle" 
                  (if (= (getvar "worlducs") 0)(progn (trans x 0 1)) x ) 
                  150
          )
          ;new_blk_entlast object
            (setq new_ename (entlast))
            (setq new_obj_ (vlax-ename->vla-object new_ename))
            (vla-put-color new_obj_ 3)
          ;
        )
      ;

    )
    (setvar "CMDECHO" 1)
  )
  (defun c:lineinter_Litc_ ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "line") ;type of object
                                                    ; (cons 8 "000 - GRID")   ;kind of layer
                                                    ; (cons 2 "000-GRID_LINE_DYN")       ;kind of nameblock
                                                    (cons 62 4)           ;kind of color call sign with color code index
                                                  )
                                            )
                )
                nil
              )
              (progn
                (setq ss_pre_filter_set_xx_ (ssget
                                                  (list
                                                    (cons 0 "line") ;type of object
                                                    ; (cons 8 "000 - GRID")   ;kind of layer
                                                    ; (cons 2 "000-GRID_LINE_DYN")       ;kind of nameblock
                                                    (cons 62 4)             ;kind of color call sign with color code index
                                                  )
                                            )
                )
              )
              (sslength ss_pre_filter_set_xx_)
            )
          ;
        )
        (setq ss_pre_filter_set_xx_ ss_pre_filter_set_xx_)
      )
    ;
    (while
      (/=
        (vl-princ-to-string
          (setq Er-msg_new_ename_
            (vl-catch-all-apply 
              (function 
                (lambda () 
                  (setq new_ss_ (ssadd))
                  (setq new_ss_ (ssget 
                                  (list 
                                    (cons 0 "line") ;type of object
                                    ; (cons 8 "000 - GRID")   ;kind of layer
                                    ; (cons 2 "000-GRID_LINE_DYN")       ;kind of nameblock
                                    '(-4 . "<OR")
                                    (cons 62 1) ; สีเบอร์ 2
                                    (cons 62 2) ; สีเบอร์ 3
                                    (cons 62 3) ; สีเบอร์ 3
                                    '(-4 . "OR>")
                                  )
                                )
                  )
                  (setq new_obj_ (vlax-ename->vla-object (ssname  new_ss_ 0)))
                  (setq new_obj_ro_ (vla-get-angle new_obj_))
                )
              )
            )
          )
        )
        "#<%catch-all-apply-error%>"
      )
      (setvar "CMDECHO" 0)
      (setvar "osmode" 0)
      (TA:interface_text_ T) 
      (setq new-lee_ (TA:Combine-SS new_ss_ ss_pre_filter_set_xx_ ) )
      (setq inter_hang_list_ (LM:intersectionsinset+0 new-lee_))
      ;preloop_and_while
        (setq inter_hang_list_i 0)
        (while (< inter_hang_list_i (length inter_hang_list_))
          (setq inter_hang_list_val_ (nth  inter_hang_list_i inter_hang_list_))
          ; (TA:vla-insertblock ;insert loop * dist. time (hanging_dist_time_i by hanging_dist_time_i)
          ;   "000 - DYNAMIC_LENGTH+COMBINE+VIEW_ASSCESSORIES_FAMELINE_BK-08_HANGING_SYSTEM_300HK_COMBINE_SET"
          ;   inter_hang_list_val_
          ;   1
          ;   new_obj_ro_
          ; )
          ;new_blk_entlast object
            (command "circle" inter_hang_list_val_  40 )
            (setq newhang_ename (entlast))
            (setq newhang_obj_ (vlax-ename->vla-object newhang_ename))
            ; (setq newhang_obj_ins_ (vlax-safearray->list (vlax-variant-value (vla-get-insertionpoint newhang_obj_))))
            (vla-put-layer newhang_obj_ "001 - ASCESSORIES")
            (vla-put-color newhang_obj_ 3)
            ; (vla-put-linetype newhang_obj_ "byblock")
            ; (LM:setdynpropvalue newhang_obj_ "view" "2_top_view")
          ;
          (TA:textscr_process_V2 "insert" inter_hang_list_i inter_hang_list_ )
          (setq inter_hang_list_i (+ inter_hang_list_i 1))
        )
      ;
      (setvar "CMDECHO" 0)
      (TA:interface_text_ nil) 
    )
    (setvar "osmode" 1215)
  )
  (defun c:revhang_ ()
    ;selection_set_for_fillter_blk_name
      (if  ;pre_select_ssget_or_post_select_ssget
        (=
          (setq ss_pre_filter_set_xx_ (ssget "i"
                                            (list
                                              (cons 0 "INSERT") ;type of object
                                              (cons -4 "<NOT")
                                              (cons 8 "000 - CSD_PL_A-_ANOT----_T-,") 
                                              (cons -4 "NOT>")
                                              (cons 8 "001 - ASCESSORIES,000 - CSD_PL_Defpoints,000 - CSD_PL_001 - ASCESSORIES")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              (cons -4 "<NOT")
                                              (cons 8 "000 - CSD_PL_A-_ANOT----_T-") 
                                              (cons -4 "NOT>")
                                              (cons 8 "001 - ASCESSORIES,000 - CSD_PL_Defpoints,000 - CSD_PL_001 - ASCESSORIES")   ;kind of layer
                                              ; (cons 2 "000-GRID_LINE_DYN")       ;kind of nameblock
                                              ; (cons 62 1)           ;kind of color call sign with color code index
                                            )
                                      )
          )
        )
        (sslength ss_pre_filter_set_xx_)
      )
    ;
    (textscr)
    (setq ss_pre_filter_set_xx_  (TA:EF_Filter_ss_set_ ss_pre_filter_set_xx_  "000 - DYNAMIC_LENGTH+COMBINE+VIEW_ASSCESSORIES_FAMELINE_BK-08_HANGING_SYSTEM_300HK_COMBINE_SET"))
    ;preloop_and_while
      (setq ss_pre_filter_set_xx_i 0)
      (setvar "CMDECHO" 0)
      (TA:interface_text_ T)
      (setq new_rev_ss_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        
        (command "circle" 
                  (if (= (getvar "worlducs") 0)(progn (trans ss_pre_filter_set_xx_obj_ins_ 0 1)) ss_pre_filter_set_xx_obj_ins_ ) 
                  150
        )
        ;new_blk_entlast object
          (setq new_revc_ename (entlast))
          (setq new_rev_ss_ (ssadd new_revc_ename new_rev_ss_)) 
          ; (setq new_revc_obj_ (vlax-ename->vla-object new_revc_ename))
          ; (command "revcloud"  "A"  80 "" "o" new_revc_ename "n") 
          ; (setq new_revc_ename (entlast))
          ; (setq new_revc_obj_ (vlax-ename->vla-object new_revc_ename))
          ; (vla-put-color new_revc_obj_ 6)
          ; (vla-put-ConstantWidth new_revc_obj_ 10)
    
        ;
        (TA:textscr_process "\nupdate" ss_pre_filter_set_xx_i ss_pre_filter_set_xx_)
        (setq ss_pre_filter_set_xx_i (+ ss_pre_filter_set_xx_i 1))
        
      )
    ;
      (setvar "osmode" 0)
      (setq main_bol_ (TA:ss_vla-getboundingbox new_rev_ss_ ))
      (command "rectangle" (car main_bol_ ) (cadr main_bol_ ))
      (setq new_revc_ename (entlast))
      (setq new_revc_obj_ (vlax-ename->vla-object new_revc_ename))
      (command "revcloud"  "A"  200 "" "o" new_revc_ename "n") 
      (setq new_revc_ename (entlast))
      (setq new_revc_obj_ (vlax-ename->vla-object new_revc_ename))
      (vla-put-color new_revc_obj_ 6)
      (vla-put-ConstantWidth new_revc_obj_ 10)
      (command "erase" new_rev_ss_ "")
      (TA:interface_text_ nil)
      (setvar "CMDECHO" 1)
      (setvar "osmode" 1215)
    
  )
  (defun c:revhang2_ ()
    (defun LM:PolyOutline ( ent / _vertices lst )
    
        (defun _vertices ( e )
            (if (setq e (member (assoc 10 e) e))
                (cons
                    (list
                        (cdr (assoc 10 e))
                        (cdr (assoc 40 e))
                        (cdr (assoc 41 e))
                    )
                    (_vertices (cdr e))
                )
            )
        )
    
        (setq
            ent (entget ent)
            lst (_vertices ent)
            lst (apply 'mapcar
                    (cons
                        (function
                            (lambda ( a b )
                                (
                                    (lambda ( c )
                                        (mapcar
                                            (function
                                                (lambda ( d )
                                                    (mapcar
                                                        (function
                                                            (lambda ( e f )
                                                                (mapcar 'd (car e)
                                                                    (mapcar
                                                                        (function
                                                                            (lambda ( g ) (* g (/ f 2.0)))
                                                                        )
                                                                        c
                                                                    )
                                                                )
                                                            )
                                                        )
                                                        (list a b) (cdr a)
                                                    )
                                                )
                                            )
                                            (list + -)
                                        )
                                    )
                                    (
                                        (lambda ( v / n )
                                            (setq v (list (- (cadr v)) (car v) 0.0)
                                                  n (distance '(0. 0.) v)
                                            )
                                            (if (equal 0.0 n 1e-14)
                                                (list  0.0 0.0 0.0)
                                                (mapcar '/ v (list n n n))
                                            )
                                        )
                                        (mapcar '- (car a) (car b))
                                    )
                                )
                            )
                        )
                        (if (= 1 (logand 1 (cdr (assoc 70 ent))))
                            (list
                                (cons (last lst) lst)
                                (append lst (list (car lst)))
                            )
                            (list lst (cdr lst))
                        )
                    )
                )
            lst (
                    (lambda ( a )
                        (if (zerop (logand 1 (cdr (assoc 70 ent))))
                            (append
                                (list (mapcar 'car  (car  lst)))
                                a
                                (list (mapcar 'cadr (last lst)))
                            )
                            a
                        )
                    )
                    (apply 'append
                        (mapcar
                            (function
                                (lambda ( a b / c )
                                    (if
                                        (setq c
                                            (apply 'append
                                                (mapcar
                                                    (function
                                                        (lambda ( d e / f )
                                                            (if (setq f (inters (car d) (cadr d) (car e) (cadr e) nil))
                                                                (list f)
                                                            )
                                                        )
                                                    )
                                                    a b
                                                )
                                            )
                                        )
                                        (list c)
                                    )
                                )
                            )
                            lst (cdr lst)
                        )
                    )
                )
        )
        (mapcar
            (function
                (lambda ( a )
                    (entmakex
                        (append
                            (subst (cons 43 0.0) (assoc 43 ent)
                                (subst (cons 70 (logior 1 (cdr (assoc 70 ent)))) (assoc 70 ent)
                                    (subst (cons 90 (length a)) (assoc 90 ent)
                                        (reverse (member (assoc 39 ent) (reverse ent)))
                                    )
                                )
                            )
                            (mapcar '(lambda ( p ) (cons 10 p)) a) (list (assoc 210 ent))
                        )
                    )
                )
            )
            (
                (lambda ( a b )
                    (if (zerop (logand 1 (cdr (assoc 70 ent))))
                        (list
                            (append
                                (if (equal (car a) (last b) 1e-8)
                                    (setq a (cdr a))
                                    a
                                )
                                (if (equal (car b) (last a) 1e-8)
                                    (setq b (cdr b))
                                    b
                                )
                            )
                        )
                        (list a b)
                    )
                )
                (mapcar 'car lst) (reverse (mapcar 'cadr lst))
            )
        )
    )
    ;selection_set_for_fillter_blk_name
      (setq ss_pre_filter_set_xx_ ())
      (setq Er-msg_ ())
      (setq jkj ())
      (while
        (/= (wcmatch 
            (vl-princ-to-string
              (setq Er-msg_ 
                     (vl-catch-all-apply 
                       (function (lambda () 
                                   (setq ss_pre_filter_set_xx_ (cons  
                                                                  (ssname
                                                                        (setq Er-msg_2 
                                                                          (vl-catch-all-apply 
                                                                            (function 
                                                                              (lambda () 
                                                                                (setq sub_sset (ssget "_+.:E:S"
                                                                                            (list 
                                                                                              (cons 0 "circle") ;type of object
                                                                                              ; (cons 8 "000 - GRID")   ;kind of layer
                                                                                              ; (cons 2 "000-GRID_LINE_DYN")       ;kind of nameblock
                                                                                              '(-4 . "<OR")
                                                                                              (cons 62 1) ; สีเบอร์ 2
                                                                                              (cons 62 2) ; สีเบอร์ 3
                                                                                              (cons 62 3) ; สีเบอร์ 3
                                                                                              '(-4 . "OR>")
                                                                                            )
                                                                                      )
                                                                                )
                                                                              )
                                                                            )
                                                                          )
                                                                        )
                                                                      
                                                                    0
                                                                  )
                                                                  ss_pre_filter_set_xx_ 
                                                                ) 
                                    ) 
                                    
                                 ) 
                       ) 
                     ) 
              ) 
            )
            "*error*"
          ) 
          T
        )
      )
    ;
    ;preloop_and_while
      (setq ss_pre_filter_set_xx_i 0)
      (setq new_ss_circle_ins_ ())
      (while (and 
               (= Er-msg_2 nil)
               (< ss_pre_filter_set_xx_i (length ss_pre_filter_set_xx_))
             )
        (setq ss_pre_filter_set_xx_ename_ (nth ss_pre_filter_set_xx_i ss_pre_filter_set_xx_ ))
        (setq ss_pre_filter_set_xx_obj_ (vlax-ename->vla-object  ss_pre_filter_set_xx_ename_))
        (setq new_ss_circle_ins_ (cons (setq ss_pre_filter_set_xx_obj_cenpt (vlax-safearray->list (vlax-variant-value (vla-get-center ss_pre_filter_set_xx_obj_)))) new_ss_circle_ins_ ))
        (setq ss_pre_filter_set_xx_i (+ ss_pre_filter_set_xx_i 1))
      )
    ;
    ;TA:stanndard_lambda_sorting
      (setq new_ss_circle_ins_sorted_ new_ss_circle_ins_ )
      ; (setq new_ss_circle_ins_sorted_ (vl-sort new_ss_circle_ins_  ;bigest open indent list
      ;                                           (function 
      ;                                             (lambda (a b) 
      ;                                               (< (car a) (car b))
      ;                                             )
      ;                                           )
      ;                       ) ;bigest close indent list
      ; )
    ;
    (setvar "osmode" 0)
    (create-plines new_ss_circle_ins_sorted_ "open" )
    
    ;new_blk_entlast object
      (setq pline_ename (entlast))
      (setq pline_obj_ (vlax-ename->vla-object pline_ename))
      (vla-put-constantwidth pline_obj_ 200)
      (LM:PolyOutline pline_ename )
      (command "erase" pline_ename "")
      (setq new_revc_ename (entlast))
      
      (vla-Offset (vlax-ename->vla-object new_revc_ename) 150)
      (command "erase" new_revc_ename "")
      (setq newnew_revc_ename (entlast))
      (command "revcloud"  "A"  200 "" "o" newnew_revc_ename "n")
      (setq newnewnew_revc_ename (entlast)) 
      (setq newnewnew_revc_ename_obj_ (vlax-ename->vla-object newnewnew_revc_ename))
      (vla-put-color newnewnew_revc_ename_obj_ 6)
      (vla-put-constantwidth newnewnew_revc_ename_obj_ 10)
      (setvar "osmode" 1215)
    ;
    
  )
  (defun c:revhang3_ ()
    ;selection_set_for_fillter_blk_name
      (if  ;pre_select_ssget_or_post_select_ssget
        (=
          (setq ss_pre_filter_set_xx_ (ssget "i"
                                            (list
                                              (cons 0 "circle") ;type of object
                                              (cons -4 "<NOT")
                                              (cons 8 "000 - CSD_PL_A-_ANOT----_T-,") 
                                              (cons -4 "NOT>")
                                              (cons 8 "001 - ASCESSORIES,000 - CSD_PL_Defpoints,000 - CSD_PL_001 - ASCESSORIES")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "circle") ;type of object
                                              (cons -4 "<NOT")
                                              (cons 8 "000 - CSD_PL_A-_ANOT----_T-") 
                                              (cons -4 "NOT>")
                                              (cons 8 "001 - ASCESSORIES,000 - CSD_PL_Defpoints,000 - CSD_PL_001 - ASCESSORIES")   ;kind of layer
                                              ; (cons 2 "000-GRID_LINE_DYN")       ;kind of nameblock
                                              ; (cons 62 1)           ;kind of color call sign with color code index
                                            )
                                      )
          )
        )
        (sslength ss_pre_filter_set_xx_)
      )
    ;
    (textscr)
    ;preloop_and_while
      (setq ss_pre_filter_set_xx_i 0)
      (setvar "CMDECHO" 0)
      (TA:interface_text_ T)
      (setq new_rev_ss_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-center ss_pre_filter_set_xx_obj_))))
        
        (command "circle" 
                  (if (= (getvar "worlducs") 0)(progn (trans ss_pre_filter_set_xx_obj_ins_ 0 1)) ss_pre_filter_set_xx_obj_ins_ ) 
                  150
        )
        ;new_blk_entlast object
          (setq new_revc_ename (entlast))
          (setq new_rev_ss_ (ssadd new_revc_ename new_rev_ss_)) 
          ; (setq new_revc_obj_ (vlax-ename->vla-object new_revc_ename))
          ; (command "revcloud"  "A"  80 "" "o" new_revc_ename "n") 
          ; (setq new_revc_ename (entlast))
          ; (setq new_revc_obj_ (vlax-ename->vla-object new_revc_ename))
          ; (vla-put-color new_revc_obj_ 6)
          ; (vla-put-ConstantWidth new_revc_obj_ 10)
    
        ;
        (TA:textscr_process "\nupdate" ss_pre_filter_set_xx_i ss_pre_filter_set_xx_)
        (setq ss_pre_filter_set_xx_i (+ ss_pre_filter_set_xx_i 1))
        
      )
    ;
      (setvar "osmode" 0)
      (setq main_bol_ (TA:ss_vla-getboundingbox new_rev_ss_ ))
      (command "rectangle" (car main_bol_ ) (cadr main_bol_ ))
      (setq new_revc_ename (entlast))
      (setq new_revc_obj_ (vlax-ename->vla-object new_revc_ename))
      (command "revcloud"  "A"  200 "" "o" new_revc_ename "n") 
      (setq new_revc_ename (entlast))
      (setq new_revc_obj_ (vlax-ename->vla-object new_revc_ename))
      (vla-put-color new_revc_obj_ 6)
      (vla-put-ConstantWidth new_revc_obj_ 10)
      (command "erase" new_rev_ss_ "")
      (TA:interface_text_ nil)
      (setvar "CMDECHO" 1)
      (setvar "osmode" 1215)
    
  )
;
;000_CKST-FAMELINE_CEILING_CODE_PANEL
  ; (defun c:PPLINE_CKST_insert_code_panel_ins310adc ()
  ;   (setq panel_matt_type1_ ;Get-string by keep previous value
  ;       (if
  ;         (or
  ;           (/= (setq panel_matt_type1_val (getstring (strcat "\nSpecify MATT CODE <" (if panel_matt_type1_ panel_matt_type1_ "") ">: ") ) ) "" )
  ;         )
  ;           (progn
  ;             (setq panel_matt_type1_ panel_matt_type1_val)
  ;             (setq panel_matt_type1_keep_val_ panel_matt_type1_val)
  ;           )
  ;         (setq panel_matt_type1_val panel_matt_type1_keep_val_)
  ;       )
  ;   )
  ;   (setq color_code_ ;Get-string by keep previous value
  ;       (if
  ;         (or
  ;           (/= (setq color_code_val (getstring (strcat "\nSpecify color code <" (if color_code_ color_code_ "") ">: ") ) ) "" )
  ;         )
  ;           (progn
  ;             (setq color_code_ color_code_val)
  ;             (setq color_code_keep_val_ color_code_val)
  ;           )
  ;         (setq color_code_val color_code_keep_val_)
  ;       )
  ;   )
  ;   ;selection_set_for_fillter_blk_name
  ;     (if  ;pre_select_ssget_or_post_select_ssget
  ;       (=
  ;         (setq ss_pre_filter_set_xx_ (ssget "i"
  ;                                           (list
  ;                                             (cons 0 "INSERT") ;type of object
  ;                                             ; (cons 8 "000 - GRID")   ;kind of layer
  ;                                             ; (cons 2 "000-GRID_LINE_DYN")       ;kind of nameblock
  ;                                             ; (cons 62 1)           ;kind of color call sign with color code index
  ;                                           )
  ;                                     )
  ;         )
  ;         nil
  ;       )
  ;       (progn
  ;         (setq ss_pre_filter_set_xx_ (ssget
  ;                                           (list
  ;                                             (cons 0 "INSERT") ;type of object
  ;                                             ; (cons 8 "000 - GRID")   ;kind of layer
  ;                                             ; (cons 2 "000-GRID_LINE_DYN")       ;kind of nameblock
  ;                                             ; (cons 62 1)           ;kind of color call sign with color code index
  ;                                           )
  ;                                     )
  ;         )
  ;       )
  ;       (sslength ss_pre_filter_set_xx_)
  ;     )
  ;   ;
  ;   (TA:EF_Filter_ss_set_V2_ ss_pre_filter_set_xx_ (list "000 - FAMELINE-CKST_AL.CELING_PANEL_300HK_@310mm_BOTTOM_VIEW_FOR_AS-02(1st_LOT)" "000 - FAMELINE-CKST_AL.CELING_PANEL_300HK_@400mm_BOTTOM_VIEW_FOR_AS-02(1st_LOT)" ))
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object  ss_pre_filter_set_xx_ename_))
  ;       (setq ss_pre_filter_set_xx_obj_ins_ (vlax-safearray->list (vlax-variant-value (vla-get-insertionpoint ss_pre_filter_set_xx_obj_))))
        
  ;       (setq panel_name "300HK" )
  ;       (setq panel_length (if (or (= (LM:effectivename ss_pre_filter_set_xx_obj_) "000 - FAMELINE-CKST_AL.CELING_PANEL_300HK_@310mm_BOTTOM_VIEW_FOR_AS-02(1st_LOT)")  ) (progn 300 ) ) )
  ;       (setq panel_width (fix (LM:roundup (LM:getdynpropvalue ss_pre_filter_set_xx_obj_ "panel_width") 5)) )
  ;       ; (setq panel_color "XXXXXXX")
  ;       (setq panel_shape (if (or (= (LM:effectivename ss_pre_filter_set_xx_obj_) "000 - FAMELINE-CKST_AL.CELING_PANEL_300HK_@310mm_BOTTOM_VIEW_FOR_AS-02(1st_LOT)")  ) (progn "standard_shape" ) ) )
  ;       ; (setq panel_add-on "XXXXXXX" )
  ;       (setq panel_date-create (TA:cdate "-" "YYYYMMDD") )
  ;       (setq panel_station 
  ;         (cond
  ;           (;_case_1
  ;             (and
  ;                 (= (wcmatch (getvar "dwgname"  ) "*PP17*") )
  ;             )
  ;             (progn
  ;               "PP17"
                
  ;             )
  ;           )
  ;           (;_case_2
  ;             (and
  ;                 (= (wcmatch (getvar "dwgname"  ) "*PP18*") )
  ;             )
  ;             (progn
  ;               "PP18"
                
  ;             )
  ;           )
  ;           (;_case_3
  ;             (and
  ;                 (= (wcmatch (getvar "dwgname"  ) "*PP19*") )
  ;             )
  ;             (progn
  ;               "PP19"
                
  ;             )
  ;           )
  ;           (;_case_4
  ;             (and 
  ;               (= (wcmatch (getvar "dwgname"  ) "*PP20*") )
  ;             )
  ;             (progn
  ;               "PP20"
                
  ;             )
  ;           )
  ;         )
  ;       )
  ;       (setq panel_level 
  ;         (cond
  ;           (;_case_2
  ;             (and
  ;                 (= (wcmatch (getvar "dwgname"  ) "*PP17*") )
  ;                 (= (wcmatch (getvar "dwgname"  ) "AR-4150*") )
  ;             )
  ;             (progn
  ;               "concourse_level"
  ;             )
  ;           )
  ;           (;_case_3
  ;             (and
  ;                 (= (wcmatch (getvar "dwgname"  ) "*PP17*") )
  ;                 (= (wcmatch (getvar "dwgname"  ) "AR-4180*") )
  ;             )
  ;             (progn
  ;               "platform_level"
  ;             )
  ;           )
  ;           (;_case_1
  ;             (and
  ;                 (= (wcmatch (getvar "dwgname"  ) "*PP18*") )
  ;                 (= (wcmatch (getvar "dwgname"  ) "AR-4130*") )
  ;             )
  ;             (progn
  ;               "multi_purpose_level"
  ;             )
  ;           )
  ;           (;_case_2
  ;             (and
  ;                 (= (wcmatch (getvar "dwgname"  ) "*PP18*") )
  ;                 (= (wcmatch (getvar "dwgname"  ) "AR-4150*") )
  ;             )
  ;             (progn
  ;               "concourse_level"
  ;             )
  ;           )
  ;           (;_case_2
  ;             (and
  ;                 (= (wcmatch (getvar "dwgname"  ) "*PP18*") )
  ;                 (= (wcmatch (getvar "dwgname"  ) "AR-4160*") )
  ;             )
  ;             (progn
  ;               "upper_platform_level"
  ;             )
  ;           )
  ;           (;_case_2
  ;             (and
  ;                 (= (wcmatch (getvar "dwgname"  ) "*PP18*") )
  ;                 (= (wcmatch (getvar "dwgname"  ) "AR-4180*") )
  ;             )
  ;             (progn
  ;               "lower_platform_level"
  ;             )
  ;           )
  ;           (;_case_1
  ;             (and
  ;                 (= (wcmatch (getvar "dwgname"  ) "*PP19*") )
  ;                 (= (wcmatch (getvar "dwgname"  ) "AR-4130*") )
  ;             )
  ;             (progn
  ;               "multi_purpose_level"
  ;             )
  ;           )
  ;           (;_case_2
  ;             (and
  ;                 (= (wcmatch (getvar "dwgname"  ) "*PP19*") )
  ;                 (= (wcmatch (getvar "dwgname"  ) "AR-4150*") )
  ;             )
  ;             (progn
  ;               "concourse_level"
  ;             )
  ;           )
  ;           (;_case_2
  ;             (and
  ;                 (= (wcmatch (getvar "dwgname"  ) "*PP19*") )
  ;                 (= (wcmatch (getvar "dwgname"  ) "AR-4160*") )
  ;             )
  ;             (progn
  ;               "upper_platform_level"
  ;             )
  ;           )
  ;           (;_case_2
  ;             (and
  ;                 (= (wcmatch (getvar "dwgname"  ) "*PP19*") )
  ;                 (= (wcmatch (getvar "dwgname"  ) "AR-4180*") )
  ;             )
  ;             (progn
  ;               "lower_platform_level"
  ;             )
  ;           )
  ;           (;_case_1
  ;             (and
  ;                 (= (wcmatch (getvar "dwgname"  ) "*PP20*") )
  ;                 (= (wcmatch (getvar "dwgname"  ) "AR-4130*") )
  ;             )
  ;             (progn
  ;               "multi_purpose_level"
  ;             )
  ;           )
  ;           (;_case_2
  ;             (and
  ;                 (= (wcmatch (getvar "dwgname"  ) "*PP20*") )
  ;                 (= (wcmatch (getvar "dwgname"  ) "AR-4150*") )
  ;             )
  ;             (progn
  ;               "concourse_level"
  ;             )
  ;           )
  ;           (;_case_2
  ;             (and
  ;                 (= (wcmatch (getvar "dwgname"  ) "*PP20*") )
  ;                 (= (wcmatch (getvar "dwgname"  ) "AR-4180*") )
  ;             )
  ;             (progn
  ;               "platform_level"
  ;             )
  ;           )
            
  ;         )
  ;       )
  ;       (if (or 
  ;             (= (LM:effectivename ss_pre_filter_set_xx_obj_) "000 - FAMELINE-CKST_AL.CELING_PANEL_300HK_@310mm_BOTTOM_VIEW_FOR_AS-02(1st_LOT)")
  ;           )
  ;         (progn
  ;           (setq ss_pre_filter_set_xx_obj_total_panel_i (/ (LM:getdynpropvalue ss_pre_filter_set_xx_obj_ "ARRAY_LENGTH") 310))
  ;           (TA:vla-insertblock 
  ;             "000_CKST-FAMELINE_CEILING_CODE_PANEL"
  ;             ss_pre_filter_set_xx_obj_ins_
  ;             1
  ;             0
  ;           )
  ;           ;new_blk_entlast object
  ;             (setq new_box_ename (entlast))
  ;             (setq new_box_obj (vlax-ename->vla-object new_box_ename))
  ;             (LM:setdynpropvalue new_box_obj "distance1" 300)
  ;             (TA:move_polar_insertionpoint new_box_obj "Y" 300)
  ;           ;
  ;           (setq ASB_textbox_ename_obj_ (vlax-ename->vla-object new_box_ename))
  ;           ;input_first_pc
  ;             (setq panel_code_name1(LM:vl-setattributevalue ASB_textbox_ename_obj_ "panel_code_name" ""))
  ;             (LM:vl-setattributevalue ASB_textbox_ename_obj_ "panel_matt_type" panel_matt_type1)
  ;             (setq panel_name1 (LM:vl-setattributevalue ASB_textbox_ename_obj_ "panel_name" panel_name))
  ;             (setq panel_no1 (LM:vl-getattributevalue ASB_textbox_ename_obj_ "panel_no1" ))
  ;             (setq panel_length1 (LM:vl-setattributevalue ASB_textbox_ename_obj_ "panel_length" panel_length))
  ;             (setq panel_width1 (LM:vl-setattributevalue ASB_textbox_ename_obj_ "panel_width" panel_width))
  ;             (setq panel_color1 (LM:vl-setattributevalue ASB_textbox_ename_obj_ "panel_color" color_code_))
  ;             (setq panel_shape1 (LM:vl-setattributevalue ASB_textbox_ename_obj_ "panel_shape" panel_shape))
  ;             (setq panel_add-on1 (LM:vl-getattributevalue ASB_textbox_ename_obj_ "panel_add-on" ))
  ;             (setq panel_date-create1(LM:vl-setattributevalue ASB_textbox_ename_obj_ "panel_date-create" panel_date-create))
  ;             (setq panel_station1(LM:vl-setattributevalue ASB_textbox_ename_obj_ "panel_station" panel_station))
  ;             (setq panel_level (LM:vl-setattributevalue ASB_textbox_ename_obj_ "panel_level"panel_level ))
  ;             (setq panel_zone1 (LM:vl-getattributevalue ASB_textbox_ename_obj_ "panel_zone" ))
  ;           ;
  ;           ;generate_code_name
  ;             (setq sumsum_ (strcat panel_station "-" (strcase (substr panel_level 1 4 )) "-"
  ;                                   panel_matt_type1 "-" panel_name "-" "\n" 
  ;                                   (rtos panel_length1 2 0) "x" (rtos panel_width1 2 0) "mm." "-"
  ;                                   panel_color1 "-" "\n"
  ;                                   ""
  ;                                   (cond
  ;                                     ( (= (wcmatch panel_shape "*standard*") T)
  ;                                       (progn
  ;                                         "STD-SHAPE"
  ;                                       )
  ;                                     )
  ;                                     ( (= (wcmatch panel_shape "*trapezoids*") T)
  ;                                       (progn
  ;                                         "TPZ-SHAPE"
  ;                                       )
  ;                                     )
  ;                                     ( (= (wcmatch panel_shape "varies") T)
  ;                                       (progn
  ;                                         "VA"
  ;                                       )
  ;                                     )
  ;                                   )
  ;                                   "-" panel_add-on1
  ;                           ) 
  ;             )
  ;             (LM:vl-setattributevalue ASB_textbox_ename_obj_ "panel_code_name" sumsum_)
  ;           ;
            
  ;           (setq new_i 0)
  ;           (while (and 
  ;                   (= (LM:effectivename ASB_textbox_ename_obj_) "000_CKST-FAMELINE_CEILING_CODE_PANEL")
  ;                   (< new_i (- ss_pre_filter_set_xx_obj_total_panel_i 1))
  ;                 )
  ;             (vla-copy ASB_textbox_ename_obj_)
  ;             ;new_blk_entlast object
  ;               (setq new_box_ename_ (entlast)) 
  ;               (setq new_box_ename_obj (vlax-ename->vla-object new_box_ename_))
  ;             ;
  ;             (TA:move_polar_insertionpoint new_box_ename_obj "Y" (* 310 (+ new_i 1)))
  ;             (setq new_i (+ new_i 1))
  ;           )
  ;         )
  ;       )
        
  ;       (setq ss_pre_filter_set_xx_i (+ ss_pre_filter_set_xx_i 1))
  ;     )
  ;   ;
  ; )
  (defun c:PPLINE_CKST_300dode_findaddon ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "000_CKST-FAMELINE_CEILING_CODE_PANEL"))
    ;preloop_and_while
      (setq global_selction_set_ (ssadd))
      (setq ss_pre_filter_set_xx_i 0)
      (TA:interface_text_ T)
      
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))

        (if (/= (LM:vl-getattributevalue ss_pre_filter_set_xx_obj_ "panel_add-on"  ) "")
          (progn
            (setq global_selction_set_ (ssadd ss_pre_filter_set_xx_ename_ global_selction_set_))
          )
        )
        
        (TA:textscr_process_V2 "\nu finding add-on block" ss_pre_filter_set_xx_i ss_pre_filter_set_xx_)
        (setq ss_pre_filter_set_xx_i (+ ss_pre_filter_set_xx_i 1))
      )
    ;
    (command "pselect"  global_selction_set_ "" )
  )
  (defun c:PPLINE_CKST_insert_code_panel_300codemklayer ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000_CKST-FAMELINE_CEILING_CODE_PANEL"))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (vla-put-layer ss_pre_filter_set_xx_obj_ "C0x_300HK_CODE_TEXT")
        (setq ss_pre_filter_set_xx_i (+ ss_pre_filter_set_xx_i 1))
      )
    ;
  )
  (defun c:PPLINE_CKST_insert_code_panel_300selcode ()
     ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_code_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_code_filter_set_xx_ (ssget
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_code_filter_set_xx_)
            )
          ;
        )
        (setq ss_code_filter_set_xx_ ss_code_filter_set_xx_)
      )
    ;
      (setq ss_code_filter_set_xx_ (TA:EF_Filter_ss_set_ ss_code_filter_set_xx_ "000_CKST-FAMELINE_CEILING_CODE_PANEL"))
    ;
    ;preloop_and_while
      (setq att_filter_ename_ (car (nentsel "specify Object")))
      (setq att_filter_obj_ (vlax-ename->vla-object att_filter_ename_))
      (if (= (vla-get-objectname att_filter_obj_ ) "AcDbAttribute")
        (progn
          (setq att_filter_obj_tagstr_ (vla-get-tagstring att_filter_obj_))
          (setq att_filter_obj_txtstr_ (vla-get-TextString  att_filter_obj_)) 
        )
        (alert "please select attribute")
      )
      (setq ss_code_filter_set_xx_i 0)
      (setq ss_code_filter_set_xx_newss (ssadd))
      (while (and 
               (= (vla-get-objectname att_filter_obj_ ) "AcDbAttribute")
               (< ss_code_filter_set_xx_i (sslength ss_code_filter_set_xx_))
             )
        (setq ss_code_filter_set_xx_ename_ (ssname ss_code_filter_set_xx_ ss_code_filter_set_xx_i))
        (setq ss_code_filter_set_xx_obj_ (vlax-ename->vla-object  ss_code_filter_set_xx_ename_))
        (if (= (LM:vl-getattributevalue ss_code_filter_set_xx_obj_ att_filter_obj_tagstr_) att_filter_obj_txtstr_)
          (progn
            (setq ss_code_filter_set_xx_newss (ssadd  ss_code_filter_set_xx_ename_ ss_code_filter_set_xx_newss))
          )
        )
        
        (setq ss_code_filter_set_xx_i (+ ss_code_filter_set_xx_i 1))
      )
    ;
    (command "pselect"  ss_code_filter_set_xx_newss "" )
  )
  (defun c:PPLINE_CKST_insert_code_panel_ins310adc ()
    (setq panel_matt_type1_ ;Get-string by keep previous value
        (if
          (or
            (/= (setq panel_matt_type1_val (getstring (strcat "\nSpecify MATT CODE <" (if panel_matt_type1_ panel_matt_type1_ "") ">: ") ) ) "" )
          )
            (progn
              (setq panel_matt_type1_ panel_matt_type1_val)
              (setq panel_matt_type1_keep_val_ panel_matt_type1_val)
            )
          (setq panel_matt_type1_val panel_matt_type1_keep_val_)
        )
    )
    (setq color_code_ ;Get-string by keep previous value
        (if
          (or
            (/= (setq color_code_val (getstring (strcat "\nSpecify color code <" (if color_code_ color_code_ "") ">: ") ) ) "" )
          )
            (progn
              (setq color_code_ color_code_val)
              (setq color_code_keep_val_ color_code_val)
            )
          (setq color_code_val color_code_keep_val_)
        )
    )
    (setq date_create_ ;Get-string by keep previous value
        (if
          (or
            (/= (setq date_create_val (getstring (strcat "\nSpecify date_create_  <" (if date_create_ date_create_ "") ">: ") ) ) "" )
          )
            (progn
              (setq date_create_ date_create_val)
              (setq date_create_keep_val_ date_create_val)
            )
          (setq date_create_val date_create_keep_val_)
        )
    )
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_) 
      )
    ;
    (setq ss_pre_filter_set_xx_ (TA:EF_Filter_ss_set_V2_  
                                  ss_pre_filter_set_xx_
                                  (list 
                                    "000 - FAMELINE-CKST_AL.CELING_PANEL_300HK_@310mm_BOTTOM_VIEW_FOR_AS-02(1st_LOT)"
                                  )
                                )
    )
    ;preloop_and_while
      (setq ss_box_ss_ (ssadd ))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_ro_ (rad-to-deg (vla-get-rotation ss_pre_filter_set_xx_obj_) ))
        
        (setq panel_name "300HK" )
        (setq panel_length (if (or 
                                 (= (LM:effectivename ss_pre_filter_set_xx_obj_) "000 - FAMELINE-CKST_AL.CELING_PANEL_300HK_@310mm_BOTTOM_VIEW_FOR_AS-02(1st_LOT)")  
                               ) 
                             (progn 300 ) ) )
        (setq panel_width (fix (LM:roundup (LM:getdynpropvalue ss_pre_filter_set_xx_obj_ "panel_width") 5)) )
        ; (setq panel_color "XXXXXXX")
        (setq panel_shape (if 
                            (or 
                              (= (LM:effectivename ss_pre_filter_set_xx_obj_) "000 - FAMELINE-CKST_AL.CELING_PANEL_300HK_@310mm_BOTTOM_VIEW_FOR_AS-02(1st_LOT)" )
                            )
                            (progn "standard_shape")
                          )
        )
        ; (setq panel_add-on "XXXXXXX" )
        ; (setq panel_date-create (TA:cdate "-" "YYYYMMDD") )
        (setq panel_date-create date_create_ )
        
        (setq panel_station 
          (cond
            (;_case_1
              (and
                  (= (wcmatch (getvar "dwgname"  ) "*PP17*") T)
              )
              (progn
                "PP17"
              )
            )
            (;_case_2
              (and
                  (= (wcmatch (getvar "dwgname"  ) "*PP18*") T)
              )
              (progn
                "PP18"
                
              )
            )
            (;_case_3
              (and
                  (= (wcmatch (getvar "dwgname"  ) "*PP19*") T)
              )
              (progn
                "PP19"
                
              )
            )
            (;_case_4
              (and 
                (= (wcmatch (getvar "dwgname"  ) "*PP20*") T )
              )
              (progn
                "PP20"
                
              )
            )
          )
        )
        (setq panel_level 
          (cond
            (;_case_2
              (and
                  (= (wcmatch (getvar "dwgname"  ) "*PP17*") T)
                  (= (wcmatch (getvar "dwgname"  ) "*AR-4150*") T)
              )
              (progn
                "concourse_level"
              )
            )
            (;_case_3
              (and
                  (= (wcmatch (getvar "dwgname"  ) "*PP17*") T)
                  (= (wcmatch (getvar "dwgname"  ) "*AR-4180*") T)
              )
              (progn
                "platform_level"
              )
            )
            (;_case_1
              (and
                  (= (wcmatch (getvar "dwgname"  ) "*PP18*") T)
                  (= (wcmatch (getvar "dwgname"  ) "*AR-4130*") T)
              )
              (progn
                "multi_purpose_level"
              )
            )
            (;_case_2
              (and
                  (= (wcmatch (getvar "dwgname"  ) "*PP18*") T)
                  (= (wcmatch (getvar "dwgname"  ) "*AR-4150*") T)
              )
              (progn
                "concourse_level"
              )
            )
            (;_case_2
              (and
                  (= (wcmatch (getvar "dwgname"  ) "*PP18*") T)
                  (= (wcmatch (getvar "dwgname"  ) "*AR-4160*") T)
              )
              (progn
                "upper_platform_level"
              )
            )
            (;_case_2
              (and
                  (= (wcmatch (getvar "dwgname"  ) "*PP18*") T )
                  (= (wcmatch (getvar "dwgname"  ) "*AR-4180*") T )
              )
              (progn
                "lower_platform_level"
              )
            )
            (;_case_1
              (and
                  (= (wcmatch (getvar "dwgname"  ) "*PP19*") T)
                  (= (wcmatch (getvar "dwgname"  ) "*AR-4130*") T)
              )
              (progn
                "multi_purpose_level"
              )
            )
            (;_case_2
              (and
                  (= (wcmatch (getvar "dwgname"  ) "*PP19*") T)
                  (= (wcmatch (getvar "dwgname"  ) "*AR-4150*") T)
              )
              (progn
                "concourse_level"
              )
            )
            (;_case_2
              (and
                  (= (wcmatch (getvar "dwgname"  ) "*PP19*") T)
                  (= (wcmatch (getvar "dwgname"  ) "*AR-4160*") T)
              )
              (progn
                "upper_platform_level"
              )
            )
            (;_case_2
              (and
                  (= (wcmatch (getvar "dwgname"  ) "*PP19*") T)
                  (= (wcmatch (getvar "dwgname"  ) "*AR-4180*") T)
              )
              (progn
                "lower_platform_level"
              )
            )
            (;_case_1
              (and
                  (= (wcmatch (getvar "dwgname"  ) "*PP20*") T)
                  (= (wcmatch (getvar "dwgname"  ) "*AR-4130*") T)
              )
              (progn
                "multi_purpose_level"
              )
            )
            (;_case_2
              (and
                  (= (wcmatch (getvar "dwgname"  ) "*PP20*") T )
                  (= (wcmatch (getvar "dwgname"  ) "*AR-4150*")  T)
              )
              (progn
                "concourse_level"
              )
            )
            (;_case_2
              (and
                  (= (wcmatch (getvar "dwgname"  ) "*PP20*") T)
                  (= (wcmatch (getvar "dwgname"  ) "*AR-4180*") T)
              )
              (progn
                "platform_level"
              )
            )
            
          )
        )
        (if (or 
              (= (LM:effectivename ss_pre_filter_set_xx_obj_) "000 - FAMELINE-CKST_AL.CELING_PANEL_300HK_@310mm_BOTTOM_VIEW_FOR_AS-02(1st_LOT)")
            )
          (progn
            (setq ss_pre_filter_set_xx_obj_total_panel_i (/ (LM:getdynpropvalue ss_pre_filter_set_xx_obj_ "ARRAY_LENGTH") 310))
            (TA:vla-insertblock 
              "000_CKST-FAMELINE_CEILING_CODE_PANEL"
              ss_pre_filter_set_xx_obj_ins_
              1
              (cond
                ( (and 
                      (= ss_pre_filter_set_xx_obj_ro_ 0)
                      (= (LM:getdynpropvalue ss_pre_filter_set_xx_obj_ "flip state1") 1)
                    )
                  (progn
                    0
                  )
                )
                ( (and 
                      (= ss_pre_filter_set_xx_obj_ro_ 180)
                      (= (LM:getdynpropvalue ss_pre_filter_set_xx_obj_ "flip state1") 0)
                    )
                  (progn
                    0
                  )
                )
                ( (and 
                      (= ss_pre_filter_set_xx_obj_ro_ 90)
                      (= (LM:getdynpropvalue ss_pre_filter_set_xx_obj_ "flip state1") 0)
                    )
                  (progn
                    (deg-to-rad 270)
                  )
                )
                ( (and 
                      (= ss_pre_filter_set_xx_obj_ro_ 270)
                      (= (LM:getdynpropvalue ss_pre_filter_set_xx_obj_ "flip state1") 1)
                    )
                  (progn
                    (deg-to-rad 270)
                  )
                )
                ( (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 0)
                    )
                  (progn
                    (deg-to-rad (TA:ModifyRotation ss_pre_filter_set_xx_obj_ro_ 180))
                  )
                )
                ( (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 1)
                    )
                  (progn
                    (deg-to-rad (TA:ModifyRotation ss_pre_filter_set_xx_obj_ro_ 0))
                  )
                )
              )
            )
            ;new_blk_entlast object
              (setq new_box_ename (entlast))
              (setq new_box_obj (vlax-ename->vla-object new_box_ename))
              (vla-put-layer new_box_obj "C0x_300HK_CODE_TEXT")
              (vla-put-color new_box_obj 256)
              (LM:setdynpropvalue new_box_obj "distance1" 300)
              (TA:move_polar_insertionpoint new_box_obj "Y" 300)
              (if (and 
                    (= ss_pre_filter_set_xx_obj_ro_ 180)
                    (= (LM:getdynpropvalue ss_pre_filter_set_xx_obj_ "flip state1") 0 )
                  )
                (progn
                  (TA:move_polar_insertionpoint new_box_obj "x" (* (LM:getdynpropvalue ss_pre_filter_set_xx_obj_ "panel_width") -1))
                )
              )
              (if (and 
                    (= ss_pre_filter_set_xx_obj_ro_ 90)
                    (= (LM:getdynpropvalue ss_pre_filter_set_xx_obj_ "flip state1") 0 )
                  )
                (progn
                  (TA:move_polar_insertionpoint new_box_obj "x" (* (LM:getdynpropvalue ss_pre_filter_set_xx_obj_ "panel_width") -1))
                )
              )
              (if (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 0)
                    )
                (progn
                  (TA:move_polar_insertionpoint new_box_obj "x" (* (LM:getdynpropvalue ss_pre_filter_set_xx_obj_ "panel_width") -1))
                )
              )
              (setq ss_box_ss_ (ssadd  new_box_ename ss_box_ss_))
            ;
            (setq ASB_textbox_ename_obj_ (vlax-ename->vla-object new_box_ename)) 
            ;input_first_pc
              (setq panel_code_name1(LM:vl-setattributevalue ASB_textbox_ename_obj_ "panel_code_name" ""))
              (LM:vl-setattributevalue ASB_textbox_ename_obj_ "panel_matt_type" panel_matt_type1_)
              (setq panel_name1 (LM:vl-setattributevalue ASB_textbox_ename_obj_ "panel_name" panel_name))
              (setq panel_no1 (LM:vl-getattributevalue ASB_textbox_ename_obj_ "panel_no1" ))
              (setq panel_length1 (LM:vl-setattributevalue ASB_textbox_ename_obj_ "panel_length" panel_length))
              (setq panel_width1 (LM:vl-setattributevalue ASB_textbox_ename_obj_ "panel_width" panel_width))
              (setq panel_color1 (LM:vl-setattributevalue ASB_textbox_ename_obj_ "panel_color" color_code_))
              (setq panel_shape1 (LM:vl-setattributevalue ASB_textbox_ename_obj_ "panel_shape" panel_shape))
              (setq panel_add-on1 (LM:vl-getattributevalue ASB_textbox_ename_obj_ "panel_add-on" ))
              (setq panel_date-create1(LM:vl-setattributevalue ASB_textbox_ename_obj_ "panel_date-create" panel_date-create))
              (setq panel_station1(LM:vl-setattributevalue ASB_textbox_ename_obj_ "panel_station" panel_station))
              (setq panel_level (LM:vl-setattributevalue ASB_textbox_ename_obj_ "panel_level" panel_level ))
              (setq panel_zone1 (LM:vl-getattributevalue ASB_textbox_ename_obj_ "panel_zone" ))
            ;
            ;generate_code_name
              (setq sumsum_ (strcat panel_station "-" (strcase (substr panel_level 1 4 )) "-"
                                    panel_matt_type1_ "-" panel_name "-" "\n" 
                                    (rtos panel_length1 2 0) "x" (rtos panel_width1 2 0) "mm." "-"
                                    panel_color1 "-" "\n"
                                    ""
                                    (cond
                                      ( (= (wcmatch panel_shape "*standard*") T)
                                        (progn
                                          "STD-SHAPE"
                                        )
                                      )
                                      ( (= (wcmatch panel_shape "*trapezoids*") T)
                                        (progn
                                          "TPZ-SHAPE"
                                        )
                                      )
                                      ( (= (wcmatch panel_shape "varies") T)
                                        (progn
                                          "VA"
                                        )
                                      )
                                    )
                                    "-" panel_add-on1
                            ) 
              )
              (LM:vl-setattributevalue ASB_textbox_ename_obj_ "panel_code_name" sumsum_)
            ;
            (setq new_i 0)
            (while (and 
                    (= (LM:effectivename ASB_textbox_ename_obj_) "000_CKST-FAMELINE_CEILING_CODE_PANEL")
                    (< new_i (- ss_pre_filter_set_xx_obj_total_panel_i 1))
                  )
              (vla-copy ASB_textbox_ename_obj_)
              ;new_blk_entlast object
                (setq new_box_ename_ (entlast)) 
                (setq new_box_ename_obj (vlax-ename->vla-object new_box_ename_))
                (setq ss_box_ss_ (ssadd  new_box_ename_ ss_box_ss_))
              ;
              (TA:move_polar_insertionpoint new_box_ename_obj "Y" (* 310 (+ new_i 1)))
              (setq new_i (+ new_i 1))
            )
          )
        )
        
        (setq ss_pre_filter_set_xx_i (+ ss_pre_filter_set_xx_i 1))
      )
    ;
    (command "pselect"  ss_box_ss_ "" )
    
  )
  (defun c:PPLINE_CKST_insert_code_panel_ins400adc ()
    (setq panel_matt_type1_ ;Get-string by keep previous value
        (if
          (or
            (/= (setq panel_matt_type1_val (getstring (strcat "\nSpecify MATT CODE <" (if panel_matt_type1_ panel_matt_type1_ "") ">: ") ) ) "" )
          )
            (progn
              (setq panel_matt_type1_ panel_matt_type1_val)
              (setq panel_matt_type1_keep_val_ panel_matt_type1_val)
            )
          (setq panel_matt_type1_val panel_matt_type1_keep_val_)
        )
    )
    (setq color_code_ ;Get-string by keep previous value
        (if
          (or
            (/= (setq color_code_val (getstring (strcat "\nSpecify color code <" (if color_code_ color_code_ "") ">: ") ) ) "" )
          )
            (progn
              (setq color_code_ color_code_val)
              (setq color_code_keep_val_ color_code_val)
            )
          (setq color_code_val color_code_keep_val_)
        )
    )
    (setq date_create_ ;Get-string by keep previous value
        (if
          (or
            (/= (setq date_create_val (getstring (strcat "\nSpecify date_create_  <" (if date_create_ date_create_ "") ">: ") ) ) "" )
          )
            (progn
              (setq date_create_ date_create_val)
              (setq date_create_keep_val_ date_create_val)
            )
          (setq date_create_val date_create_keep_val_)
        )
    )
    
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_) 
      )
    ;
    (setq ss_pre_filter_set_xx_ (TA:EF_Filter_ss_set_V2_  
                                  ss_pre_filter_set_xx_
                                  (list 
                                    "000 - FAMELINE-CKST_AL.CELING_PANEL_300HK_@400mm_BOTTOM_VIEW_FOR_AS-02(1st_LOT)"
                                    "000 - FAMELINE-CKST_AL.CELING_PANEL_300HK_@400mm_BOTTOM_VIEW_FOR_AS-02"
                                    "000 - FAMELINE-CKST_AL.CELING_PANEL_300HK_@400mm_BOTTOM_VIEW_FOR_AS-02(varies_LOT)"
                                  )
                                )
    )
    ;preloop_and_while
      (setq ss_box_ss_ (ssadd ))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_ro_ (rad-to-deg (vla-get-rotation ss_pre_filter_set_xx_obj_) ))
        ;;;;;;;;;;;;;;;;;;;;;;;;;;;;;;;;;;; TEMP ;;;;;;;;;;;;;;;;;;;;;;;;;;;;;;;;;;;;;;;;;;;;;;;;;;;;;;;;;;;
        ;;;;;;;;;;;;;;;;;;;;;;;;;;;;;;;;;;; TEMP ;;;;;;;;;;;;;;;;;;;;;;;;;;;;;;;;;;;;;;;;;;;;;;;;;;;;;;;;;;;
        (cond
          (;_case_1
             (and
                (= (LM:effectivename ss_pre_filter_set_xx_obj_) "000 - FAMELINE-CKST_AL.CELING_PANEL_300HK_@400mm_BOTTOM_VIEW_FOR_AS-02(1st_LOT)")
             )
             (progn
               (setq date_create_ "1st_lot")
               (princ "_case_1")
             )
          )
          (;_case_1
             (and
                (= (LM:effectivename ss_pre_filter_set_xx_obj_) "000 - FAMELINE-CKST_AL.CELING_PANEL_300HK_@400mm_BOTTOM_VIEW_FOR_AS-02")
             )
             (progn
               (setq date_create_ "2nd_lot")
               (princ "_case_1")
             )
          )
          (;_case_1
             (and
                (= (LM:effectivename ss_pre_filter_set_xx_obj_) "000 - FAMELINE-CKST_AL.CELING_PANEL_300HK_@400mm_BOTTOM_VIEW_FOR_AS-02(varies_LOT)")
             )
             (progn
               (setq date_create_ "varies_lot")
               (princ "_case_1")
             )
          )
        )
        ;;;;;;;;;;;;;;;;;;;;;;;;;;;;;;;;;;; TEMP ;;;;;;;;;;;;;;;;;;;;;;;;;;;;;;;;;;;;;;;;;;;;;;;;;;;;;;;;;;;
        ;;;;;;;;;;;;;;;;;;;;;;;;;;;;;;;;;;; TEMP ;;;;;;;;;;;;;;;;;;;;;;;;;;;;;;;;;;;;;;;;;;;;;;;;;;;;;;;;;;;
        ;;;;;;;;;;;;;;;;;;;;;;;;;;;;;;;;;;; TEMP ;;;;;;;;;;;;;;;;;;;;;;;;;;;;;;;;;;;;;;;;;;;;;;;;;;;;;;;;;;;
        (setq panel_name "300HK" )
        (setq panel_length (if 
                             (or 
                               (= (LM:effectivename ss_pre_filter_set_xx_obj_) 
                                  "000 - FAMELINE-CKST_AL.CELING_PANEL_300HK_@400mm_BOTTOM_VIEW_FOR_AS-02(1st_LOT)"
                               )
                               (= (LM:effectivename ss_pre_filter_set_xx_obj_) 
                                  "000 - FAMELINE-CKST_AL.CELING_PANEL_300HK_@400mm_BOTTOM_VIEW_FOR_AS-02"
                               )
                               (= (LM:effectivename ss_pre_filter_set_xx_obj_) 
                                  "000 - FAMELINE-CKST_AL.CELING_PANEL_300HK_@400mm_BOTTOM_VIEW_FOR_AS-02(varies_LOT)"
                               )
                             )
                             (progn 300)
                           )
        )
        (setq panel_width (fix (LM:roundup (LM:getdynpropvalue ss_pre_filter_set_xx_obj_ "panel_width") 5)) )
        ; (setq panel_color "XXXXXXX")
        (setq panel_shape 
               (cond
                ( 
                  (or 
                    (= (LM:effectivename ss_pre_filter_set_xx_obj_) "000 - FAMELINE-CKST_AL.CELING_PANEL_300HK_@400mm_BOTTOM_VIEW_FOR_AS-02(1st_LOT)" )
                    (= (LM:effectivename ss_pre_filter_set_xx_obj_) "000 - FAMELINE-CKST_AL.CELING_PANEL_300HK_@400mm_BOTTOM_VIEW_FOR_AS-02" )
                  )
                  (progn "standard_shape")
                )
                ( 
                  (or 
                    (= (LM:effectivename ss_pre_filter_set_xx_obj_) "000 - FAMELINE-CKST_AL.CELING_PANEL_300HK_@400mm_BOTTOM_VIEW_FOR_AS-02(varies_LOT)" )
                  )
                  (progn "standard_shape")
                )
               )
        )
        ; (setq panel_add-on "XXXXXXX" )
        ; (setq panel_date-create (TA:cdate "-" "YYYYMMDD") )
        (setq panel_date-create date_create_ )
        
        (setq panel_station 
          (cond
            (;_case_1
              (and
                  (= (wcmatch (getvar "dwgname"  ) "*PP17*") T)
              )
              (progn
                "PP17"
              )
            )
            (;_case_2
              (and
                  (= (wcmatch (getvar "dwgname"  ) "*PP18*") T)
              )
              (progn
                "PP18"
                
              )
            )
            (;_case_3
              (and
                  (= (wcmatch (getvar "dwgname"  ) "*PP19*") T)
              )
              (progn
                "PP19"
                
              )
            )
            (;_case_4
              (and 
                (= (wcmatch (getvar "dwgname"  ) "*PP20*") T )
              )
              (progn
                "PP20"
                
              )
            )
          )
        )
        (setq panel_level 
          (cond
            (;_case_2
              (and
                  (= (wcmatch (getvar "dwgname"  ) "*PP17*") T)
                  (= (wcmatch (getvar "dwgname"  ) "*AR-4150*") T)
              )
              (progn
                "concourse_level"
              )
            )
            (;_case_3
              (and
                  (= (wcmatch (getvar "dwgname"  ) "*PP17*") T)
                  (= (wcmatch (getvar "dwgname"  ) "*AR-4180*") T)
              )
              (progn
                "platform_level"
              )
            )
            (;_case_1
              (and
                  (= (wcmatch (getvar "dwgname"  ) "*PP18*") T)
                  (= (wcmatch (getvar "dwgname"  ) "*AR-4130*") T)
              )
              (progn
                "multi_purpose_level"
              )
            )
            (;_case_2
              (and
                  (= (wcmatch (getvar "dwgname"  ) "*PP18*") T)
                  (= (wcmatch (getvar "dwgname"  ) "*AR-4150*") T)
              )
              (progn
                "concourse_level"
              )
            )
            (;_case_2
              (and
                  (= (wcmatch (getvar "dwgname"  ) "*PP18*") T)
                  (= (wcmatch (getvar "dwgname"  ) "*AR-4160*") T)
              )
              (progn
                "upper_platform_level"
              )
            )
            (;_case_2
              (and
                  (= (wcmatch (getvar "dwgname"  ) "*PP18*") T )
                  (= (wcmatch (getvar "dwgname"  ) "*AR-4180*") T )
              )
              (progn
                "lower_platform_level"
              )
            )
            (;_case_1
              (and
                  (= (wcmatch (getvar "dwgname"  ) "*PP19*") T)
                  (= (wcmatch (getvar "dwgname"  ) "*AR-4130*") T)
              )
              (progn
                "multi_purpose_level"
              )
            )
            (;_case_2
              (and
                  (= (wcmatch (getvar "dwgname"  ) "*PP19*") T)
                  (= (wcmatch (getvar "dwgname"  ) "*AR-4150*") T)
              )
              (progn
                "concourse_level"
              )
            )
            (;_case_2
              (and
                  (= (wcmatch (getvar "dwgname"  ) "*PP19*") T)
                  (= (wcmatch (getvar "dwgname"  ) "*AR-4160*") T)
              )
              (progn
                "upper_platform_level"
              )
            )
            (;_case_2
              (and
                  (= (wcmatch (getvar "dwgname"  ) "*PP19*") T)
                  (= (wcmatch (getvar "dwgname"  ) "*AR-4180*") T)
              )
              (progn
                "lower_platform_level"
              )
            )
            (;_case_1
              (and
                  (= (wcmatch (getvar "dwgname"  ) "*PP20*") T)
                  (= (wcmatch (getvar "dwgname"  ) "*AR-4130*") T)
              )
              (progn
                "multi_purpose_level"
              )
            )
            (;_case_2
              (and
                  (= (wcmatch (getvar "dwgname"  ) "*PP20*") T )
                  (= (wcmatch (getvar "dwgname"  ) "*AR-4150*")  T)
              )
              (progn
                "concourse_level"
              )
            )
            (;_case_2
              (and
                  (= (wcmatch (getvar "dwgname"  ) "*PP20*") T)
                  (= (wcmatch (getvar "dwgname"  ) "*AR-4180*") T)
              )
              (progn
                "platform_level"
              )
            )
            
          )
        )
        (if (or 
              (= (LM:effectivename ss_pre_filter_set_xx_obj_) "000 - FAMELINE-CKST_AL.CELING_PANEL_300HK_@400mm_BOTTOM_VIEW_FOR_AS-02(1st_LOT)")
              (= (LM:effectivename ss_pre_filter_set_xx_obj_) "000 - FAMELINE-CKST_AL.CELING_PANEL_300HK_@400mm_BOTTOM_VIEW_FOR_AS-02")
              (= (LM:effectivename ss_pre_filter_set_xx_obj_) "000 - FAMELINE-CKST_AL.CELING_PANEL_300HK_@400mm_BOTTOM_VIEW_FOR_AS-02(varies_LOT)")
            )
          (progn
            (setq ss_pre_filter_set_xx_obj_total_panel_i (/ (LM:getdynpropvalue ss_pre_filter_set_xx_obj_ "ARRAY_LENGTH") 400))
            (TA:vla-insertblock 
              "000_CKST-FAMELINE_CEILING_CODE_PANEL"
              ss_pre_filter_set_xx_obj_ins_
              1
              (cond
                ( (and 
                      (= ss_pre_filter_set_xx_obj_ro_ 0)
                      (= (LM:getdynpropvalue ss_pre_filter_set_xx_obj_ "flip state1") 1)
                    )
                  (progn
                    0
                  )
                )
                ( (and 
                      (= ss_pre_filter_set_xx_obj_ro_ 180)
                      (= (LM:getdynpropvalue ss_pre_filter_set_xx_obj_ "flip state1") 0)
                    )
                  (progn
                    0
                  )
                )
                ( (and 
                      (= ss_pre_filter_set_xx_obj_ro_ 90)
                      (= (LM:getdynpropvalue ss_pre_filter_set_xx_obj_ "flip state1") 0)
                    )
                  (progn
                    (deg-to-rad 270)
                  )
                )
                ( (and 
                      (= ss_pre_filter_set_xx_obj_ro_ 270)
                      (= (LM:getdynpropvalue ss_pre_filter_set_xx_obj_ "flip state1") 1)
                    )
                  (progn
                    (deg-to-rad 270)
                  )
                )
                ( (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 0)
                    )
                  (progn
                    (deg-to-rad (TA:ModifyRotation ss_pre_filter_set_xx_obj_ro_ 180))
                  )
                )
                ( (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 1)
                    )
                  (progn
                    (deg-to-rad (TA:ModifyRotation ss_pre_filter_set_xx_obj_ro_ 0))
                  )
                )
              )
            )
            ;new_blk_entlast object
              (setq new_box_ename (entlast))
              (setq new_box_obj (vlax-ename->vla-object new_box_ename))
              (vla-put-layer new_box_obj "C0x_300HK_CODE_TEXT")
              (vla-put-color new_box_obj 256)
              (LM:setdynpropvalue new_box_obj "distance1" 300)
              (TA:move_polar_insertionpoint new_box_obj "Y" 300)
              (if (and 
                    (= ss_pre_filter_set_xx_obj_ro_ 180)
                    (= (LM:getdynpropvalue ss_pre_filter_set_xx_obj_ "flip state1") 0 )
                  )
                (progn
                  (TA:move_polar_insertionpoint new_box_obj "x" (* (LM:getdynpropvalue ss_pre_filter_set_xx_obj_ "panel_width") -1))
                )
              )
              (if (and 
                    (= ss_pre_filter_set_xx_obj_ro_ 90)
                    (= (LM:getdynpropvalue ss_pre_filter_set_xx_obj_ "flip state1") 0 )
                  )
                (progn
                  (TA:move_polar_insertionpoint new_box_obj "x" (* (LM:getdynpropvalue ss_pre_filter_set_xx_obj_ "panel_width") -1))
                )
              )
              (if (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 0)
                    )
                (progn
                  (TA:move_polar_insertionpoint new_box_obj "x" (* (LM:getdynpropvalue ss_pre_filter_set_xx_obj_ "panel_width") -1))
                )
              )
              (setq ss_box_ss_ (ssadd  new_box_ename ss_box_ss_))
            ;
            (setq ASB_textbox_ename_obj_ (vlax-ename->vla-object new_box_ename)) 
            ;input_first_pc
              (setq panel_code_name1(LM:vl-setattributevalue ASB_textbox_ename_obj_ "panel_code_name" ""))
              (LM:vl-setattributevalue ASB_textbox_ename_obj_ "panel_matt_type" panel_matt_type1_)
              (setq panel_name1 (LM:vl-setattributevalue ASB_textbox_ename_obj_ "panel_name" panel_name))
              (setq panel_no1 (LM:vl-getattributevalue ASB_textbox_ename_obj_ "panel_no1" ))
              (setq panel_length1 (LM:vl-setattributevalue ASB_textbox_ename_obj_ "panel_length" panel_length))
              (setq panel_width1 (LM:vl-setattributevalue ASB_textbox_ename_obj_ "panel_width" panel_width))
              (setq panel_color1 (LM:vl-setattributevalue ASB_textbox_ename_obj_ "panel_color" color_code_))
              (setq panel_shape1 (LM:vl-setattributevalue ASB_textbox_ename_obj_ "panel_shape" panel_shape))
              (setq panel_add-on1 (LM:vl-getattributevalue ASB_textbox_ename_obj_ "panel_add-on" ))
              (setq panel_date-create1(LM:vl-setattributevalue ASB_textbox_ename_obj_ "panel_date-create" panel_date-create))
              (setq panel_station1(LM:vl-setattributevalue ASB_textbox_ename_obj_ "panel_station" panel_station))
              (setq panel_level (LM:vl-setattributevalue ASB_textbox_ename_obj_ "panel_level" panel_level ))
              (setq panel_zone1 (LM:vl-getattributevalue ASB_textbox_ename_obj_ "panel_zone" ))
            ;
            ;generate_code_name
              (setq sumsum_ (strcat panel_station "-" (strcase (substr panel_level 1 4 )) "-"
                                    panel_matt_type1_ "-" panel_name "-" "\n" 
                                    (rtos panel_length1 2 0) "x" (rtos panel_width1 2 0) "mm." "-"
                                    panel_color1 "-" "\n"
                                    ""
                                    (cond
                                      ( (= (wcmatch panel_shape "*standard*") T)
                                        (progn
                                          "STD-SHAPE"
                                        )
                                      )
                                      ( (= (wcmatch panel_shape "*trapezoids*") T)
                                        (progn
                                          "TPZ-SHAPE"
                                        )
                                      )
                                      ( (= (wcmatch panel_shape "varies") T)
                                        (progn
                                          "VA"
                                        )
                                      )
                                    )
                                    "-" panel_add-on1
                            ) 
              )
              (LM:vl-setattributevalue ASB_textbox_ename_obj_ "panel_code_name" sumsum_)
            ;
            (setq new_i 0)
            (while (and 
                    (= (LM:effectivename ASB_textbox_ename_obj_) "000_CKST-FAMELINE_CEILING_CODE_PANEL")
                    (/= new_i (fix (- ss_pre_filter_set_xx_obj_total_panel_i 1)))
                  )
              (vla-copy ASB_textbox_ename_obj_)
              ;new_blk_entlast object
                (setq new_box_ename_ (entlast)) 
                (setq new_box_ename_obj (vlax-ename->vla-object new_box_ename_))
                (setq ss_box_ss_ (ssadd  new_box_ename_ ss_box_ss_))
              ;
              (TA:move_polar_insertionpoint new_box_ename_obj "Y" (* 400 (+ new_i 1)))
              (setq new_i (+ new_i 1))
            )
          )
        )
        
        (setq ss_pre_filter_set_xx_i (+ ss_pre_filter_set_xx_i 1))
      )
    ;
    (command "pselect"  ss_box_ss_ "" )
    
  )
  (defun c:PPLINE_CKST_insert_code_panel_ins400va ()
    (setq panel_matt_type1_ ;Get-string by keep previous value
        (if
          (or
            (/= (setq panel_matt_type1_val (getstring (strcat "\nSpecify MATT CODE <" (if panel_matt_type1_ panel_matt_type1_ "") ">: ") ) ) "" )
          )
            (progn
              (setq panel_matt_type1_ panel_matt_type1_val)
              (setq panel_matt_type1_keep_val_ panel_matt_type1_val)
            )
          (setq panel_matt_type1_val panel_matt_type1_keep_val_)
        )
    )
    (setq color_code_ ;Get-string by keep previous value
        (if
          (or
            (/= (setq color_code_val (getstring (strcat "\nSpecify color code <" (if color_code_ color_code_ "") ">: ") ) ) "" )
          )
            (progn
              (setq color_code_ color_code_val)
              (setq color_code_keep_val_ color_code_val)
            )
          (setq color_code_val color_code_keep_val_)
        )
    )
    (setq date_create_ ;Get-string by keep previous value
        (if
          (or
            (/= (setq date_create_val (getstring (strcat "\nSpecify date_create_  <" (if date_create_ date_create_ "") ">: ") ) ) "" )
          )
            (progn
              (setq date_create_ date_create_val)
              (setq date_create_keep_val_ date_create_val)
            )
          (setq date_create_val date_create_keep_val_)
        )
    )
    (setq date_create_ "varies_lot")
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_) 
      )
    ;
    (setq ss_pre_filter_set_xx_ (TA:EF_Filter_ss_set_V2_  
                                  ss_pre_filter_set_xx_
                                  (list 
                                    "000 - FAMELINE-CKST_AL.CELING_PANEL_300HK_@400mm_BOTTOM_VIEW_FOR_AS-02(L-varies_LOT)"
                                  )
                                )
    )
    ;preloop_and_while
      (setq ss_box_ss_ (ssadd ))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_ro_ (rad-to-deg (vla-get-rotation ss_pre_filter_set_xx_obj_) ))
        
        (setq panel_name "300HK" )
        (setq panel_length (if 
                             (or 
                               (= (LM:effectivename ss_pre_filter_set_xx_obj_) "000 - FAMELINE-CKST_AL.CELING_PANEL_300HK_@400mm_BOTTOM_VIEW_FOR_AS-02(L-varies_LOT)" )
                               
                               
                             )
                             (LM:round (LM:getdynpropvalue ss_pre_filter_set_xx_obj_ "panel_length" ))
                           )
        )
        (setq panel_width (fix (LM:roundup (LM:getdynpropvalue ss_pre_filter_set_xx_obj_ "panel_width") 5)) )
        ; (setq panel_color "XXXXXXX")
        (setq panel_shape 
               (cond
                ( 
                  (or 
                    (= (LM:effectivename ss_pre_filter_set_xx_obj_) "000 - FAMELINE-CKST_AL.CELING_PANEL_300HK_@400mm_BOTTOM_VIEW_FOR_AS-02(L-varies_LOT)" )
                    
                  )
                  (progn "standard_varies_shape")
                )
                
               )
        )
        ; (setq panel_add-on "XXXXXXX" )
        ; (setq panel_date-create (TA:cdate "-" "YYYYMMDD") )
        (setq panel_date-create date_create_ )
        
        (setq panel_station 
          (cond
            (;_case_1
              (and
                  (= (wcmatch (getvar "dwgname"  ) "*PP17*") T)
              )
              (progn
                "PP17"
              )
            )
            (;_case_2
              (and
                  (= (wcmatch (getvar "dwgname"  ) "*PP18*") T)
              )
              (progn
                "PP18"
                
              )
            )
            (;_case_3
              (and
                  (= (wcmatch (getvar "dwgname"  ) "*PP19*") T)
              )
              (progn
                "PP19"
                
              )
            )
            (;_case_4
              (and 
                (= (wcmatch (getvar "dwgname"  ) "*PP20*") T )
              )
              (progn
                "PP20"
                
              )
            )
          )
        )
        (setq panel_level 
          (cond
            (;_case_2
              (and
                  (= (wcmatch (getvar "dwgname"  ) "*PP17*") T)
                  (= (wcmatch (getvar "dwgname"  ) "*AR-4150*") T)
              )
              (progn
                "concourse_level"
              )
            )
            (;_case_3
              (and
                  (= (wcmatch (getvar "dwgname"  ) "*PP17*") T)
                  (= (wcmatch (getvar "dwgname"  ) "*AR-4180*") T)
              )
              (progn
                "platform_level"
              )
            )
            (;_case_1
              (and
                  (= (wcmatch (getvar "dwgname"  ) "*PP18*") T)
                  (= (wcmatch (getvar "dwgname"  ) "*AR-4130*") T)
              )
              (progn
                "multi_purpose_level"
              )
            )
            (;_case_2
              (and
                  (= (wcmatch (getvar "dwgname"  ) "*PP18*") T)
                  (= (wcmatch (getvar "dwgname"  ) "*AR-4150*") T)
              )
              (progn
                "concourse_level"
              )
            )
            (;_case_2
              (and
                  (= (wcmatch (getvar "dwgname"  ) "*PP18*") T)
                  (= (wcmatch (getvar "dwgname"  ) "*AR-4160*") T)
              )
              (progn
                "upper_platform_level"
              )
            )
            (;_case_2
              (and
                  (= (wcmatch (getvar "dwgname"  ) "*PP18*") T )
                  (= (wcmatch (getvar "dwgname"  ) "*AR-4180*") T )
              )
              (progn
                "lower_platform_level"
              )
            )
            (;_case_1
              (and
                  (= (wcmatch (getvar "dwgname"  ) "*PP19*") T)
                  (= (wcmatch (getvar "dwgname"  ) "*AR-4130*") T)
              )
              (progn
                "multi_purpose_level"
              )
            )
            (;_case_2
              (and
                  (= (wcmatch (getvar "dwgname"  ) "*PP19*") T)
                  (= (wcmatch (getvar "dwgname"  ) "*AR-4150*") T)
              )
              (progn
                "concourse_level"
              )
            )
            (;_case_2
              (and
                  (= (wcmatch (getvar "dwgname"  ) "*PP19*") T)
                  (= (wcmatch (getvar "dwgname"  ) "*AR-4160*") T)
              )
              (progn
                "upper_platform_level"
              )
            )
            (;_case_2
              (and
                  (= (wcmatch (getvar "dwgname"  ) "*PP19*") T)
                  (= (wcmatch (getvar "dwgname"  ) "*AR-4180*") T)
              )
              (progn
                "lower_platform_level"
              )
            )
            (;_case_1
              (and
                  (= (wcmatch (getvar "dwgname"  ) "*PP20*") T)
                  (= (wcmatch (getvar "dwgname"  ) "*AR-4130*") T)
              )
              (progn
                "multi_purpose_level"
              )
            )
            (;_case_2
              (and
                  (= (wcmatch (getvar "dwgname"  ) "*PP20*") T )
                  (= (wcmatch (getvar "dwgname"  ) "*AR-4150*")  T)
              )
              (progn
                "concourse_level"
              )
            )
            (;_case_2
              (and
                  (= (wcmatch (getvar "dwgname"  ) "*PP20*") T)
                  (= (wcmatch (getvar "dwgname"  ) "*AR-4180*") T)
              )
              (progn
                "platform_level"
              )
            )
            
          )
        )
        (if (or 
              (= (LM:effectivename ss_pre_filter_set_xx_obj_) 
                 "000 - FAMELINE-CKST_AL.CELING_PANEL_300HK_@400mm_BOTTOM_VIEW_FOR_AS-02(L-varies_LOT)"
              )
            )
          (progn
            (TA:vla-insertblock 
              "000_CKST-FAMELINE_CEILING_CODE_PANEL"
              ss_pre_filter_set_xx_obj_ins_
              1
              (cond
                ( (and 
                      (= ss_pre_filter_set_xx_obj_ro_ 0)
                      (= (LM:getdynpropvalue ss_pre_filter_set_xx_obj_ "flip state1") 1)
                    )
                  (progn
                    0
                  )
                )
                ( (and 
                      (= ss_pre_filter_set_xx_obj_ro_ 180)
                      (= (LM:getdynpropvalue ss_pre_filter_set_xx_obj_ "flip state1") 0)
                    )
                  (progn
                    0
                  )
                )
                ( (and 
                      (= ss_pre_filter_set_xx_obj_ro_ 90)
                      (= (LM:getdynpropvalue ss_pre_filter_set_xx_obj_ "flip state1") 0)
                    )
                  (progn
                    (deg-to-rad 270)
                  )
                )
                ( (and 
                      (= ss_pre_filter_set_xx_obj_ro_ 270)
                      (= (LM:getdynpropvalue ss_pre_filter_set_xx_obj_ "flip state1") 1)
                    )
                  (progn
                    (deg-to-rad 270)
                  )
                )
                ( (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 0)
                    )
                  (progn
                    (deg-to-rad (TA:ModifyRotation ss_pre_filter_set_xx_obj_ro_ 180))
                  )
                )
                ( (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 1)
                    )
                  (progn
                    (deg-to-rad (TA:ModifyRotation ss_pre_filter_set_xx_obj_ro_ 0))
                  )
                )
              )
            )
            ;new_blk_entlast object
              (setq new_box_ename (entlast))
              (setq new_box_obj (vlax-ename->vla-object new_box_ename))
              (vla-put-layer new_box_obj "C0x_300HK_CODE_TEXT")
              (vla-put-color new_box_obj 256)
              (LM:setdynpropvalue new_box_obj "distance1" 300)
              (TA:move_polar_insertionpoint new_box_obj "Y" panel_length)
              (if (and 
                    (= ss_pre_filter_set_xx_obj_ro_ 180)
                    (= (LM:getdynpropvalue ss_pre_filter_set_xx_obj_ "flip state1") 0 )
                  )
                (progn
                  (TA:move_polar_insertionpoint new_box_obj "x" (* (LM:getdynpropvalue ss_pre_filter_set_xx_obj_ "panel_width") -1))
                )
              )
              (if (and 
                    (= ss_pre_filter_set_xx_obj_ro_ 90)
                    (= (LM:getdynpropvalue ss_pre_filter_set_xx_obj_ "flip state1") 0 )
                  )
                (progn
                  (TA:move_polar_insertionpoint new_box_obj "x" (* (LM:getdynpropvalue ss_pre_filter_set_xx_obj_ "panel_width") -1))
                )
              )
              (if (and 
                      (/= ss_pre_filter_set_xx_obj_ro_ 0)
                      (/= ss_pre_filter_set_xx_obj_ro_ 90)
                      (/= ss_pre_filter_set_xx_obj_ro_ 180)
                      (/= ss_pre_filter_set_xx_obj_ro_ 180)
                      (= (LM:getdynpropvalue ss_pre_filter_set_xx_obj_ "flip state1") 0)
                    )
                (progn
                  (TA:move_polar_insertionpoint new_box_obj "x" (* (LM:getdynpropvalue ss_pre_filter_set_xx_obj_ "panel_width") -1))
                )
              )
              (setq ss_box_ss_ (ssadd  new_box_ename ss_box_ss_))
            ;
            (setq ASB_textbox_ename_obj_ (vlax-ename->vla-object new_box_ename)) 
            ;input_first_pc
              (setq panel_code_name1(LM:vl-setattributevalue ASB_textbox_ename_obj_ "panel_code_name" ""))
              (LM:vl-setattributevalue ASB_textbox_ename_obj_ "panel_matt_type" panel_matt_type1_)
              (setq panel_name1 (LM:vl-setattributevalue ASB_textbox_ename_obj_ "panel_name" panel_name))
              (setq panel_no1 (LM:vl-getattributevalue ASB_textbox_ename_obj_ "panel_no1" ))
              (setq panel_length1 (LM:vl-setattributevalue ASB_textbox_ename_obj_ "panel_length" panel_length))
              (setq panel_width1 (LM:vl-setattributevalue ASB_textbox_ename_obj_ "panel_width" panel_width))
              (setq panel_color1 (LM:vl-setattributevalue ASB_textbox_ename_obj_ "panel_color" color_code_))
              (setq panel_shape1 (LM:vl-setattributevalue ASB_textbox_ename_obj_ "panel_shape" panel_shape))
              (setq panel_add-on1 (LM:vl-getattributevalue ASB_textbox_ename_obj_ "panel_add-on" ))
              (setq panel_date-create1(LM:vl-setattributevalue ASB_textbox_ename_obj_ "panel_date-create" panel_date-create))
              (setq panel_station1(LM:vl-setattributevalue ASB_textbox_ename_obj_ "panel_station" panel_station))
              (setq panel_level (LM:vl-setattributevalue ASB_textbox_ename_obj_ "panel_level" panel_level ))
              (setq panel_zone1 (LM:vl-getattributevalue ASB_textbox_ename_obj_ "panel_zone" ))
            ;
            ;generate_code_name
              (setq sumsum_ (strcat panel_station "-" (strcase (substr panel_level 1 4 )) "-"
                                    panel_matt_type1_ "-" panel_name "-" "\n" 
                                    (rtos panel_length1 2 0) "x" (rtos panel_width1 2 0) "mm." "-"
                                    panel_color1 "-" "\n"
                                    ""
                                    (cond
                                      ( (= (wcmatch panel_shape "*standard*") T)
                                        (progn
                                          "STD-SHAPE"
                                        )
                                      )
                                      ( (= (wcmatch panel_shape "*trapezoids*") T)
                                        (progn
                                          "TPZ-SHAPE"
                                        )
                                      )
                                      ( (= (wcmatch panel_shape "varies") T)
                                        (progn
                                          "VA"
                                        )
                                      )
                                    )
                                    "-" panel_add-on1
                            ) 
              )
              (LM:vl-setattributevalue ASB_textbox_ename_obj_ "panel_code_name" sumsum_)
            ;
            (setq new_i 0)
            ; (while (and 
            ;         (= (LM:effectivename ASB_textbox_ename_obj_) "000_CKST-FAMELINE_CEILING_CODE_PANEL")
            ;         (/= new_i (fix (- ss_pre_filter_set_xx_obj_total_panel_i 1)))
            ;       )
            ;   (vla-copy ASB_textbox_ename_obj_)
            ;   ;new_blk_entlast object
            ;     (setq new_box_ename_ (entlast)) 
            ;     (setq new_box_ename_obj (vlax-ename->vla-object new_box_ename_))
            ;     (setq ss_box_ss_ (ssadd  new_box_ename_ ss_box_ss_))
            ;   ;
            ;   (TA:move_polar_insertionpoint new_box_ename_obj "Y" (* 400 (+ new_i 1)))
            ;   (setq new_i (+ new_i 1))
            ; )
          )
        )
        
        (setq ss_pre_filter_set_xx_i (+ ss_pre_filter_set_xx_i 1))
      )
    ;
    (command "pselect"  ss_box_ss_ "" )
    
  )
  
  (defun c:PPLINE_CKST_insert_code_panel_ins360adc ()
    (setq panel_matt_type1_ ;Get-string by keep previous value
        (if
          (or
            (/= (setq panel_matt_type1_val (getstring (strcat "\nSpecify MATT CODE <" (if panel_matt_type1_ panel_matt_type1_ "") ">: ") ) ) "" )
          )
            (progn
              (setq panel_matt_type1_ panel_matt_type1_val)
              (setq panel_matt_type1_keep_val_ panel_matt_type1_val)
            )
          (setq panel_matt_type1_val panel_matt_type1_keep_val_)
        )
    )
    (setq color_code_ ;Get-string by keep previous value
        (if
          (or
            (/= (setq color_code_val (getstring (strcat "\nSpecify color code <" (if color_code_ color_code_ "") ">: ") ) ) "" )
          )
            (progn
              (setq color_code_ color_code_val)
              (setq color_code_keep_val_ color_code_val)
            )
          (setq color_code_val color_code_keep_val_)
        )
    )
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_) 
      )
    ;
    (setq ss_pre_filter_set_xx_ (TA:EF_Filter_ss_set_V2_  
                                  ss_pre_filter_set_xx_
                                  (list 
                                    "000 - FAMELINE-CKST_AL.CELING_PANEL_360HK_@372mm_BOTTOM_VIEW_FOR_AS-02(1st_LOT)"
                                  )
                                )
    )
    ;preloop_and_while
      (setq ss_box_ss_ (ssadd ))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_ro_ (rad-to-deg (vla-get-rotation ss_pre_filter_set_xx_obj_) ))
        
        (setq panel_name "300HK" )
        (setq panel_length (if (or 
                                 (= (LM:effectivename ss_pre_filter_set_xx_obj_) "000 - FAMELINE-CKST_AL.CELING_PANEL_360HK_@372mm_BOTTOM_VIEW_FOR_AS-02(1st_LOT)")  
                               ) 
                             (progn 300 ) ) )
        (setq panel_width (fix (LM:roundup (LM:getdynpropvalue ss_pre_filter_set_xx_obj_ "panel_width") 5)) )
        ; (setq panel_color "XXXXXXX")
        (setq panel_shape (if (or 
                                (= (LM:effectivename ss_pre_filter_set_xx_obj_) "000 - FAMELINE-CKST_AL.CELING_PANEL_360HK_@372mm_BOTTOM_VIEW_FOR_AS-02(1st_LOT)")  
                              ) (progn "standard_shape" ) ) )
        ; (setq panel_add-on "XXXXXXX" )
        (setq panel_date-create (TA:cdate "-" "YYYYMMDD") )
        (setq panel_station 
          (cond
            (;_case_1
              (and
                  (= (wcmatch (getvar "dwgname"  ) "*PP17*") T)
              )
              (progn
                "PP17"
              )
            )
            (;_case_2
              (and
                  (= (wcmatch (getvar "dwgname"  ) "*PP18*") T )
              )
              (progn
                "PP18"
                
              )
            )
            (;_case_3
              (and
                  (= (wcmatch (getvar "dwgname"  ) "*PP19*") T)
              )
              (progn
                "PP19"
                
              )
            )
            (;_case_4
              (and 
                (= (wcmatch (getvar "dwgname"  ) "*PP20*") T )
              )
              (progn
                "PP20"
                
              )
            )
          )
        )
        (setq panel_level 
          (cond
            (;_case_2
              (and
                  (= (wcmatch (getvar "dwgname"  ) "*PP17*") T)
                  (= (wcmatch (getvar "dwgname"  ) "*AR-4150*") T)
              )
              (progn
                "concourse_level"
              )
            )
            (;_case_3
              (and
                  (= (wcmatch (getvar "dwgname"  ) "*PP17*") T)
                  (= (wcmatch (getvar "dwgname"  ) "*AR-4180*") T)
              )
              (progn
                "platform_level"
              )
            )
            (;_case_1
              (and
                  (= (wcmatch (getvar "dwgname"  ) "*PP18*") T)
                  (= (wcmatch (getvar "dwgname"  ) "*AR-4130*") T)
              )
              (progn
                "multi_purpose_level"
              )
            )
            (;_case_2
              (and
                  (= (wcmatch (getvar "dwgname"  ) "*PP18*") T)
                  (= (wcmatch (getvar "dwgname"  ) "*AR-4150*") T)
              )
              (progn
                "concourse_level"
              )
            )
            (;_case_2
              (and
                  (= (wcmatch (getvar "dwgname"  ) "*PP18*") T)
                  (= (wcmatch (getvar "dwgname"  ) "*AR-4160*") T)
              )
              (progn
                "upper_platform_level"
              )
            )
            (;_case_2
              (and
                  (= (wcmatch (getvar "dwgname"  ) "*PP18*") T )
                  (= (wcmatch (getvar "dwgname"  ) "*AR-4180*")  )
              )
              (progn
                "lower_platform_level"
              )
            )
            (;_case_1
              (and
                  (= (wcmatch (getvar "dwgname"  ) "*PP19*") T)
                  (= (wcmatch (getvar "dwgname"  ) "*AR-4130*") T)
              )
              (progn
                "multi_purpose_level"
              )
            )
            (;_case_2
              (and
                  (= (wcmatch (getvar "dwgname"  ) "*PP19*") T)
                  (= (wcmatch (getvar "dwgname"  ) "*AR-4150*") T)
              )
              (progn
                "concourse_level"
              )
            )
            (;_case_2
              (and
                  (= (wcmatch (getvar "dwgname"  ) "*PP19*") T)
                  (= (wcmatch (getvar "dwgname"  ) "*AR-4160*") T)
              )
              (progn
                "upper_platform_level"
              )
            )
            (;_case_2
              (and
                  (= (wcmatch (getvar "dwgname"  ) "*PP19*") T)
                  (= (wcmatch (getvar "dwgname"  ) "*AR-4180*") T)
              )
              (progn
                "lower_platform_level"
              )
            )
            (;_case_1
              (and
                  (= (wcmatch (getvar "dwgname"  ) "*PP20*") T)
                  (= (wcmatch (getvar "dwgname"  ) "*AR-4130*") T)
              )
              (progn
                "multi_purpose_level"
              )
            )
            (;_case_2
              (and
                  (= (wcmatch (getvar "dwgname"  ) "*PP20*") T )
                  (= (wcmatch (getvar "dwgname"  ) "*AR-4150*")  T)
              )
              (progn
                "concourse_level"
              )
            )
            (;_case_2
              (and
                  (= (wcmatch (getvar "dwgname"  ) "*PP20*") T)
                  (= (wcmatch (getvar "dwgname"  ) "*AR-4180*") T)
              )
              (progn
                "platform_level"
              )
            )
            
          )
        )
        (if (or 
              (= (LM:effectivename ss_pre_filter_set_xx_obj_) "000 - FAMELINE-CKST_AL.CELING_PANEL_360HK_@372mm_BOTTOM_VIEW_FOR_AS-02(1st_LOT)")
            )
          (progn
            (setq ss_pre_filter_set_xx_obj_total_panel_i (/ (LM:getdynpropvalue ss_pre_filter_set_xx_obj_ "ARRAY_LENGTH") 400))
            (TA:vla-insertblock 
              "000_CKST-FAMELINE_CEILING_CODE_PANEL"
              ss_pre_filter_set_xx_obj_ins_
              1
              (cond
                ( (and 
                      (= ss_pre_filter_set_xx_obj_ro_ 0)
                      ; (= (LM:getdynpropvalue ss_pre_filter_set_xx_obj_ "flip state1") 0)
                    )
                  (progn
                    0
                  )
                )
                ( (and 
                      (= ss_pre_filter_set_xx_obj_ro_ 180)
                      ; (= (LM:getdynpropvalue ss_pre_filter_set_xx_obj_ "flip state1") 0)
                    )
                  (progn
                    0
                  )
                )
                ( (and 
                      (= ss_pre_filter_set_xx_obj_ro_ 90)
                      ; (= (LM:getdynpropvalue ss_pre_filter_set_xx_obj_ "flip state1") 0)
                    )
                  (progn
                    (deg-to-rad 270)
                  )
                )
                ( (and 
                      (/= ss_pre_filter_set_xx_obj_ro_ 90)
                      (/= ss_pre_filter_set_xx_obj_ro_ 180)
                      (/= ss_pre_filter_set_xx_obj_ro_ 180)
                      ; (= (LM:getdynpropvalue ss_pre_filter_set_xx_obj_ "flip state1") 0)
                    )
                  (progn
                    (deg-to-rad (TA:ModifyRotation ss_pre_filter_set_xx_obj_ro_ 180))
                  )
                )
                
              )
            )
            ;new_blk_entlast object
              (setq new_box_ename (entlast))
              (setq new_box_obj (vlax-ename->vla-object new_box_ename))
              (LM:setdynpropvalue new_box_obj "distance1" 300)
              (TA:move_polar_insertionpoint new_box_obj "Y" 360)
              (setq ss_box_ss_ (ssadd  new_box_ename ss_box_ss_))
            ;
            (setq ASB_textbox_ename_obj_ (vlax-ename->vla-object new_box_ename)) 
            ;input_first_pc
              (setq panel_code_name1(LM:vl-setattributevalue ASB_textbox_ename_obj_ "panel_code_name" ""))
              (LM:vl-setattributevalue ASB_textbox_ename_obj_ "panel_matt_type" panel_matt_type1_)
              (setq panel_name1 (LM:vl-setattributevalue ASB_textbox_ename_obj_ "panel_name" panel_name))
              (setq panel_no1 (LM:vl-getattributevalue ASB_textbox_ename_obj_ "panel_no1" ))
              (setq panel_length1 (LM:vl-setattributevalue ASB_textbox_ename_obj_ "panel_length" panel_length))
              (setq panel_width1 (LM:vl-setattributevalue ASB_textbox_ename_obj_ "panel_width" panel_width))
              (setq panel_color1 (LM:vl-setattributevalue ASB_textbox_ename_obj_ "panel_color" color_code_))
              (setq panel_shape1 (LM:vl-setattributevalue ASB_textbox_ename_obj_ "panel_shape" panel_shape))
              (setq panel_add-on1 (LM:vl-getattributevalue ASB_textbox_ename_obj_ "panel_add-on" ))
              (setq panel_date-create1(LM:vl-setattributevalue ASB_textbox_ename_obj_ "panel_date-create" panel_date-create))
              (setq panel_station1(LM:vl-setattributevalue ASB_textbox_ename_obj_ "panel_station" panel_station))
              (setq panel_level (LM:vl-setattributevalue ASB_textbox_ename_obj_ "panel_level"panel_level ))
              (setq panel_zone1 (LM:vl-getattributevalue ASB_textbox_ename_obj_ "panel_zone" ))
            ;
            ;generate_code_name
              (setq sumsum_ (strcat panel_station "-" (strcase (substr panel_level 1 4 )) "-"
                                    panel_matt_type1_ "-" panel_name "-" "\n" 
                                    (rtos panel_length1 2 0) "x" (rtos panel_width1 2 0) "mm." "-"
                                    panel_color1 "-" "\n"
                                    ""
                                    (cond
                                      ( (= (wcmatch panel_shape "*standard*") T)
                                        (progn
                                          "STD-SHAPE"
                                        )
                                      )
                                      ( (= (wcmatch panel_shape "*trapezoids*") T)
                                        (progn
                                          "TPZ-SHAPE"
                                        )
                                      )
                                      ( (= (wcmatch panel_shape "varies") T)
                                        (progn
                                          "VA"
                                        )
                                      )
                                    )
                                    "-" panel_add-on1
                            ) 
              )
              (LM:vl-setattributevalue ASB_textbox_ename_obj_ "panel_code_name" sumsum_)
            ;
            
            (setq new_i 0)
            (while (and 
                    (= (LM:effectivename ASB_textbox_ename_obj_) "000_CKST-FAMELINE_CEILING_CODE_PANEL")
                    (< new_i (- ss_pre_filter_set_xx_obj_total_panel_i 1))
                  )
              (vla-copy ASB_textbox_ename_obj_)
              ;new_blk_entlast object
                (setq new_box_ename_ (entlast)) 
                (setq new_box_ename_obj (vlax-ename->vla-object new_box_ename_))
                (setq ss_box_ss_ (ssadd  new_box_ename_ ss_box_ss_))
              ;
              (TA:move_polar_insertionpoint new_box_ename_obj "Y" (* 372 (+ new_i 1)))
              (setq new_i (+ new_i 1))
            )
          )
        )
        
        (setq ss_pre_filter_set_xx_i (+ ss_pre_filter_set_xx_i 1))
      )
    ;
    (command "pselect"  ss_box_ss_ "" )
    
  )
  (defun c:PPLINE_CKST_ADD_CODE_TO_PANEL_300adc ()
    (setq ASB_ename_ (car (entsel "specify Object")))
    (setq ASB_obj_ (vlax-ename->vla-object ASB_ename_))
    ;get data panel 
      ; (setq panel_matt_type "C0x" )
      (setq panel_name "300HK" )
      (setq panel_length (if (or (= (LM:effectivename ASB_obj_) "000 - FAMELINE-CKST_AL.CELING_PANEL_300HK_@400mm_BOTTOM_VIEW_FOR_AS-02") (= (LM:effectivename ASB_obj_) "000 - FAMELINE-CKST_AL.CELING_PANEL_300HK_@400mm_BOTTOM_VIEW_FOR_AS-02(1st_LOT)") ) (progn 300 ) ) )
      (setq panel_width (fix (LM:getdynpropvalue ASB_obj_ "panel_width")) )
      ; (setq panel_color "XXXXXXX")
      (setq panel_shape (if (or (= (LM:effectivename ASB_obj_) "000 - FAMELINE-CKST_AL.CELING_PANEL_300HK_@400mm_BOTTOM_VIEW_FOR_AS-02") (= (LM:effectivename ASB_obj_) "000 - FAMELINE-CKST_AL.CELING_PANEL_300HK_@400mm_BOTTOM_VIEW_FOR_AS-02(1st_LOT)") ) (progn "standard_shape" ) ) )
      ; (setq panel_add-on "XXXXXXX" )
      (setq panel_date-create (TA:cdate "-" "YYYYMMDD") )
      (setq panel_station 
        (cond
          (;_case_1
            (and
                (= (wcmatch (getvar "dwgname"  ) "*PP17*") )
            )
            (progn
              "PP17"
              
            )
          )
          (;_case_2
            (and
                (= (wcmatch (getvar "dwgname"  ) "*PP18*") )
            )
            (progn
              "PP18"
              
            )
          )
          (;_case_3
            (and
                (= (wcmatch (getvar "dwgname"  ) "*PP19*") )
            )
            (progn
              "PP19"
              
            )
          )
          (;_case_4
            (and 
              (= (wcmatch (getvar "dwgname"  ) "*PP20*") )
            )
            (progn
              "PP20"
              
            )
          )
        )
      )
      (setq panel_level 
        (cond
          (;_case_2
            (and
                (= (wcmatch (getvar "dwgname"  ) "*PP17*") )
                (= (wcmatch (getvar "dwgname"  ) "AR-4150*") )
            )
            (progn
              "concourse_level"
            )
          )
          (;_case_3
            (and
                (= (wcmatch (getvar "dwgname"  ) "*PP17*") )
                (= (wcmatch (getvar "dwgname"  ) "AR-4180*") )
            )
            (progn
              "platform_level"
            )
          )
          (;_case_1
            (and
                (= (wcmatch (getvar "dwgname"  ) "*PP18*") )
                (= (wcmatch (getvar "dwgname"  ) "AR-4130*") )
            )
            (progn
              "multi_purpose_level"
            )
          )
          (;_case_2
            (and
                (= (wcmatch (getvar "dwgname"  ) "*PP18*") )
                (= (wcmatch (getvar "dwgname"  ) "AR-4150*") )
            )
            (progn
              "concourse_level"
            )
          )
          (;_case_2
            (and
                (= (wcmatch (getvar "dwgname"  ) "*PP18*") )
                (= (wcmatch (getvar "dwgname"  ) "AR-4160*") )
            )
            (progn
              "upper_platform_level"
            )
          )
          (;_case_2
            (and
                (= (wcmatch (getvar "dwgname"  ) "*PP18*") )
                (= (wcmatch (getvar "dwgname"  ) "AR-4180*") )
            )
            (progn
              "lower_platform_level"
            )
          )
          (;_case_1
            (and
                (= (wcmatch (getvar "dwgname"  ) "*PP19*") )
                (= (wcmatch (getvar "dwgname"  ) "AR-4130*") )
            )
            (progn
              "multi_purpose_level"
            )
          )
          (;_case_2
            (and
                (= (wcmatch (getvar "dwgname"  ) "*PP19*") )
                (= (wcmatch (getvar "dwgname"  ) "AR-4150*") )
            )
            (progn
              "concourse_level"
            )
          )
          (;_case_2
            (and
                (= (wcmatch (getvar "dwgname"  ) "*PP19*") )
                (= (wcmatch (getvar "dwgname"  ) "AR-4160*") )
            )
            (progn
              "upper_platform_level"
            )
          )
          (;_case_2
            (and
                (= (wcmatch (getvar "dwgname"  ) "*PP19*") )
                (= (wcmatch (getvar "dwgname"  ) "AR-4180*") )
            )
            (progn
              "lower_platform_level"
            )
          )
          (;_case_1
            (and
                (= (wcmatch (getvar "dwgname"  ) "*PP20*") )
                (= (wcmatch (getvar "dwgname"  ) "AR-4130*") )
            )
            (progn
              "multi_purpose_level"
            )
          )
          (;_case_2
            (and
                (= (wcmatch (getvar "dwgname"  ) "*PP20*") )
                (= (wcmatch (getvar "dwgname"  ) "AR-4150*") )
            )
            (progn
              "concourse_level"
            )
          )
          (;_case_2
            (and
                (= (wcmatch (getvar "dwgname"  ) "*PP20*") )
                (= (wcmatch (getvar "dwgname"  ) "AR-4180*") )
            )
            (progn
              "platform_level"
              (princ "_case_2")
            )
          )
          
        )
      )
      ; (setq panel_zone "")
    ;

    (if (or 
          (= (LM:effectivename ASB_obj_) "000 - FAMELINE-CKST_AL.CELING_PANEL_300HK_@400mm_BOTTOM_VIEW_FOR_AS-02")
          (= (LM:effectivename ASB_obj_) "000 - FAMELINE-CKST_AL.CELING_PANEL_300HK_@400mm_BOTTOM_VIEW_FOR_AS-02(1st_LOT)")
        )
      (progn
        (setq ASB_obj_total_panel_i (/ (LM:getdynpropvalue ASB_obj_ "ARRAY_LENGTH") 400))
        (setq ASB_textbox_ename_ (car (entsel "specify ATT DATA BOX "))) 
        (setq ASB_textbox_ename_obj_ (vlax-ename->vla-object ASB_textbox_ename_))
        ;input_first_pc
          (setq panel_code_name1(LM:vl-setattributevalue ASB_textbox_ename_obj_ "panel_code_name" ""))
          (setq panel_matt_type1 (LM:vl-getattributevalue ASB_textbox_ename_obj_ "panel_matt_type" ))
          (setq panel_name1 (LM:vl-setattributevalue ASB_textbox_ename_obj_ "panel_name" panel_name))
          (setq panel_no1 (LM:vl-getattributevalue ASB_textbox_ename_obj_ "panel_no1" ))
          (setq panel_length1 (LM:vl-setattributevalue ASB_textbox_ename_obj_ "panel_length" panel_length))
          (setq panel_width1 (LM:vl-setattributevalue ASB_textbox_ename_obj_ "panel_width" panel_width))
          (setq panel_color1 (LM:vl-getattributevalue ASB_textbox_ename_obj_ "panel_color" ))
          (setq panel_shape1 (LM:vl-setattributevalue ASB_textbox_ename_obj_ "panel_shape" panel_shape))
          (setq panel_add-on1 (LM:vl-getattributevalue ASB_textbox_ename_obj_ "panel_add-on" ))
          (setq panel_date-create1(LM:vl-setattributevalue ASB_textbox_ename_obj_ "panel_date-create" panel_date-create))
          (setq panel_station1(LM:vl-setattributevalue ASB_textbox_ename_obj_ "panel_station" panel_station))
          (setq panel_level (LM:vl-setattributevalue ASB_textbox_ename_obj_ "panel_level"panel_level ))
          (setq panel_zone1 (LM:vl-getattributevalue ASB_textbox_ename_obj_ "panel_zone" ))
        ;
        ;generate_code_name
          (setq sumsum_ (strcat panel_station "-" (strcase (substr panel_level 1 4 )) "-"
                                panel_matt_type "-" panel_name "-" "\n" 
                                (rtos panel_length 2 0) "x" (rtos panel_width 2 0) "mm." "-"
                                panel_color1 "-" "\n"
                                ""
                                (cond
                                  ( (= (wcmatch panel_shape "*standard*") T)
                                    (progn
                                      "STD-SHAPE"
                                    )
                                  )
                                  ( (= (wcmatch panel_shape "*trapezoids*") T)
                                    (progn
                                      "TPZ-SHAPE"
                                    )
                                  )
                                  ( (= (wcmatch panel_shape "varies") T)
                                    (progn
                                      "VA"
                                    )
                                  )
                                )
                                "-" panel_add-on1
                        ) 
          )
        
        
        
        
        
          (LM:vl-setattributevalue ASB_textbox_ename_obj_ "panel_code_name" sumsum_)
        ;
        
        (setq new_i 0)
        (while (and 
                 (= (LM:effectivename ASB_textbox_ename_obj_) "000_CKST-FAMELINE_CEILING_CODE_PANEL")
                 (< new_i (- ASB_obj_total_panel_i 1))
               )
          (vla-copy ASB_textbox_ename_obj_)
          ;new_blk_entlast object
            (setq new_box_ename_ (entlast))
            (setq new_box_ename_obj (vlax-ename->vla-object new_box_ename_))
          ;
          (TA:move_polar_insertionpoint new_box_ename_obj "Y" (* 400 (+ new_i 1)))
          (setq new_i (+ new_i 1))
        )
      )
    )
    
  )
  (defun c:PPLINE_CKST_ADD_CODE_TO_PANEL_310adc ()
    (setq ASB_ename_ (car (entsel "specify Object")))
    (setq ASB_obj_ (vlax-ename->vla-object ASB_ename_))
    ;get data panel 
      ; (setq panel_matt_type "C0x" )
      (setq panel_name "300HK" )
      (setq panel_length (if (or (= (LM:effectivename ASB_obj_) "000 - FAMELINE-CKST_AL.CELING_PANEL_300HK_@310mm_BOTTOM_VIEW_FOR_AS-02(1st_LOT)")  ) (progn 300 ) ) )
      (setq panel_width (fix (LM:getdynpropvalue ASB_obj_ "panel_width")) )
      ; (setq panel_color "XXXXXXX")
      (setq panel_shape (if (or (= (LM:effectivename ASB_obj_) "000 - FAMELINE-CKST_AL.CELING_PANEL_300HK_@310mm_BOTTOM_VIEW_FOR_AS-02(1st_LOT)")  ) (progn "standard_shape" ) ) )
      ; (setq panel_add-on "XXXXXXX" )
      (setq panel_date-create (TA:cdate "-" "YYYYMMDD") )
      (setq panel_station 
        (cond
          (;_case_1
            (and
                (= (wcmatch (getvar "dwgname"  ) "*PP17*") )
            )
            (progn
              "PP17"
              
            )
          )
          (;_case_2
            (and
                (= (wcmatch (getvar "dwgname"  ) "*PP18*") )
            )
            (progn
              "PP18"
              
            )
          )
          (;_case_3
            (and
                (= (wcmatch (getvar "dwgname"  ) "*PP19*") )
            )
            (progn
              "PP19"
              
            )
          )
          (;_case_4
            (and 
              (= (wcmatch (getvar "dwgname"  ) "*PP20*") )
            )
            (progn
              "PP20"
              
            )
          )
        )
      )
      (setq panel_level 
        (cond
          (;_case_2
            (and
                (= (wcmatch (getvar "dwgname"  ) "*PP17*") )
                (= (wcmatch (getvar "dwgname"  ) "AR-4150*") )
            )
            (progn
              "concourse_level"
            )
          )
          (;_case_3
            (and
                (= (wcmatch (getvar "dwgname"  ) "*PP17*") )
                (= (wcmatch (getvar "dwgname"  ) "AR-4180*") )
            )
            (progn
              "platform_level"
            )
          )
          (;_case_1
            (and
                (= (wcmatch (getvar "dwgname"  ) "*PP18*") )
                (= (wcmatch (getvar "dwgname"  ) "AR-4130*") )
            )
            (progn
              "multi_purpose_level"
            )
          )
          (;_case_2
            (and
                (= (wcmatch (getvar "dwgname"  ) "*PP18*") )
                (= (wcmatch (getvar "dwgname"  ) "AR-4150*") )
            )
            (progn
              "concourse_level"
            )
          )
          (;_case_2
            (and
                (= (wcmatch (getvar "dwgname"  ) "*PP18*") )
                (= (wcmatch (getvar "dwgname"  ) "AR-4160*") )
            )
            (progn
              "upper_platform_level"
            )
          )
          (;_case_2
            (and
                (= (wcmatch (getvar "dwgname"  ) "*PP18*") )
                (= (wcmatch (getvar "dwgname"  ) "AR-4180*") )
            )
            (progn
              "lower_platform_level"
            )
          )
          (;_case_1
            (and
                (= (wcmatch (getvar "dwgname"  ) "*PP19*") )
                (= (wcmatch (getvar "dwgname"  ) "AR-4130*") )
            )
            (progn
              "multi_purpose_level"
            )
          )
          (;_case_2
            (and
                (= (wcmatch (getvar "dwgname"  ) "*PP19*") )
                (= (wcmatch (getvar "dwgname"  ) "AR-4150*") )
            )
            (progn
              "concourse_level"
            )
          )
          (;_case_2
            (and
                (= (wcmatch (getvar "dwgname"  ) "*PP19*") )
                (= (wcmatch (getvar "dwgname"  ) "AR-4160*") )
            )
            (progn
              "upper_platform_level"
            )
          )
          (;_case_2
            (and
                (= (wcmatch (getvar "dwgname"  ) "*PP19*") )
                (= (wcmatch (getvar "dwgname"  ) "AR-4180*") )
            )
            (progn
              "lower_platform_level"
            )
          )
          (;_case_1
            (and
                (= (wcmatch (getvar "dwgname"  ) "*PP20*") )
                (= (wcmatch (getvar "dwgname"  ) "AR-4130*") )
            )
            (progn
              "multi_purpose_level"
            )
          )
          (;_case_2
            (and
                (= (wcmatch (getvar "dwgname"  ) "*PP20*") )
                (= (wcmatch (getvar "dwgname"  ) "AR-4150*") )
            )
            (progn
              "concourse_level"
            )
          )
          (;_case_2
            (and
                (= (wcmatch (getvar "dwgname"  ) "*PP20*") )
                (= (wcmatch (getvar "dwgname"  ) "AR-4180*") )
            )
            (progn
              "platform_level"
              (princ "_case_2")
            )
          )
          
        )
      )
      ; (setq panel_zone "")
    ;

    (if (or 
          (= (LM:effectivename ASB_obj_) "000 - FAMELINE-CKST_AL.CELING_PANEL_300HK_@310mm_BOTTOM_VIEW_FOR_AS-02(1st_LOT)")
          
        )
      (progn
        (setq ASB_obj_total_panel_i (/ (LM:getdynpropvalue ASB_obj_ "ARRAY_LENGTH") 310))
        (setq ASB_textbox_ename_ (car (entsel "specify ATT DATA BOX "))) 
        (setq ASB_textbox_ename_obj_ (vlax-ename->vla-object ASB_textbox_ename_))
        ;input_first_pc
          (setq panel_code_name1(LM:vl-setattributevalue ASB_textbox_ename_obj_ "panel_code_name" ""))
          (setq panel_matt_type1 (LM:vl-getattributevalue ASB_textbox_ename_obj_ "panel_matt_type" ))
          (setq panel_name1 (LM:vl-setattributevalue ASB_textbox_ename_obj_ "panel_name" panel_name))
          (setq panel_no1 (LM:vl-getattributevalue ASB_textbox_ename_obj_ "panel_no1" ))
          (setq panel_length1 (LM:vl-setattributevalue ASB_textbox_ename_obj_ "panel_length" panel_length))
          (setq panel_width1 (LM:vl-setattributevalue ASB_textbox_ename_obj_ "panel_width" panel_width))
          (setq panel_color1 (LM:vl-getattributevalue ASB_textbox_ename_obj_ "panel_color" ))
          (setq panel_shape1 (LM:vl-setattributevalue ASB_textbox_ename_obj_ "panel_shape" panel_shape))
          (setq panel_add-on1 (LM:vl-getattributevalue ASB_textbox_ename_obj_ "panel_add-on" ))
          (setq panel_date-create1(LM:vl-setattributevalue ASB_textbox_ename_obj_ "panel_date-create" panel_date-create))
          (setq panel_station1(LM:vl-setattributevalue ASB_textbox_ename_obj_ "panel_station" panel_station))
          (setq panel_level (LM:vl-setattributevalue ASB_textbox_ename_obj_ "panel_level"panel_level ))
          (setq panel_zone1 (LM:vl-getattributevalue ASB_textbox_ename_obj_ "panel_zone" ))
        ;
        ;generate_code_name
          (setq sumsum_ (strcat panel_station "-" (strcase (substr panel_level 1 4 )) "-"
                                panel_matt_type "-" panel_name "-" "\n" 
                                (rtos panel_length 2 0) "x" (rtos panel_width 2 0) "mm." "-"
                                panel_color1 "-" "\n"
                                ""
                                (cond
                                  ( (= (wcmatch panel_shape "*standard*") T)
                                    (progn
                                      "STD-SHAPE"
                                    )
                                  )
                                  ( (= (wcmatch panel_shape "*trapezoids*") T)
                                    (progn
                                      "TPZ-SHAPE"
                                    )
                                  )
                                  ( (= (wcmatch panel_shape "varies") T)
                                    (progn
                                      "VA"
                                    )
                                  )
                                )
                                "-" panel_add-on1
                        ) 
          )
        
        
        
        
        
          (LM:vl-setattributevalue ASB_textbox_ename_obj_ "panel_code_name" sumsum_)
        ;
        
        (setq new_i 0)
        (while (and 
                 (= (LM:effectivename ASB_textbox_ename_obj_) "000_CKST-FAMELINE_CEILING_CODE_PANEL")
                 (< new_i (- ASB_obj_total_panel_i 1))
               )
          (vla-copy ASB_textbox_ename_obj_)
          ;new_blk_entlast object
            (setq new_box_ename_ (entlast)) 
            (setq new_box_ename_obj (vlax-ename->vla-object new_box_ename_))
          ;
          (TA:move_polar_insertionpoint new_box_ename_obj "Y" (* 310 (+ new_i 1)))
          (setq new_i (+ new_i 1))
        )
      )
    )
    
  )
  (defun c:PPLINE_CKST_ADD_CODE_TO_PANEL_300sort ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000_CKST-FAMELINE_CEILING_CODE_PANEL")))
    (setq sorting_ ;Get-string by keep previous value
      (strcase
        (if 
          (or 
            (/= (setq sorting_val (getstring ( strcat "\nSpecify Pattern name <" ( if sorting_ sorting_ "" ) ">: " ) ) ) "" )
          )
          (progn 
            (setq sorting_ sorting_val)
            (setq sorting_keep_val_ sorting_val)
          )
          (setq sorting_val sorting_keep_val_)
        )
      )                                                      
    )
    (setq ss_pre_filter_set_xx_sort_ (TA:standard_list_croodinate_sorting ss_pre_filter_set_xx_ sorting_))
    ;TA:stanndard_lambda_sorting
      (cond
        (;_case_1
           (and
              (= sorting_ "X")
           )
           (progn
            (setq ss_pre_filter_set_xx_sort_sorted_ (vl-sort ss_pre_filter_set_xx_sort_  ;bigest open indent list
                                                (function 
                                                  (lambda (a b) 
                                                    (< (car (cadr a))  
                                                       (car (cadr b))
                                                    )
                                                  )
                                                )
                            ) ;bigest close indent list
            )
           )
        )
        (;_case_2
           (and
              (= sorting_ "Y")
           )
           (progn
            (setq ss_pre_filter_set_xx_sort_sorted_ (vl-sort ss_pre_filter_set_xx_sort_  ;bigest open indent list
                                                (function 
                                                  (lambda (a b) 
                                                    (> (cadr (cadr a))  
                                                       (cadr (cadr b))
                                                    )
                                                  )
                                                )
                            ) ;bigest close indent list
            )
           )
        )
      )
      
    ;
    (setq add_number_zone_ (cond ( (getint (strcat "\nSpecify increment_number_   <" (rtos (setq add_number_zone_ (cond (add_number_zone_) (1.0) ) ) ) "> : " ) ) ) (add_number_zone_) ) )
    (setq add_number_zone_ (if (= (- add_number_zone_ 1) 0) (progn 1 ) add_number_zone_ ) )
    (setq start_i add_number_zone_ )
    ;preloop_and_while
      (setq ss_pre_filter_set_xx_sort_i 0)
      (while (< ss_pre_filter_set_xx_sort_i (length ss_pre_filter_set_xx_sort_sorted_))
        (setq ss_pre_filter_set_xx_sort_ename_ (car (nth  ss_pre_filter_set_xx_sort_i ss_pre_filter_set_xx_sort_sorted_)))  

        (setq ss_pre_filter_set_xx_sort_obj_ (vlax-ename->vla-object  ss_pre_filter_set_xx_sort_ename_))
        (LM:vl-setattributevalue ss_pre_filter_set_xx_sort_obj_ "panel_no" (TA:prefix_value add_number_zone_))
        
        (setq add_number_zone_ (+ add_number_zone_ 1))
        (setq ss_pre_filter_set_xx_sort_i (+ ss_pre_filter_set_xx_sort_i 1))
      )
    ;
    (setq result (- (- add_number_zone_ 1 ) start_i ))
    (alert (strcat (rtos  start_i 2 0) "-" (rtos (- add_number_zone_ 1 ) 2 0) "=" (rtos result 2 0)))
    ; (command "pselect"  (setq ss_pre_filter_set_xx_ (TA:EF_Filter_ss_set_V2_ ss_pre_filter_set_xx_ (list "000_CKST-FAMELINE_CEILING_CODE_PANEL"))) "" )
    (command "pselect"  ss_pre_filter_set_xx_sort_ename_ "" )
  )
  (defun c:PPLINE_CSKST_ADD_CODE_TO_PANEL_find300accessories_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "000_CKST-FAMELINE_CEILING_CODE_PANEL")))
    ;
    ;preloop_and_while
      (setq ss_pre_filter_set_xx_i 0)
      (setq ss_newlist_  (ssadd ))
      (setq ss_newlist_listval_  ( ))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              ; (= (vla-get-hasattributes ss_pre_filter_set_xx_obj_ ) :vlax-true )
              (/= (LM:vl-getattributevalue ss_pre_filter_set_xx_obj_ "panel_add-on" ) "")
              (/= (LM:vl-getattributevalue ss_pre_filter_set_xx_obj_ "panel_add-on" ) "varies_lot")
              (/= (LM:vl-getattributevalue ss_pre_filter_set_xx_obj_ "panel_add-on" ) "XXXXXXX")
            )
          (progn
            (setq ss_newlist_listval_  (cons (list 
                                              (LM:vl-getattributevalue ss_pre_filter_set_xx_obj_ "panel_no" )
                                              (LM:vl-getattributevalue ss_pre_filter_set_xx_obj_ "panel_matt_type" )
                                              (LM:vl-getattributevalue ss_pre_filter_set_xx_obj_ "panel_width" )
                                              (LM:vl-getattributevalue ss_pre_filter_set_xx_obj_ "panel_add-on" )
                                              (LM:vl-getattributevalue ss_pre_filter_set_xx_obj_ "panel_color" )
                                              (LM:vl-getattributevalue ss_pre_filter_set_xx_obj_ "panel_shape" )
                                            )  
                                            ss_newlist_listval_ 
                                      ) 
            )
            (setq ss_newlist_ (ssadd ss_pre_filter_set_xx_ename_  ss_newlist_ ) )
          )
        )
        (TA:textscr_process_V2 "updated" ss_pre_filter_set_xx_i ss_pre_filter_set_xx_ )
        (setq ss_pre_filter_set_xx_i (+ ss_pre_filter_set_xx_i  1))
      )
    ;
    (sslength ss_newlist_ )
    (setq summary_acessories_List_ (TA:Sort_nested_list_ (TA:Count_item_in_list_ ss_newlist_listval_) 2))
    (defun TA:Print_list_by_line_ (input_list_ / item_)
      (foreach item_ input_list_
        (princ "\n")
        (prin1 item_)
      )
      (princ)
    )
    
    (command "pselect"  ss_newlist_  "" )
    (TA:Print_list_by_line_ summary_acessories_List_)
    
  )
  
  (defun c:PPLINE_300CODEexport_TO_CSV ()
    (cond
      ((and 
        (= (getenv "COMPUTERNAME") "NONGSAISUEARAIH")
        (= (getenv "USERNAME") "T")
      )
        (progn
          (setq Er-msg_1 (vl-catch-all-apply (function (lambda () (load "C:/TA/TA_COMPELETE/WriteCSV-V1-1.lsp") ) ) ) )
          (setq filepath "C:\\TA\\PPLINE CKST\\C1-C2_Finishes-Reflected Ceiling Plan\\PP-LINE_CL-PART\\HOOK ON DOWNLIGHT SMOKE\\")
        )
      )
      ((and 
        (= (getenv "COMPUTERNAME") "NONGSAISUEARAIH")
        (= (getenv "USERNAME") "popul")
      )
        (progn
          (setq Er-msg_1 (vl-catch-all-apply (function (lambda () (load "C:/TA/TA_COMPELETE/WriteCSV-V1-1.lsp") ) ) ) )
          (setq filepath "C:\\TA\\PPLINE CKST\\C1-C2_Finishes-Reflected Ceiling Plan\\PP-LINE_CL-PART\\HOOK ON DOWNLIGHT SMOKE\\")
        )
      )
    )

    (setq filename_ (strcat (LM:StringSubst "" ".dwg"  (getvar "dwgname"))  ".csv"))
    
    (setq export_list_ (append 
                         (list (List (strcat filename_ " Accessories dimension list") )) 
                         (list (list "CODE" "MATT TYPE" "PANEL WIDTH" "TYPE ACESSORIES" "COLOR" "panel_shape" "OFFSET L" "OFFSET R" "DN SK POSITION") ) 
                         ss_newlist_listval_
                       )
    )
    (if (findfile (strcat filepath  filename_)) 
      (progn
        (LM:writecsv export_list_ (strcat filepath (LM:StringSubst "-" "." (rtos (getvar "cdate") 2 8) ) "-" filename_))
      )
      (LM:writecsv export_list_ (strcat filepath filename_))
    )
    
  )
  (defun c:PPLINE_CKST_regenerate_reCODE ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq newattset_ss_ (TA:EF_Filter_ss_set_V2_ ss_pre_filter_set_xx_ (list "000_CKST-FAMELINE_CEILING_CODE_PANEL")))
    
    ;preloop_and_while
      (setq newattset_ss_i 0)
      (while (< newattset_ss_i (sslength newattset_ss_))
        (setq newattset_ss_ename_ (ssname newattset_ss_ newattset_ss_i))    
        (setq newattset_ss_obj_ (vlax-ename->vla-object  newattset_ss_ename_))
        
        (LM:vl-setattributevalue newattset_ss_obj_ "panel_length" (itoa (LM:round (atof (LM:vl-getattributevalue newattset_ss_obj_ "panel_length" )))))
        (setq newattset_ss_obj_att_list_ (LM:vl-getattributevalues newattset_ss_obj_))
        (setq ss (strcat 
                   (cdr (nth 10 newattset_ss_obj_att_list_))
                   "-"
                   (substr (strcase (cdr (nth 11 newattset_ss_obj_att_list_))) 1 4)
                   "-"
                   (cdr (nth 1 newattset_ss_obj_att_list_))
                   "-"
                   (cdr (nth 2 newattset_ss_obj_att_list_))
                   "-" "\n"
                   (cdr (nth 3 newattset_ss_obj_att_list_))
                   "-"
                   (if 
                     (and 
                       (/= (cdr (nth 4 newattset_ss_obj_att_list_)) "")
                       (/= (cdr (nth 5 newattset_ss_obj_att_list_)) "")
                     )
                     (progn 
                       (strcat 
                         (cdr (nth 4 newattset_ss_obj_att_list_))
                         "x"
                         (cdr (nth 5 newattset_ss_obj_att_list_))
                         "mm"
                         "-" "\n"
                       )
                     )
                     ""
                   )
                   (cdr (nth 6 newattset_ss_obj_att_list_))
                   "-" 
                   (cond
                    ( (and 
                        (= (wcmatch (strcase (cdr (nth 7 newattset_ss_obj_att_list_))) "*STANDARD*") T)
                        (= (wcmatch (strcase (cdr (nth 7 newattset_ss_obj_att_list_))) "*VARIES*") nil)
                      )
                      (progn
                        "STD-SHAPE"
                      )
                    )
                    ( (wcmatch (strcase (cdr (nth 7 newattset_ss_obj_att_list_))) "*TRAPEZOIDS*")
                      (progn
                        "TRPZ-SHAPE"
                      )          
                    )
                    ( (and 
                        (= (wcmatch (strcase (cdr (nth 7 newattset_ss_obj_att_list_))) "*STANDARD*") T)
                        (= (wcmatch (strcase (cdr (nth 7 newattset_ss_obj_att_list_))) "*VARIES*") T)
                      )
                      (progn
                        "VA-SHAPE"
                      )          
                    )
                   )
                    "-"
                    (if (= (cdr (nth 8 newattset_ss_obj_att_list_)) "")
                      (progn
                        "\nnon_add-on"
                      )
                      (cdr (nth 8 newattset_ss_obj_att_list_))
                    )
                    
                   
                 )
        )
        (LM:vl-setattributevalue newattset_ss_obj_ "panel_code_name" ss)
        
        
        
        (setq newattset_ss_i (+ newattset_ss_i 1))
      )
    ;
    (command "pselect"  newattset_ss_ "" )
  )
  (defun c:PPLINE_CKST_regenerate_303xsort ()
    (defun TA:convert-list-ucs (lst /)
      (mapcar
        '(lambda (a)
          (list
            (car a)
            (trans (cadr a) 0 1)
          )
        )
        lst
      )
    )
    ;selection_set_for_fillter_blk_name
      (if  ;pre_select_ssget_or_post_select_ssget
        (=
          (setq ss_pre_filter_set_xx_ (ssget "i"
                                            (list
                                              (cons 0 "INSERT") ;type of object
                                              (cons 8 "C0x_300HK_CODE_*")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              (cons 8 "C0x_300HK_CODE_*")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "000_CKST-FAMELINE_CEILING_CODE_PANEL")))
      (setq ss_pre_filter_set_xx_list_ (TA:standard_list_croodinate_sorting ss_pre_filter_set_xx_ "X"))
    ;
     

      
      (setq tol 100.00) ; ระยะที่ถือว่าเป็นแถวเดียวกัน (mm)
      (setq tol (cond ( (getint (strcat "\nSpecify tol   <" (rtos (setq tol (cond (tol) (1.0) ) ) ) "> : " ) ) ) (tol) ) )
      (if (= (getvar "worlducs" ) 0 )
        (progn
          (setq ss_pre_filter_set_xx_list_ (TA:convert-list-ucs ss_pre_filter_set_xx_list_))
          (setq sorted_
            (vl-sort ss_pre_filter_set_xx_list_
              '(lambda (a b)

                (setq ya (cadr (cadr a)))
                (setq yb (cadr (cadr b)))

                (setq xa (car (cadr a)))
                (setq xb (car (cadr b)))

                (if (> (abs (- ya yb)) tol)
                  (> ya yb) ; แถวบน -> ล่าง
                  (< xa xb) ; ซ้าย -> ขวา
                )

              )
            )

          )
        )
        (setq sorted_
          (vl-sort ss_pre_filter_set_xx_list_
            '(lambda (a b)

              (setq ya (cadr (cadr a)))
              (setq yb (cadr (cadr b)))

              (setq xa (car (cadr a)))
              (setq xb (car (cadr b)))

              (if (> (abs (- ya yb)) tol)
                (> ya yb) ; แถวบน -> ล่าง
                (< xa xb) ; ซ้าย -> ขวา
              )

            )
          )
        )
        
      )
      
    ;
    (setq add_number_zone_ (cond ( (getint (strcat "\nSpecify increment_number_   <" (rtos (setq add_number_zone_ (cond (add_number_zone_) (1.0) ) ) ) "> : " ) ) ) (add_number_zone_) ) )
    ;preloop_and_while
      (setq sorted_i 0)
      (while (< sorted_i (length sorted_))
        (setq sorted_ename_ (car (nth  sorted_i sorted_)))   
        (setq sorted_obj_ (vlax-ename->vla-object  sorted_ename_))
        (LM:vl-setattributevalue sorted_obj_ "panel_no" (TA:prefix_value add_number_zone_))
        (setq add_number_zone_ (+ add_number_zone_ 1))
        (setq sorted_i (+ sorted_i 1))
      )
    ;
    (command "pselect"  sorted_ename_ "" )
  )
  (defun c:PPLINE_CKST_regenerate_303ysort ()
      (defun TA:convert-list-ucs (lst /)
        (mapcar
          '(lambda (a)
            (list
              (car a)
              (trans (cadr a) 0 1)
            )
          )
          lst
        )
      )
    ;selection_set_for_fillter_blk_name
      (if  ;pre_select_ssget_or_post_select_ssget
        (=
          (setq ss_pre_filter_set_xx_ (ssget "i"
                                            (list
                                              (cons 0 "INSERT") ;type of object
                                              (cons 8 "C0x_300HK_CODE_*")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              (cons 8 "C0x_300HK_CODE_*")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "000_CKST-FAMELINE_CEILING_CODE_PANEL")))
      (setq ss_pre_filter_set_xx_list_ (TA:standard_list_croodinate_sorting ss_pre_filter_set_xx_ "X"))
    ;
     

      
      (setq tol 5) ; ระยะที่ถือว่าเป็นแถวเดียวกัน (mm)
      (setq tol (cond ( (getint (strcat "\nSpecify tol   <" (rtos (setq tol (cond (tol) (1.0) ) ) ) "> : " ) ) ) (tol) ) )

      (setq tol 5.0) ; ระยะที่ถือว่าเป็นแถวเดียวกัน (mm)
      (if (= (getvar "worlducs" ) 0 )
        (progn
          (setq ss_pre_filter_set_xx_list_ (TA:convert-list-ucs ss_pre_filter_set_xx_list_))
          (setq sorted_
            (setq sorted_ (vl-sort 
                            ss_pre_filter_set_xx_list_
                            '(lambda (a b) 

                               (setq xa (car (cadr a)))
                               (setq ya (cadr (cadr a)))

                               (setq xb (car (cadr b)))
                               (setq yb (cadr (cadr b)))

                               (if (> (abs (- xa xb)) tol) 
                                 (< xa xb) ; ซ้าย -> ขวา
                                 (> ya yb) ; บน -> ล่าง
                               )
                             )
                          )
            )

          )
        )
        (setq sorted_ (vl-sort 
                      ss_pre_filter_set_xx_list_
                      '(lambda (a b) 

                          (setq xa (car (cadr a)))
                          (setq ya (cadr (cadr a)))

                          (setq xb (car (cadr b)))
                          (setq yb (cadr (cadr b)))

                          (if (> (abs (- xa xb)) tol) 
                            (< xa xb) ; ซ้าย -> ขวา
                            (> ya yb) ; บน -> ล่าง
                          )
                        )
                    )
        )
      )
      
    ;
    (setq add_number_zone_ (cond ( (getint (strcat "\nSpecify increment_number_   <" (rtos (setq add_number_zone_ (cond (add_number_zone_) (1.0) ) ) ) "> : " ) ) ) (add_number_zone_) ) )
    ;preloop_and_while
      (setq sorted_i 0)
      (while (< sorted_i (length sorted_))
        (setq sorted_ename_ (car (nth  sorted_i sorted_)))  
        (setq sorted_obj_ (vlax-ename->vla-object  sorted_ename_))
        (LM:vl-setattributevalue sorted_obj_ "panel_no" (TA:prefix_value add_number_zone_))
        (setq add_number_zone_ (+ add_number_zone_ 1))
        (setq sorted_i (+ sorted_i 1))
      )
    ;
    (command "pselect"  sorted_ename_ "" )
  )
  (defun c:c:PPLINE_CKST_ADD_CODE_TO_PANEL_find_blankno ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000_CKST-FAMELINE_CEILING_CODE_PANEL")))
    ;preloop_and_while
      (setq ss_pre_filter_set_xx_i 0)
      (setq new_sel_ss_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))

        (if (= (LM:vl-getattributevalue ss_pre_filter_set_xx_obj_ "panel_no" ) "")
          (progn
            (setq new_sel_ss_ (ssadd ss_pre_filter_set_xx_ename_ new_sel_ss_)) 
          )
        )
        (setq ss_pre_filter_set_xx_i (+ ss_pre_filter_set_xx_i 1))
      )
    ;
    (command "pselect"  new_sel_ss_ "" )
  )
  (defun c:PPLINE_CKST_ADD_CODE_TO_PANEL_find_1st ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000_CKST-FAMELINE_CEILING_CODE_PANEL")))
    ;preloop_and_while
      (setq ss_pre_filter_set_xx_i 0)
      (setq new_sel_ss_ (ssadd))
      (setq new_sel_ss_2 (ssadd))
      (setq new_sel_ss_3 (ssadd))
      (while (< ss_pre_filter_set_xx_i (sslength ss_pre_filter_set_xx_))
        (setq ss_pre_filter_set_xx_ename_ (ssname ss_pre_filter_set_xx_ ss_pre_filter_set_xx_i)) 
        (setq ss_pre_filter_set_xx_obj_ (vlax-ename->vla-object  ss_pre_filter_set_xx_ename_))

        (if (= (wcmatch (LM:vl-getattributevalue ss_pre_filter_set_xx_obj_ "panel_date-create") "*1st*") t)
          (progn
            (setq new_sel_ss_ (ssadd ss_pre_filter_set_xx_ename_ new_sel_ss_)) 
          )
        )
        (if (or 
              (= (wcmatch (LM:vl-getattributevalue ss_pre_filter_set_xx_obj_ "panel_date-create") "*2nd*") t)
              (/= (wcmatch (LM:vl-getattributevalue ss_pre_filter_set_xx_obj_ "panel_date-create") "*1st*") t)
            )
          (progn
            (setq new_sel_ss_2 (ssadd ss_pre_filter_set_xx_ename_ new_sel_ss_2)) 
          )
        )
        (if (and 
              (/= (wcmatch (LM:vl-getattributevalue ss_pre_filter_set_xx_obj_ "panel_date-create") "*1st*") t)
              (/= (wcmatch (LM:vl-getattributevalue ss_pre_filter_set_xx_obj_ "panel_date-create") "*2nd*") t)
            )
          (progn
            (setq new_sel_ss_3 (ssadd ss_pre_filter_set_xx_ename_ new_sel_ss_3)) 
          )
        )
        (setq ss_pre_filter_set_xx_i (+ ss_pre_filter_set_xx_i 1))
      )
    ;
    (= (+ (sslength new_sel_ss_2 ) (sslength new_sel_ss_)  (sslength new_sel_ss_3 )) (sslength ss_pre_filter_set_xx_))
    (command "pselect"  new_sel_ss_3 "" )
  )
  (defun c:swaddon ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000_CKST-FAMELINE_CEILING_CODE_PANEL")))
    ;preloop_and_while
      (setq ss_pre_filter_set_xx_i 0)
      (while (and 
                (< ss_pre_filter_set_xx_i (sslength ss_pre_filter_set_xx_))
              )
        (setq ss_pre_filter_set_xx_ename_ (ssname ss_pre_filter_set_xx_ ss_pre_filter_set_xx_i))
        (setq ss_pre_filter_set_xx_obj_ (vlax-ename->vla-object  ss_pre_filter_set_xx_ename_))
        (cond
          (;ss_pre_filter_set_xx_obj_case_1
              (and
                (= (LM:vl-getattributevalue ss_pre_filter_set_xx_obj_ "panel_add-on") "")
              )
              (progn
                (LM:vl-setattributevalue ss_pre_filter_set_xx_obj_ "panel_add-on" "1DL")
                (vla-put-color ss_pre_filter_set_xx_obj_ 1)
                (princ "ss_pre_filter_set_xx_obj_case_1")
              )
          )
          (;ss_pre_filter_set_xx_obj_case_1
              (and
                (= (LM:vl-getattributevalue ss_pre_filter_set_xx_obj_ "panel_add-on") "1DL")
              )
              (progn
                (LM:vl-setattributevalue ss_pre_filter_set_xx_obj_ "panel_add-on" "2DL")
                (vla-put-color ss_pre_filter_set_xx_obj_ 4)
                (princ "ss_pre_filter_set_xx_obj_case_1")
              )
          )
          (;ss_pre_filter_set_xx_obj_case_1
              (and
                (= (LM:vl-getattributevalue ss_pre_filter_set_xx_obj_ "panel_add-on") "2DL")
              )
              (progn
                (LM:vl-setattributevalue ss_pre_filter_set_xx_obj_ "panel_add-on" "SD")
                (vla-put-color ss_pre_filter_set_xx_obj_ 6)
                (princ "ss_pre_filter_set_xx_obj_case_1")
              )
          )
          (;ss_pre_filter_set_xx_obj_case_1
              (and
                (= (LM:vl-getattributevalue ss_pre_filter_set_xx_obj_ "panel_add-on") "SD")
              )
              (progn
                (LM:vl-setattributevalue ss_pre_filter_set_xx_obj_ "panel_add-on" "1DL+SD")
                (vla-put-color ss_pre_filter_set_xx_obj_ 5)
                (princ "ss_pre_filter_set_xx_obj_case_1")
              )
          )
          (;ss_pre_filter_set_xx_obj_case_1
              (and
                (= (LM:vl-getattributevalue ss_pre_filter_set_xx_obj_ "panel_add-on") "1DL+SD")
              )
              (progn
                (LM:vl-setattributevalue ss_pre_filter_set_xx_obj_ "panel_add-on" "2DL+SD")
                (vla-put-color ss_pre_filter_set_xx_obj_ 30)
                (princ "ss_pre_filter_set_xx_obj_case_1")
              )
          )
          (;ss_pre_filter_set_xx_obj_case_1
              (and
                (= (LM:vl-getattributevalue ss_pre_filter_set_xx_obj_ "panel_add-on") "2DL+SD")
              )
              (progn
                (LM:vl-setattributevalue ss_pre_filter_set_xx_obj_ "panel_add-on" "3DL")
                (vla-put-color ss_pre_filter_set_xx_obj_ 2)
                (princ "ss_pre_filter_set_xx_obj_case_1")
              )
          )
          (;ss_pre_filter_set_xx_obj_case_1
              (and
                (= (LM:vl-getattributevalue ss_pre_filter_set_xx_obj_ "panel_add-on") "3DL")
              )
              (progn
                (LM:vl-setattributevalue ss_pre_filter_set_xx_obj_ "panel_add-on" "")
                (vla-put-color ss_pre_filter_set_xx_obj_ 3)
                (princ "ss_pre_filter_set_xx_obj_case_1")
              )
          )
        
        )
        
        (setq ss_pre_filter_set_xx_i (+ ss_pre_filter_set_xx_i 1))
      )
    ;
      
    ;while selection process
      (setq ERR_ nil)
      (while ;for keep insertion point and dist. fix length one side
        (and
          (= (vl-catch-all-error-p ERR_) nil)
        )
        (setq ERR_
          (vl-catch-all-apply
            (function
              (lambda ()
                (getstring (strcat "enter for " (LM:vl-getattributevalue (vlax-ename->vla-object  (ssname ss_pre_filter_set_xx_ 0))  "panel_add-on") " continue"));input_cond entsel ssget
              )
            )
          )
        )
        ;preloop_and_while
          (setq ss_pre_filter_set_xx_i 0)
          (while (and 
                   (= (vl-catch-all-error-p ERR_) nil)
                   (< ss_pre_filter_set_xx_i (sslength ss_pre_filter_set_xx_))
                 )
            (setq ss_pre_filter_set_xx_ename_ (ssname ss_pre_filter_set_xx_ ss_pre_filter_set_xx_i))
            (setq ss_pre_filter_set_xx_obj_ (vlax-ename->vla-object  ss_pre_filter_set_xx_ename_))
            (cond
              (;ss_pre_filter_set_xx_obj_case_1
                  (and
                    (= (LM:vl-getattributevalue ss_pre_filter_set_xx_obj_ "panel_add-on") "")
                  )
                  (progn
                    (LM:vl-setattributevalue ss_pre_filter_set_xx_obj_ "panel_add-on" "1DL")
                    (vla-put-color ss_pre_filter_set_xx_obj_ 1)
                    (princ "ss_pre_filter_set_xx_obj_case_1")
                  )
              )
              (;ss_pre_filter_set_xx_obj_case_1
                  (and
                    (= (LM:vl-getattributevalue ss_pre_filter_set_xx_obj_ "panel_add-on") "1DL")
                  )
                  (progn
                    (LM:vl-setattributevalue ss_pre_filter_set_xx_obj_ "panel_add-on" "2DL")
                    (vla-put-color ss_pre_filter_set_xx_obj_ 4)
                    (princ "ss_pre_filter_set_xx_obj_case_1")
                  )
              )
              (;ss_pre_filter_set_xx_obj_case_1
                  (and
                    (= (LM:vl-getattributevalue ss_pre_filter_set_xx_obj_ "panel_add-on") "2DL")
                  )
                  (progn
                    (LM:vl-setattributevalue ss_pre_filter_set_xx_obj_ "panel_add-on" "SD")
                    (vla-put-color ss_pre_filter_set_xx_obj_ 6)
                    (princ "ss_pre_filter_set_xx_obj_case_1")
                  )
              )
              (;ss_pre_filter_set_xx_obj_case_1
                  (and
                    (= (LM:vl-getattributevalue ss_pre_filter_set_xx_obj_ "panel_add-on") "SD")
                  )
                  (progn
                    (LM:vl-setattributevalue ss_pre_filter_set_xx_obj_ "panel_add-on" "1DL+SD")
                    (vla-put-color ss_pre_filter_set_xx_obj_ 5)
                    (princ "ss_pre_filter_set_xx_obj_case_1")
                  )
              )
              (;ss_pre_filter_set_xx_obj_case_1
                  (and
                    (= (LM:vl-getattributevalue ss_pre_filter_set_xx_obj_ "panel_add-on") "1DL+SD")
                  )
                  (progn
                    (LM:vl-setattributevalue ss_pre_filter_set_xx_obj_ "panel_add-on" "2DL+SD")
                    (vla-put-color ss_pre_filter_set_xx_obj_ 30)
                    (princ "ss_pre_filter_set_xx_obj_case_1")
                  )
              )
              (;ss_pre_filter_set_xx_obj_case_1
                  (and
                    (= (LM:vl-getattributevalue ss_pre_filter_set_xx_obj_ "panel_add-on") "2DL+SD")
                  )
                  (progn
                    (LM:vl-setattributevalue ss_pre_filter_set_xx_obj_ "panel_add-on" "3DL")
                    (vla-put-color ss_pre_filter_set_xx_obj_ 2)
                    (princ "ss_pre_filter_set_xx_obj_case_1")
                  )
              )
              (;ss_pre_filter_set_xx_obj_case_1
                  (and
                    (= (LM:vl-getattributevalue ss_pre_filter_set_xx_obj_ "panel_add-on") "3DL")
                  )
                  (progn
                    (LM:vl-setattributevalue ss_pre_filter_set_xx_obj_ "panel_add-on" "")
                    (vla-put-color ss_pre_filter_set_xx_obj_ 3)
                    (princ "ss_pre_filter_set_xx_obj_case_1")
                  )
              )
            
            )
            
            (setq ss_pre_filter_set_xx_i (+ ss_pre_filter_set_xx_i 1))
          )
        ;
      )
    ;
    (if (= (vl-catch-all-error-p ERR_) T)
      (progn
        (setq blank_ss (ssadd))
        (command "pselect" blank_ss   "")
      )
    )
  )
  (defun c:swappanel ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list 
                                                                                 "000 - FAMELINE-CKST_AL.CELING_PANEL_300HK_@400mm_BOTTOM_VIEW_FOR_AS-02(L-varies_LOT)"
                                                                                 "000 - FAMELINE-CKST_AL.CELING_PANEL_300HK_@400mm_BOTTOM_VIEW_FOR_AS-02(varies_LOT)"
                                                                                 
                                                                               )
                                )
    )
    ;preloop_and_while
      (setq ERR_ nil)
      (setq ss_pre_filter_set_xx_i 0)
      (while (and 
                (= (vl-catch-all-error-p ERR_) nil)
                (/= (sslength ss_pre_filter_set_xx_) 0)
                (< ss_pre_filter_set_xx_i (sslength ss_pre_filter_set_xx_))
              )
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ro (rad-to-deg (vla-get-rotation  ss_pre_filter_set_xx_obj_)))
        (cond
          (;ss_pre_filter_set_xx_obj_case_1
              (and
                (= (LM:getdynpropvalue ss_pre_filter_set_xx_obj_ "flip state1") 1)
                (= ss_pre_filter_set_xx_obj_ro 0)
              )
              (progn
                (LM:setdynpropvalue ss_pre_filter_set_xx_obj_ "flip state1" 0)
                (vla-put-rotation  ss_pre_filter_set_xx_obj_ (deg-to-rad 180))
              )
          )
          (;ss_pre_filter_set_xx_obj_case_1
              (and
                (= (LM:getdynpropvalue ss_pre_filter_set_xx_obj_ "flip state1") 0)
                (= ss_pre_filter_set_xx_obj_ro 180)
              )
              (progn
                (LM:setdynpropvalue ss_pre_filter_set_xx_obj_ "flip state1" 1)
                (vla-put-rotation  ss_pre_filter_set_xx_obj_ (deg-to-rad 0))
              )
          )
          (;ss_pre_filter_set_xx_obj_case_1
              (and
                
                (/= ss_pre_filter_set_xx_obj_ro 0)
                (/= ss_pre_filter_set_xx_obj_ro 90)
                (/= ss_pre_filter_set_xx_obj_ro 180)
                (/= ss_pre_filter_set_xx_obj_ro 270)
                (= (LM:getdynpropvalue ss_pre_filter_set_xx_obj_ "flip state1" ) 1)
              )
              (progn
                (LM:setdynpropvalue ss_pre_filter_set_xx_obj_ "flip state1" 0)
              )
          )
          (;ss_pre_filter_set_xx_obj_case_1
              (and
                
                (/= ss_pre_filter_set_xx_obj_ro 0)
                (/= ss_pre_filter_set_xx_obj_ro 90)
                (/= ss_pre_filter_set_xx_obj_ro 180)
                (/= ss_pre_filter_set_xx_obj_ro 270)
                (= (LM:getdynpropvalue ss_pre_filter_set_xx_obj_ "flip state1" ) 0 )
              )
              (progn
                (LM:setdynpropvalue ss_pre_filter_set_xx_obj_ "flip state1" 1)
              )
          )
          
          
          
          
          
        
        )
        
        (setq ss_pre_filter_set_xx_i (+ ss_pre_filter_set_xx_i 1))
      )
    ;
    ;while selection process
      (setq ERR_ nil)
      (while ;for keep insertion point and dist. fix length one side
        (and
          (= (vl-catch-all-error-p ERR_) nil)
        )
        (setq ERR_
          (vl-catch-all-apply
            (function
              (lambda ()
                (getstring (strcat "enter for continue"));input_cond entsel ssget
              )
            )
          )
        )
        ;preloop_and_while
          (setq ss_pre_filter_set_xx_i 0)
          (while (and 
                   (= (vl-catch-all-error-p ERR_) nil)
                   (/= (sslength ss_pre_filter_set_xx_) 0)
                   (< ss_pre_filter_set_xx_i (sslength ss_pre_filter_set_xx_))
                 )
            (setq ss_pre_filter_set_xx_ename_ (ssname ss_pre_filter_set_xx_ ss_pre_filter_set_xx_i))
            (setq ss_pre_filter_set_xx_obj_ (vlax-ename->vla-object  ss_pre_filter_set_xx_ename_))
            (setq ss_pre_filter_set_xx_obj_ro (rad-to-deg (vla-get-rotation  ss_pre_filter_set_xx_obj_)))
            (cond
              (;ss_pre_filter_set_xx_obj_case_1
                  (and
                    (= (LM:getdynpropvalue ss_pre_filter_set_xx_obj_ "flip state1") 1)
                    (= ss_pre_filter_set_xx_obj_ro 0)
                  )
                  (progn
                    (LM:setdynpropvalue ss_pre_filter_set_xx_obj_ "flip state1" 0)
                    (vla-put-rotation  ss_pre_filter_set_xx_obj_ (deg-to-rad 180))
                  )
              )
              (;ss_pre_filter_set_xx_obj_case_1
                  (and
                    (= (LM:getdynpropvalue ss_pre_filter_set_xx_obj_ "flip state1") 0)
                    (= ss_pre_filter_set_xx_obj_ro 180)
                  )
                  (progn
                    (LM:setdynpropvalue ss_pre_filter_set_xx_obj_ "flip state1" 1)
                    (vla-put-rotation  ss_pre_filter_set_xx_obj_ (deg-to-rad 0))
                  )
              )
              (;ss_pre_filter_set_xx_obj_case_1
                  (and
                    
                    (/= ss_pre_filter_set_xx_obj_ro 0)
                    (/= ss_pre_filter_set_xx_obj_ro 90)
                    (/= ss_pre_filter_set_xx_obj_ro 180)
                    (/= ss_pre_filter_set_xx_obj_ro 270)
                    (= (LM:getdynpropvalue ss_pre_filter_set_xx_obj_ "flip state1" ) 1)
                  )
                  (progn
                    (LM:setdynpropvalue ss_pre_filter_set_xx_obj_ "flip state1" 0)
                  )
              )
              (;ss_pre_filter_set_xx_obj_case_1
                  (and
                    
                    (/= ss_pre_filter_set_xx_obj_ro 0)
                    (/= ss_pre_filter_set_xx_obj_ro 90)
                    (/= ss_pre_filter_set_xx_obj_ro 180)
                    (/= ss_pre_filter_set_xx_obj_ro 270)
                    (= (LM:getdynpropvalue ss_pre_filter_set_xx_obj_ "flip state1" ) 0 )
                  )
                  (progn
                    (LM:setdynpropvalue ss_pre_filter_set_xx_obj_ "flip state1" 1)
                  )
              )
            )
            (setq ss_pre_filter_set_xx_i (+ ss_pre_filter_set_xx_i 1))
          )
        ;
      )
    ;
    ; (if (= (vl-catch-all-error-p ERR_) T)
    ;   (progn
    ;     (setq blank_ss (ssadd))
    ;     (command "pselect"  blank_ss  "" )
    ;   )
    ; )
  )
  (defun c:tempswblk ()
    (setq old_block_ename_ (car (entsel "specify Object")))
    (setq old_block_obj_ (vlax-ename->vla-object old_block_ename_))
    (setq old_block_obj_ins_ (vlax-safearray->list (vlax-variant-value (vla-get-insertionpoint old_block_obj_))))
    (setq old_block_obj_ro_ (rad-to-deg (vla-get-rotation old_block_obj_)))
    (TA:vla-insertblock 
      "000 - FAMELINE-CKST_AL.CELING_PANEL_300HK_@400mm_BOTTOM_VIEW_FOR_AS-02(1st_LOT)"
      (getpoint "specify point")
      1
      (cond
        ( (= old_block_obj_ro_ 0)
          (progn
            (deg-to-rad (TA:ModifyRotation old_block_obj_ro_ 270))
          )
        )
        ( (= old_block_obj_ro_ 90)
          (progn
            (deg-to-rad (TA:ModifyRotation old_block_obj_ro_ -90))
          )
        )
        ( (and 
            (/= old_block_obj_ro_ 0)
            (/= old_block_obj_ro_ 90)
            (/= old_block_obj_ro_ 180)
            (/= old_block_obj_ro_ 270)
          )
          (progn
            (deg-to-rad (TA:ModifyRotation old_block_obj_ro_ -90))
          )
        )
      )
    )
    (setq array_panel_length (LM:getdynpropvalue old_block_obj_ "array_panel_length"))
    (setq panel_width (LM:getdynpropvalue old_block_obj_ "panel_width"))
    ;new_blk_entlast object
      (setq newinsert_ename (entlast))
      (setq newinsert_obj_ (vlax-ename->vla-object newinsert_ename))
      
      (cond
        ( (= old_block_obj_ro_ 0)
          (progn
            (LM:setdynpropvalue newinsert_obj_ "flip state1" 1)
          )
        )
        ( (= old_block_obj_ro_ 90)
          (progn
            (LM:setdynpropvalue newinsert_obj_ "flip state1" 1)
          )
        )
        ( (and 
              (/= old_block_obj_ro_ 0)
              (/= old_block_obj_ro_ 90)
              (/= old_block_obj_ro_ 180)
              (/= old_block_obj_ro_ 270)
            )
          (progn
            (LM:setdynpropvalue newinsert_obj_ "flip state1" 1)
          )
        )
      )
      (LM:setdynpropvalue newinsert_obj_ "array_length" array_panel_length)
      (LM:setdynpropvalue newinsert_obj_ "panel_width" panel_width)
      (LM:setdynpropvalue newinsert_obj_ "ref_line" 0)
    ;
    (vla-delete old_block_obj_)
  )
  (defun TAS:polygon2dyn (sss_ename_ nameblockname distance_block-scaling_ angle-block_)
    (defun TAS:convert-list-ucs (lst /)
      (mapcar
        '(lambda (pt)
          (trans (append pt '(0.0)) 0  1)
        )
        lst
      )
    )
    ;reporcess vertex pt
      ;1st process recrete vertex point
        ; (setq sss_ename_ (car (nentsel "specify Object"))) 
        (setq sss_ename_entget_ (entget sss_ename_))
        (setq sss_obj_ (vlax-ename->vla-object sss_ename_))
        (setq sss_obj_layer (vla-get-layer (vlax-ename->vla-object sss_ename_)))
        (setq sss_obj_color (vla-get-color (vlax-ename->vla-object sss_ename_)))
        (setq i 0)
        (setq sss_ename_vertex_ (vl-remove-if-not '(lambda (x) (= 10 (car x))) sss_ename_entget_))
        (setq sss_ename_vertex_ (mapcar 'cdr sss_ename_vertex_))
        (setq sss_ename_vertex_list_ (mapcar 
                                      '(lambda (x) 
                                          (cons x (setq i (+ i 1)))
                                        )
                                      sss_ename_vertex_
                                    )
        )
        ;TA:stanndard_lambda_sorting
          (setq sss_ename_vertex_list_sorted_ (vl-sort sss_ename_vertex_list_  ;bigest open indent list
                                                    (function 
                                                      (lambda (a b) 
                                                        (< (nth 0 (car a)) (nth 0 (car b))) ;กำหนดจุดให้ทำงาน ซ้ายบนของ vertex ทั้งหมด
                                                      )
                                                    )
                                ) ;bigest close indent list
          )
          (setq sss_ename_vertex_list_sorted_ sss_ename_vertex_list_) ;ไม่ต้อง fix จุดที่ต่ำที่สุดของ vertex ทั้งหมด 
        ;
        ;preloop_and_while
          (setq xest_nopt_ (cdr (car sss_ename_vertex_list_sorted_)))
          (setq xest_new_ ())
          (setq xest_old_ ())
          (setq sss_ename_vertex_list_sorted_i 0)
          ;preloop_and_while
            (while (< sss_ename_vertex_list_sorted_i (length sss_ename_vertex_list_))
              (setq sss_ename_vertex_list_sorted_val_ (nth  sss_ename_vertex_list_sorted_i sss_ename_vertex_list_))
              (if (< sss_ename_vertex_list_sorted_i (- xest_nopt_ 1) )
                (progn
                  (setq xest_new_ (cons sss_ename_vertex_list_sorted_val_ xest_new_ ))
                )
                (setq xest_old_ (cons sss_ename_vertex_list_sorted_val_ xest_old_ ))
              )
              (setq sss_ename_vertex_list_sorted_i (+ sss_ename_vertex_list_sorted_i 1))
            )
          ;
          (setq xest_new_ (reverse xest_new_)) 
          (setq xest_old_ (reverse xest_old_))
          (setq xest_all (append  xest_old_ xest_new_))
          (setq xest_all-1 (mapcar 
                            '(lambda (x) 
                              (car x) ;; ลบค่า cdr ของ x ออกจาก xest_all
                            )
                            xest_all ;; <- นี่คือลิสต์ที่เราจะวน
                          )
          )
          (setvar "osmode" 0)
          (if (= (getvar "worlducs") 0)(progn (setq xest_all-2 (TAS:convert-list-ucs xest_all-1))) (setq xest_all-2 xest_all-1) )
          
          (create-plines xest_all-2 "close" )
          (setvar "osmode" 1215)
        ;
      ;
      ;new_blk_entlast object
        (command "erase" sss_ename_ "")
        (setq pline_ename (entlast))
        (vla-put-layer (vlax-ename->vla-object pline_ename) sss_obj_layer)
        (vla-put-color (vlax-ename->vla-object pline_ename) sss_obj_color)
        ; (if (= (setq check_val_ (check-clockwise xest_all-1)) "Counter-clockwise")
        ;   (progn
        ;     (command "reverse" pline_ename "" )
        ;   )
        ; )
      ;
    ;
    ;reporcess vertex pt
      (setq vxpt_ (cdr (TA:Get_Pline_vertext_ins_point_ pline_ename)))
      (setq base (car (car vxpt_)))
      (setq new_edit_vxpt_ (mapcar 
                             '(lambda (p) 
                                (list 
                                  (- (car p) (car base))
                                  (- (cadr p) (cadr base))
                                )
                              )
                             (car vxpt_)
                           )
      )
      (if (and 
            (= (car (nth 0 new_edit_vxpt_)) (car (nth 0 (reverse new_edit_vxpt_))))
            (= (cadr (nth 0 new_edit_vxpt_)) (cadr (nth 0 (reverse new_edit_vxpt_))))
          )
        (progn
          (setq new_edit_vxpt_ (reverse (cdr (reverse new_edit_vxpt_))))
        )
      )
    ;
    ;
      (TA:vla-insertblock 
          nameblockname
          (car (car vxpt_))
          distance_block-scaling_
          (deg-to-rad angle-block_)
      )
      ;new_blk_entlast object
        (setq new_ename (entlast))
        (setq new_obj_ (vlax-ename->vla-object new_ename))
        (setq new_obj_dynlist_ (LM:getdynprops new_obj_))
        (setq new_obj_dynlist_comb_ (list 
                                     (list 
                                       (nth 0 new_obj_dynlist_)
                                       (nth 1 new_obj_dynlist_)
                                     )
                                     (list 
                                       (nth 2 new_obj_dynlist_)
                                       (nth 3 new_obj_dynlist_)
                                     )
                                     (list 
                                       (nth 4 new_obj_dynlist_)
                                       (nth 5 new_obj_dynlist_)
                                     )
                                     (list 
                                       (nth 6 new_obj_dynlist_)
                                       (nth 7 new_obj_dynlist_)
                                     )
                                     (list 
                                       (nth 8 new_obj_dynlist_)
                                       (nth 9 new_obj_dynlist_)
                                     )
                                     (list 
                                       (nth 10 new_obj_dynlist_)
                                       (nth 11 new_obj_dynlist_)
                                     )
                                     (list 
                                       (nth 12 new_obj_dynlist_)
                                       (nth 13 new_obj_dynlist_)
                                     )
                                     (list 
                                       (nth 14 new_obj_dynlist_)
                                       (nth 15 new_obj_dynlist_)
                                     )
                                     (list 
                                       (nth 16 new_obj_dynlist_)
                                       (nth 17 new_obj_dynlist_)
                                     )
                                     (list 
                                       (nth 18 new_obj_dynlist_)
                                       (nth 19 new_obj_dynlist_)
                                     )
                                     (list 
                                       (nth 20 new_obj_dynlist_)
                                       (nth 21 new_obj_dynlist_)
                                     )
                                     (list 
                                       (nth 22 new_obj_dynlist_)
                                       (nth 23 new_obj_dynlist_)
                                     )
                                     (list 
                                       (nth 24 new_obj_dynlist_)
                                       (nth 25 new_obj_dynlist_)
                                     )
                                     (list 
                                       (nth 26 new_obj_dynlist_)
                                       (nth 27 new_obj_dynlist_)
                                     )
                                     (list 
                                       (nth 28 new_obj_dynlist_)
                                       (nth 29 new_obj_dynlist_)
                                     )
                                     (list 
                                       (nth 30 new_obj_dynlist_)
                                       (nth 31 new_obj_dynlist_)
                                     )
                                     (list 
                                       (nth 32 new_obj_dynlist_)
                                       (nth 33 new_obj_dynlist_)
                                     )
                                     (list 
                                       (nth 34 new_obj_dynlist_)
                                       (nth 35 new_obj_dynlist_)
                                     )
                                     (list 
                                       (nth 36 new_obj_dynlist_)
                                       (nth 37 new_obj_dynlist_)
                                     )
                                     (list 
                                       (nth 38 new_obj_dynlist_)
                                       (nth 39 new_obj_dynlist_)
                                     )
                                     (list 
                                       (nth 40 new_obj_dynlist_)
                                       (nth 41 new_obj_dynlist_)
                                     )
                                     (list 
                                       (nth 42 new_obj_dynlist_)
                                       (nth 43 new_obj_dynlist_)
                                     )
                                     (list 
                                       (nth 44 new_obj_dynlist_)
                                       (nth 45 new_obj_dynlist_)
                                     )
                                     (list
                                       (nth 46 new_obj_dynlist_)
                                       (nth 47 new_obj_dynlist_)
                                     )
                                     (list
                                       (nth 48 new_obj_dynlist_)
                                       (nth 49 new_obj_dynlist_)
                                     )
                                      (list
                                        (nth 50 new_obj_dynlist_)
                                        (nth 51 new_obj_dynlist_)
                                      )
                                      (list
                                        (nth 52 new_obj_dynlist_)
                                        (nth 53 new_obj_dynlist_)
                                      )
                                      (list
                                        (nth 54 new_obj_dynlist_)
                                        (nth 55 new_obj_dynlist_)
                                      )
                                      (list
                                        (nth 56 new_obj_dynlist_)
                                        (nth 57 new_obj_dynlist_)
                                      )
                                      (list
                                        (nth 58 new_obj_dynlist_)
                                        (nth 59 new_obj_dynlist_)
                                      )
                                      (list
                                        (nth 60 new_obj_dynlist_)
                                        (nth 61 new_obj_dynlist_)
                                      )

                                      (list
                                        (nth 62 new_obj_dynlist_)
                                        (nth 63 new_obj_dynlist_)
                                      )
                                      (list
                                        (nth 64 new_obj_dynlist_)
                                        (nth 65 new_obj_dynlist_)
                                      )
                                      (list
                                        (nth 66 new_obj_dynlist_)
                                        (nth 67 new_obj_dynlist_)
                                      )
                                      (list
                                        (nth 68 new_obj_dynlist_)
                                        (nth 69 new_obj_dynlist_)
                                      )
                                      (list
                                        (nth 70 new_obj_dynlist_)
                                        (nth 71 new_obj_dynlist_)
                                      )
                                      (list
                                        (nth 72 new_obj_dynlist_)
                                        (nth 73 new_obj_dynlist_)
                                      )
                                      (list
                                        (nth 74 new_obj_dynlist_)
                                        (nth 75 new_obj_dynlist_)
                                      )
                                      (list
                                        (nth 76 new_obj_dynlist_)
                                        (nth 77 new_obj_dynlist_)
                                      )
                                      (list
                                        (nth 78 new_obj_dynlist_)
                                        (nth 79 new_obj_dynlist_)
                                      )
                                      (list
                                        (nth 80 new_obj_dynlist_)
                                        (nth 81 new_obj_dynlist_)
                                      )
                                      (list
                                        (nth 82 new_obj_dynlist_)
                                        (nth 83 new_obj_dynlist_)
                                      )
                                      (list
                                        (nth 84 new_obj_dynlist_)
                                        (nth 85 new_obj_dynlist_)
                                      )
                                      (list
                                        (nth 86 new_obj_dynlist_)
                                        (nth 87 new_obj_dynlist_)
                                      )
                                      (list
                                        (nth 88 new_obj_dynlist_)
                                        (nth 89 new_obj_dynlist_)
                                      )
                                      (list
                                        (nth 90 new_obj_dynlist_)
                                        (nth 91 new_obj_dynlist_)
                                      )
                                      (list
                                        (nth 92 new_obj_dynlist_)
                                        (nth 93 new_obj_dynlist_)
                                      )
                                   )
        )
      ;
      ;preloop_and_while
        (setq new_obj_dynlist_comb_i 0)
        (setq new_edit_vxpt_i 1)
        (while (< new_obj_dynlist_comb_i (length new_obj_dynlist_comb_))
          (if (>= new_edit_vxpt_i (length new_edit_vxpt_) )
            (progn
              (setq new_obj_dynlist_comb_parameter_1 (car (car (nth  new_obj_dynlist_comb_i new_obj_dynlist_comb_))))
              (setq new_obj_dynlist_comb_parameter_2 (car (cadr (nth  new_obj_dynlist_comb_i new_obj_dynlist_comb_))))
              (setq new_edit_vxpt_val_1 (car (nth  (- new_edit_vxpt_i 1)  new_edit_vxpt_)))
              (setq new_edit_vxpt_val_2 (cadr (nth  (- new_edit_vxpt_i 1) new_edit_vxpt_)))
              (LM:setdynpropvalue new_obj_ new_obj_dynlist_comb_parameter_1 new_edit_vxpt_val_1 )
              (LM:setdynpropvalue new_obj_ new_obj_dynlist_comb_parameter_2 new_edit_vxpt_val_2 )
            )
          )
          (if (< new_edit_vxpt_i (length new_edit_vxpt_) )
            (progn
              (setq new_obj_dynlist_comb_parameter_1 (car (car (nth  new_obj_dynlist_comb_i new_obj_dynlist_comb_))))
              (setq new_obj_dynlist_comb_parameter_2 (car (cadr (nth  new_obj_dynlist_comb_i new_obj_dynlist_comb_))))
              (setq new_edit_vxpt_val_1 (car (nth  new_edit_vxpt_i new_edit_vxpt_)))
              (setq new_edit_vxpt_val_2 (cadr (nth  new_edit_vxpt_i new_edit_vxpt_)))
              (LM:setdynpropvalue new_obj_ new_obj_dynlist_comb_parameter_1 new_edit_vxpt_val_1 )
              (LM:setdynpropvalue new_obj_ new_obj_dynlist_comb_parameter_2 new_edit_vxpt_val_2 )
            )
          )
          (setq new_obj_dynlist_comb_parameter_112 (car (car (nth  new_obj_dynlist_comb_i new_obj_dynlist_comb_))))
          (if (< new_edit_vxpt_i (length new_edit_vxpt_) )
            (progn
              (setq new_edit_vxpt_i (+ new_edit_vxpt_i 1))
            )
          )
          
          (setq new_obj_dynlist_comb_i (+ new_obj_dynlist_comb_i 1))
          
        )
      ;
    ;
    (setq pline_ename pline_ename)
    
  )
  (defun C:vertex_right_ ()
    (defun TAS:convert-list-ucs (lst /)
      (mapcar
        '(lambda (pt)
          (trans (append pt '(0.0)) 0  1)
        )
        lst
      )
    )
    (defun TA:vertex_right_ (sss_ename_ )
      ;reporcess vertex pt
        ;1st process recrete vertex point
          ; (setq sss_ename_ (car (nentsel "specify Object"))) 
          (setq sss_ename_entget_ (entget sss_ename_))
          (command "redraw")
          (setq sss_obj_ (vlax-ename->vla-object sss_ename_))
          (setq i 0)
          (setq sss_ename_vertex_ (vl-remove-if-not '(lambda (x) (= 10 (car x))) sss_ename_entget_))
          (setq sss_ename_vertex_ (mapcar 'cdr sss_ename_vertex_))
          (setq sss_ename_vertex_list_ (mapcar 
                                        '(lambda (x) 
                                            (cons x (setq i (+ i 1)))
                                          )
                                        sss_ename_vertex_
                                      )
          )
          ;TA:stanndard_lambda_sorting
            ; (setq sss_ename_vertex_list_sorted_ (vl-sort sss_ename_vertex_list_  ;bigest open indent list
            ;                                           (function 
            ;                                             (lambda (a b) 
            ;                                               (< (nth 0 (car a)) (nth 0 (car b))) ;กำหนดจุดให้ทำงาน ซ้ายบนของ vertex ทั้งหมด
            ;                                             )
            ;                                           )
            ;                       ) ;bigest close indent list
            ; )
            (setq sss_ename_vertex_list_sorted_  sss_ename_vertex_list_)
          ;
          ;preloop_and_while
            (setq xest_nopt_ (cdr (car sss_ename_vertex_list_sorted_)))
            (setq xest_new_ ())
            (setq xest_old_ ())
            (setq sss_ename_vertex_list_sorted_i 0)
            ;preloop_and_while
              (while (< sss_ename_vertex_list_sorted_i (length sss_ename_vertex_list_))
                (setq sss_ename_vertex_list_sorted_val_ (nth  sss_ename_vertex_list_sorted_i sss_ename_vertex_list_))
                (if (< sss_ename_vertex_list_sorted_i (- xest_nopt_ 1) )
                  (progn
                    (setq xest_new_ (cons sss_ename_vertex_list_sorted_val_ xest_new_ ))
                  )
                  (setq xest_old_ (cons sss_ename_vertex_list_sorted_val_ xest_old_ ))
                )
                (setq sss_ename_vertex_list_sorted_i (+ sss_ename_vertex_list_sorted_i 1))
              )
            ;
            (setq xest_new_ (reverse xest_new_)) 
            (setq xest_old_ (reverse xest_old_))
            (setq xest_all (append  xest_old_ xest_new_))
            (setq xest_all-1 (mapcar 
                              '(lambda (x) 
                                (car x) ;; ลบค่า cdr ของ x ออกจาก xest_all
                              )
                              xest_all ;; <- นี่คือลิสต์ที่เราจะวน
                            )
            )
            (setvar "osmode" 0)
            (if (= (getvar "worlducs") 0)(progn (setq xest_all-2 (TAS:convert-list-ucs xest_all-1))) (setq xest_all-2 xest_all-1) )
            
            (create-plines (TA:list_rotate_left xest_all-2) "close" )
            (setvar "osmode" 1215)
          ;
        ;
        ;new_blk_entlast object
          (command "erase" sss_ename_ "")
          (setq pline_ename (entlast))
          (setq h (/ (getvar "VIEWSIZE") 10))
          (grdraw (polar (car (TA:list_rotate_left xest_all-2))  (deg-to-rad 45) h ) (polar (car (TA:list_rotate_left xest_all-2))  (deg-to-rad 225) h ) 30)
          (grdraw (polar (car (TA:list_rotate_left xest_all-2))  (deg-to-rad 135) h ) (polar (car (TA:list_rotate_left xest_all-2))  (deg-to-rad 315) h ) 30)
          ; (if (= (setq check_val_ (check-clockwise xest_all-1)) "Counter-clockwise")
          ;   (progn
          ;     (command "reverse" pline_ename "" )
          ;   )
          ; )
        ;
        
      ;
      
    )
    (defun TA:vertex_right_V2_ (sss_ename_ )
      ;reporcess vertex pt
        ; (setq sss_ename_ (car (nentsel "specify Object"))) 
        ;2nd process recrete vertex point
          (setq sss_ename_entget_ (entget sss_ename_))
          (setq sss_obj_ (vlax-ename->vla-object sss_ename_))
          (setq i 0)
          (setq sss_ename_vertex_ (vl-remove-if-not '(lambda (x) (= 10 (car x))) sss_ename_entget_))
          (setq sss_ename_vertex_ (mapcar 'cdr sss_ename_vertex_))
          (setq sss_ename_vertex_list_ (mapcar 
                                        '(lambda (x) 
                                            (car (cons x (setq i (+ i 1))))
                                          )
                                        sss_ename_vertex_
                                      )
          )
          (setvar "osmode" 0)
          (if (= (getvar "worlducs") 0)(progn (setq xest_all-2 (TAS:convert-list-ucs sss_ename_vertex_list_))) (setq xest_all-2 sss_ename_vertex_list_) )
          (setvar "osmode" 1215)
          (setq xest_all-2 (TA:list_rotate_left xest_all-2))
        ;
        ;while selection process
          (setq ERR_vertex_process_ nil)
          (while ;for keep insertion point and dist. fix length one side
            (and
              (= (vl-catch-all-error-p ERR_vertex_process_) nil)
            )
            (setq ERR_vertex_process_
              (vl-catch-all-apply
                (function
                  (lambda ()
                    (getstring "\nHit \nHit \nHit [ENTER] to continue...")
                    ;3rd
                      (setq h (/ (getvar "VIEWSIZE") 10))
                      (command "redraw")
                      (car (setq xest_all-2 (TA:list_rotate_left xest_all-2)))
                      (grdraw (polar (car xest_all-2)  (deg-to-rad 45) h ) (polar (car xest_all-2)  (deg-to-rad 225) h ) 30)
                      (grdraw (polar (car xest_all-2)  (deg-to-rad 135) h ) (polar (car xest_all-2)  (deg-to-rad 315) h ) 30)
                    ;
                  )
                )
              )
            )
          )
        ;
        ;final_result_
          (setq result_vertex_ xest_all-2)
        ;
      ;

      ; ;rebuild_pline_process
        (create-plines result_vertex_ "close" )  
        (command "erase" sss_ename_ "")
        (setq sss_ename_ (entlast))
      ;
      ;
      
    )
    
    (setq Er-msg_pline 
      (vl-catch-all-apply 
        (function 
          (lambda () 
            (setq ppline_ename_ (car (entsel "specify Object")))
          )
        )
      )
    )
    ;while selection process
      (setq ERR_ nil)
      (while ;for keep insertion point and dist. fix length one side
        (and
          (= (vl-catch-all-error-p ERR_) nil)
          (= (vl-catch-all-error-p Er-msg_pline) nil)
        )
        (setq ERR_
          (vl-catch-all-apply
            (function
              (lambda ()
                (setq time_tt (cond ( (getint (strcat "\nspecify get time \n<" (rtos (setq time_tt (cond (time_tt) (1.0) ) ) ) "> : " ) ) ) (time_tt) ) )
                (repeat (fix time_tt) 
                  (setq pline_vertex_new-data_ (TA:vertex_right_V2_ ppline_ename_))
                  (setq ppline_ename_ (entlast))
                )

              )
            )
          )
        )
      )
    ;
  )
  
  
  (defun c:PPLINE_CKST_insert_blk_polygon_inspol ()
    ;selection_set_for_fillter_blk_name
      (if  ;pre_select_ssget_or_post_select_ssget
        (=
          (setq ss_pre_filter_set_xx_ (ssget "i"
                                            (list
                                              (cons 0 "lwpolyline") ;type of object
                                              (cons 70 1) ;close assoc for lwpolyline
                                              ; (cons 8 "000 - GRID")   ;kind of layer
                                              ; (cons 2 "000-GRID_LINE_DYN")       ;kind of nameblock
                                              ; (cons 62 1)           ;kind of color call sign with color code index
                                            )
                                      )
                                      
          )
          nil
        ) 
        (progn
          (setq ss_pre_filter_set_xx_ (ssget
                                            (list
                                              (cons 0 "lwpolyline") ;type of object
                                              (cons 70 1) ;close assoc for lwpolyline   ;kind of layer
                                              ; (cons 2 "000-GRID_LINE_DYN")       ;kind of nameblock
                                              ; (cons 62 1)           ;kind of color call sign with color code index
                                            )
                                      )
          )
        )
        (sslength ss_pre_filter_set_xx_)
      )
    ;
    ;user_input_
      (setq namelist (list 
                      (setq block_0 "blank")
                      (setq block_1 "who_s_create_that_block-SOID")
                      (setq block_2 "who_s_create_that_block-RC")
                      (setq block_3 "who_s_create_that_block-deg45")
                      (setq block_4 "who_s_create_that_block-hatch-x-patt")
                      (setq block_5 "who_s_create_that_block-sand") 
                      (setq block_6 "who_s_create_that_block-metal")
                      (setq block_7 "who_s_create_that_block-ANSI35")
                      (setq block_8 "who_s_create_that_block-RC-PRECAST-1")
                      (setq block_9 "who_s_create_that_block-deg90")
                      (setq block_10 "who_s_create_that_block-RC-PLENUM-WALL")
                      (setq block_11 "who_s_create_that_block-BRICK-WALL")
                      (setq block_12 "010 - ALU_TRAY_PANEL_START-END_TZP-SHAPE_BOTTOM-VIEW")
                     )
      )
      (setq choose_block_di (cond ( (getint (strcat "\nSpecify block"
                                                    "\n1 = " block_1 
                                                    "\n2 = " block_2
                                                    "\n3 = " block_3
                                                    "\n4 = " block_4
                                                    "\n5 = " block_5 
                                                    "\n6 = " block_6 
                                                    "\n7 = " block_7 
                                                    "\n8 = " block_8 
                                                    "\n9 = " block_9 
                                                    "\n10 = " block_10
                                                    "\n11 = " block_11
                                                    "\n12 = " block_12
                                                    "\n<" 
                                                    (rtos 
                                                      (setq choose_block_di (cond 
                                                                              (choose_block_di)
                                                                              (1.0)
                                                                            )
                                                      )
                                                    )
                                                    "> : "
                                            ) ) ) (choose_block_di) ) )
    ;
    (setq distance_block-scaling_ (cond ( (getreal (strcat "\nspecify distance_block-scaling_ <" (rtos (setq distance_block-scaling_ (cond (distance_block-scaling_) (1) ) ) ) "> : " ) ) ) (distance_block-scaling_) ) )
    (setq angle-block (cond ( (getreal (strcat "\nspecify angle_ <" (rtos (setq angle-block (cond (angle-block) (0) ) ) ) "> : " ) ) ) (angle-block) ) )
    ;preloop_and_while
      (setq ss_pre_filter_set_xx_i 0)
      (setq ss_new_sec (ssadd))
      (while (< ss_pre_filter_set_xx_i (sslength ss_pre_filter_set_xx_))  
        (setq ss_pre_filter_set_xx_ename_ (ssname  ss_pre_filter_set_xx_ ss_pre_filter_set_xx_i))
        (setq ss_pre_filter_set_xx_obj_ (vlax-ename->vla-object  ss_pre_filter_set_xx_ename_))
        
        ; (cond
        ;   (;_case_1
        ;      (and
        ;         (= choose_block_di 1)
        ;      )
        ;      (progn
        ;        (setq new_set_ (TAS:polygon2dyn ss_pre_filter_set_xx_ename_ "who_s_create_that_block-SOID"))
        ;      )
        ;   )
        ;   (;_case_1
        ;      (and
        ;         (= choose_block_di 2)
        ;      )
        ;      (progn
        ;        (setq new_set_ (TAS:polygon2dyn ss_pre_filter_set_xx_ename_ "who_s_create_that_block-RC"))
        ;      )
        ;   )
        ;   (;_case_1
        ;      (and
        ;         (= choose_block_di 3)
        ;      )
        ;      (progn
        ;        (setq new_set_ (TAS:polygon2dyn ss_pre_filter_set_xx_ename_ "who_s_create_that_block-deg45"))
        ;      )
        ;   )
        ;   (;_case_1
        ;      (and
        ;         (= choose_block_di 4)
        ;      )
        ;      (progn
        ;        (setq new_set_ (TAS:polygon2dyn ss_pre_filter_set_xx_ename_ "who_s_create_that_block-hatch-x-patt"))
        ;      )
        ;   )
        ;   (;_case_1
        ;      (and
        ;         (= choose_block_di 5)
        ;      )
        ;      (progn
        ;        (setq new_set_ (TAS:polygon2dyn ss_pre_filter_set_xx_ename_ "who_s_create_that_block-sand"))
        ;      )
        ;   )
        ;   (;_case_1
        ;      (and
        ;         (= choose_block_di 5)
        ;      )
        ;      (progn
        ;        (setq new_set_ (TAS:polygon2dyn ss_pre_filter_set_xx_ename_ "who_s_create_that_block-sand"))
        ;      )
        ;   )
        ; )
        (setq new_set_ (TAS:polygon2dyn ss_pre_filter_set_xx_ename_ (nth (fix choose_block_di) namelist) distance_block-scaling_ angle-block))
        (setq ss_new_sec (ssadd new_set_ ss_new_sec))
        
        (LM:setdynpropvalue (vlax-ename->vla-object (entlast)) "visibility1" "1_fix")
        (cond
          (;_case_1
             (and
                (= (wcmatch (nth choose_block_di namelist) "*RC*") T)
                (/= (wcmatch (nth choose_block_di namelist) "*PRECAST*") T)
             )
             (progn
               (vl-catch-all-apply 
                 (function 
                   (lambda () 
                     (vla-put-layer (vlax-ename->vla-object (entlast)) 
                                    "000 - CONCRETE_COL_CUT_COLOR_5"
                     )
                   )
                 )
               )
               (princ "_case_1")
             )
          )
          (;_case_4
             (and
                (wcmatch (nth choose_block_di namelist) "*PRECAST*")
             )
             (progn
               (vl-catch-all-apply 
                 (function 
                   (lambda () 
                     (vla-put-layer (vlax-ename->vla-object (entlast)) 
                                    "000 - EXISTING_PRECAST_CUT_COLOR_4"
                     )
                   )
                 )
               )
               (princ "_case_4")
             )
          )
        )
        
        (setq ss_pre_filter_set_xx_i (+ ss_pre_filter_set_xx_i 1))
      )
    ;
    (command "pselect"  ss_new_sec "" )
  )
  ; (defun c:spoltemp_rotate_vertex ()
  ;   (setq spol_ename_ (car (entsel "specify Object")))
  ;   (setq spol_obj_ (vlax-ename->vla-object spol_ename_))
  ;   (setq spol_obj_position_xy_list (LM:getdynprops spol_obj_))
  ;   (setq spol_obj_position_xy_list_filter_
  ;     (vl-remove-if-not
  ;       '(lambda (x)
  ;         (wcmatch (car x) "*Position*")
  ;       )
  ;       spol_obj_position_xy_list  
  ;     )
  ;   )
  ;   ;preloop_and_while
  ;     (setq spol_obj_position_xy_list_filter_i 0)
  
  ;     (setq blank_position_list ())
  ;     (setq new_position_list ())
  ;     (setq new_position_list (cons (setq spol_obj_position_xy_list_filter_valx_ (nth  spol_obj_position_xy_list_filter_i spol_obj_position_xy_list_filter_)) new_position_list))
  ;     (setq new_position_list (cons (setq spol_obj_position_xy_list_filter_valy_ (nth  (+ spol_obj_position_xy_list_filter_i 1) spol_obj_position_xy_list_filter_)) new_position_list))
      
  ;     (while (< spol_obj_position_xy_list_filter_i (length spol_obj_position_xy_list_filter_))
  ;       (setq spol_obj_position_xy_list_filter_valx_ (nth  spol_obj_position_xy_list_filter_i spol_obj_position_xy_list_filter_))
  ;       (setq spol_obj_position_xy_list_filter_valy_ (nth  (+ spol_obj_position_xy_list_filter_i 1) spol_obj_position_xy_list_filter_))
        
  ;       (if (and 
  ;             (/= spol_obj_position_xy_list_filter_i 0)
  ;             (/= (cdr spol_obj_position_xy_list_filter_valx_) (cdr (nth  (- spol_obj_position_xy_list_filter_i 2) spol_obj_position_xy_list_filter_)))
  ;             (/= (cdr spol_obj_position_xy_list_filter_valy_) (cdr (nth  (- spol_obj_position_xy_list_filter_i 1) spol_obj_position_xy_list_filter_)))
  ;           )
  ;         (progn
  ;           (setq new_position_list (cons spol_obj_position_xy_list_filter_valx_ new_position_list ))
  ;           (setq new_position_list (cons spol_obj_position_xy_list_filter_valy_ new_position_list ))
  ;         )
  ;       )
  ;       (if (and 
  ;             (/= spol_obj_position_xy_list_filter_i 0)
  ;             (= (cdr spol_obj_position_xy_list_filter_valx_) (cdr (nth  (- spol_obj_position_xy_list_filter_i 2) spol_obj_position_xy_list_filter_)))
  ;             (= (cdr spol_obj_position_xy_list_filter_valy_) (cdr (nth  (- spol_obj_position_xy_list_filter_i 1) spol_obj_position_xy_list_filter_)))
  ;           )
  ;         (progn
  ;           (setq blank_position_list (cons spol_obj_position_xy_list_filter_valx_ blank_position_list ))
  ;           (setq blank_position_list (cons spol_obj_position_xy_list_filter_valy_ blank_position_list ))
  ;         )
  ;       )
  ;       (setq spol_obj_position_xy_list_filter_i (+ spol_obj_position_xy_list_filter_i 2))
  ;     )
  ;   ;
  ;   (setq new_position_list (reverse new_position_list))
  ;   (setq blank_position_list (reverse blank_position_list))
  ;   (setq spol_obj_position_xy_list_new_ro1_ (TA:list_rotate_right new_position_list ))
  ;   (setq spol_obj_position_xy_list_new_ro2_ (TA:list_rotate_right spol_obj_position_xy_list_new_ro1_ ))
    
  ; )
  (defun TAS:PPLINE_CKST_fixxy_fixpol (new_obj_)
    ; (setq new_obj_ (vlax-ename->vla-object (ssname (ssget) 0)))
    (setq new_obj_dynlist_ (LM:getdynprops new_obj_ ))
    ;preloop_and_while
      (setq new_obj_dynlist_tag_i 0)
      (while (< new_obj_dynlist_tag_i (length new_obj_dynlist_))
        (setq new_obj_dynlist_tag_ (car (nth  new_obj_dynlist_tag_i new_obj_dynlist_)))
        (setq new_obj_dynlist_val_ (cdr (nth  new_obj_dynlist_tag_i new_obj_dynlist_)))
        (if (/= new_obj_dynlist_tag_ "Visibility1")
          (progn
            (LM:setdynpropvalue new_obj_ new_obj_dynlist_tag_ (LM:round new_obj_dynlist_val_))
          )
        )
        
    
        (setq new_obj_dynlist_tag_i (+ new_obj_dynlist_tag_i 1))
      )
    ;
  )
  (defun c:PPLINE_CKST_fixxy_fixpol ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ; (setq ss_pre_filter_set_xx_ (TA:EF_Filter_ss_set_v2_ ss_pre_filter_set_xx_ 
      ;                               (list 
      ;                                 "W-1-PP19-AR-4150-01-A_000_MATTERIAL_AHP_TYPE-BUTWEEN-COL-MUL-TRAPEZOLID_VA_DYN_TOPVIEW"
      ;                                 "who_s_create_that_block-RC"
      ;                               )
      ;                             )
            
      ; )
    ;
    
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (= (wcmatch (strcase (LM:Effectivename ss_pre_filter_set_xx_obj_)) "*WHO*") T)
          (progn
            (TAS:PPLINE_CKST_fixxy_fixpol ss_pre_filter_set_xx_obj_)
          )
        )
        
        (setq ss_pre_filter_set_xx_i (+ ss_pre_filter_set_xx_i 1))
      )
    ;
    
  )


;
;PPLINE_CKST_COUNTING SPLICE EXTRUSION FUNC_
  (defun c:PPLINE_CKST_COUNTING_TYPE1 ( / ent obj txt pos cnt)
    ;Note By Code_Developer
    ;Nominal counting process block type1
    ;while selection process
      (setq ERR_ nil)
      (while ;for keep insertion point and dist. fix length one side
        (and
          (= (vl-catch-all-error-p ERR_) nil)
        )
        (setq ERR_
          (vl-catch-all-apply
            (function
              (lambda ()
                ;selection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)
                  )
                  (setq ss_pre_filter_set_xx_ (TA:EF_Filter_ss_set_V2_ ss_pre_filter_set_xx_ (list "A$Cf6525e95") ) )
                ;
                ;asdasdasdas
                  (create-text-vla 
                    (vlax-3d-point (getpoint "specify point"))
                    (strcat "splice = " (rtos (- (sslength ss_pre_filter_set_xx_) 1) 2 0))
                    50
                    0
                  )
                ;
              )
            )
          )
        )
      )
    ;
  )
  (defun c:PPLINE_CKST_COUNTING_TYPE2 ( / ent obj txt pos cnt)
    ;Note By Code_Developer
    ;Nominal counting process block type1
    ;while selection process
      (setq ERR_ nil)
      (while ;for keep insertion point and dist. fix length one side
        (and
          (= (vl-catch-all-error-p ERR_) nil)
        )
        (setq ERR_
          (vl-catch-all-apply
            (function
              (lambda ()
                ;presetting
                  ; (setq counting_endpoint (getpoint "specify end point"))
                  (setq 1st-point_ (getpoint "specify point"))
                  (if (< (rad-to-deg (angle 1st-point_ counting_endpoint )) 45)
                    (progn
                      (setq 2nd_point (list 
                                        (car counting_endpoint)
                                        (cadr 1st-point_)
                                        0
                                      )
                      )
                    )
                      (setq 2nd_point (list 
                                        (car 1st-point_)
                                        (cadr counting_endpoint)
                                        0
                                      )
                      )
                  )
                  
                ; 
                ; (command "line" 1st-point_ 2nd_point)
                ;selection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget "F" (list 1st-point_ 2nd_point)
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)  
                  )
                ;
                ;asdasdasdas
                  (create-text-vla 
                    (vlax-3d-point 1st-point_)
                    (strcat "splice = " (rtos (- (sslength ss_pre_filter_set_xx_) 1) 2 0))
                    50
                    0
                  )
                ;
              )
            )
          )
        )
      )
    ;
  )
  (defun c:PPLINE_CKST_COUNTING_local-var_for_endpoint ()
    ;presetting
      (setq counting_endpoint (getpoint "specify end point"))

  )
  (defun c:PPLINE_CKST_COUNTING_sumtext1 ()
    (defun KeepNumber (str /)
      (vl-list->string
        (vl-remove-if-not
          '(lambda (c) (and (>= c 48) (<= c 57)))
          (vl-string->list str)
        )
      )
    )
    ;selection_set_for_fillter_blk_name
      (if  ;pre_select_ssget_or_post_select_ssget
        (=
          (setq ss_pre_filter_set_xx_ (ssget "i"
                                            (list
                                              (cons 0 "text") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "text") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (setq sum 0)
      (setq sumlist ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (vla-get-objectname ss_pre_filter_set_xx_obj_ ) "AcDbText" )
              (= (wcmatch (vla-get-textstring ss_pre_filter_set_xx_obj_) "*splice*") T )
              (= (wcmatch (STRCASE (vla-get-textstring ss_pre_filter_set_xx_obj_)) "*PP*") T )
            )
          (progn
            (setq tempsum (atoi (KeepNumber  (setq txt-list (substr (vla-get-textstring ss_pre_filter_set_xx_obj_) (+ (vl-string-search "=" (setq oldtext (vla-get-textstring ss_pre_filter_set_xx_obj_)) 1) 2) 50)) )))
            (setq sumlist (cons oldtext sumlist ))
            (length sumlist)
            (setq sum (+ tempsum sum))
          )
        )
        (setq ss_pre_filter_set_xx_i (+ ss_pre_filter_set_xx_i 1))
      )
      (create-text-vla 
        (vlax-3d-point (getpoint "specify point"))
        (strcat "splice OVERALL = " (rtos (- sum 1) 2 0))
        5000
        0
      )
    ;
  )
  (defun c:PPLINE_CKST_COUNTING_sumtext2 ()
    (setq prefix_station "PP17")
    (setq prefix_floor "PLAT")
    (setq temptext_ename_ (car (entsel "specify Object")))
    (setq temptext_obj_ (vlax-ename->vla-object temptext_ename_))
    (vla-put-textstring temptext_obj_ (strcat prefix_station "_" prefix_floor "_" (vla-get-textstring temptext_obj_)))
  )
;
;PURPLE_LINE_CSKT_TTB
  (defun c:PPLINE_CKST_UPDATE_WORKING_DRAWING_CKSTUPWDTB ()
    ;presetting
      (setq new_start_numbering_ 100) ;user_input_in_code
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_v2_ ss_pre_filter_set_xx_ (list "Title Block_Under Ground_C1 v3")))
    ;
    ;preloop_and_while
      (setq ss_pre_filter_set_xx_i 0)
      (setq new_pre_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq new_pre_
          (cons (list 
                  ss_pre_filter_set_xx_obj_ins_
                  ss_pre_filter_set_xx_ename_
                )
            new_pre_
          )
        )
        (setq ss_pre_filter_set_xx_i (+ ss_pre_filter_set_xx_i 1))
      )
    ;
    (setq new_sort_ (TA:corrd_sorting_group new_pre_ 1))
    ;preloop_and_while
      (setq new_sort_i 0)
      (setq new_numbering_ new_start_numbering_)
      (while (< new_sort_i (length new_sort_))
        (setq new_sort_group_list_ (nth  new_sort_i new_sort_))
        ;preloop_and_while
          (setq new_sort_group_list_i 0)
          (while (< new_sort_group_list_i (length new_sort_group_list_))
            (setq new_sort_group_list_ename_ (cadr (nth  new_sort_group_list_i new_sort_group_list_)))
            
            (setq new_sort_group_list_obj_ (vlax-ename->vla-object  new_sort_group_list_ename_))
            (setq EX_SHEET_NO_VAL (LM:vl-getattributevalue new_sort_group_list_obj_ "SHEET_NO_VAL" ))
            (LM:vl-setattributevalue new_sort_group_list_obj_ "SHEET_NO_VAL" (strcat 
                                                                                EX_SHEET_NO_VAL
                                                                                (rtos (+ new_numbering_ 1) 2 0)
                                                                             )
            )
            (setq new_numbering_ (+ new_numbering_ 1))
            (setq new_sort_group_list_i (+ new_sort_group_list_i 1))
          )
        ; 
        (setq new_sort_i (+ new_sort_i 1))
      )
    ;
    
  )
;
;PURPLE_LINE_CKST

  (defun c:PPLINE_CKST_CKO () 
      ;selection_set_for_fillter_blk_name
        (if  ;pre_select_ssget_or_post_select_ssget
          (=
            (setq ss_pre_filter_set_xx_ (ssget "i"
                                              (list
                                                (cons 0 "mtext") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "mtext") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq list_file_val_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          
          (setq ss_pre_filter_set_xx_obj_strtext_ (vla-get-textstring ss_pre_filter_set_xx_obj_))
          (setq dwg 
            (strcat "C:\\TA\\TA_WORK\\MASS TRANSIT\\PPLINE CKST\\PP22 CSD\\" 
                    "C-" 
                    ss_pre_filter_set_xx_obj_strtext_ 
                    "-A" 
                    ".dwg"
            )
          )
          (setq list_file_val_ (cons dwg list_file_val_ ))
          (setq ss_pre_filter_set_xx_i (+ ss_pre_filter_set_xx_i 1))
        )
      ;

      (foreach x list_file_val_
        (vla-Open (vla-get-Documents (vlax-get-Acad-Object)) 
                x
                (if ReadOnly :vlax-true :vlax-false)
        )
      )
    ;(command "fileopen" dwg) ; open case delete existing
  )
  (defun c:PPLINE_CKST_CSDvis ()
    ;create visibility process
      (setq userinput_pt (list 500 500 0))
      (command "bparameter"  "v"  userinput_pt ""  )
      (command "-Bvstate" "n" "1_" "c")
      (setq new_vis_ss_pre_filter_set_xx_ (ssadd))
    ;
    
    (setq cons8 "A-ANNO-MATC,G-ANNO-SYMB,A-_ANOTTRGT_--,A-_ANOTSYBL_P-,A-ANNO-SYMB")
    ;blk process
      ;selection_set_for_fillter_blk_name
        (if  ;pre_select_ssget_or_post_select_ssget
          (=
            (setq ss_pre_filter_set_xx_ (ssget "X"
                                              (list
                                                (cons 0 "insert") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
            nil
          )
          (progn
            (setq ss_pre_filter_set_xx_ (ssget "X"
                                              (list
                                                (cons 0 "insert") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq new_vis_ss_pre_filter_set_xx_ (ssadd))
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if (or   
                (= (wcmatch (strcase (LM:effectivename ss_pre_filter_set_xx_obj_ )) (strcase (strcat "*" "Object ID"  "*"    ))) T)
                (= (wcmatch (strcase (LM:effectivename ss_pre_filter_set_xx_obj_ )) (strcase (strcat "*" "GRID"  "*"    ))) T)
                (= (wcmatch (strcase (LM:effectivename ss_pre_filter_set_xx_obj_ )) (strcase (strcat "*" "-AR-"  "*"    ))) T)
                (= (wcmatch (strcase (LM:effectivename ss_pre_filter_set_xx_obj_ )) (strcase (strcat "*" "-SE-"  "*"    ))) T)
                ;(= (wcmatch (strcase (LM:effectivename ss_pre_filter_set_xx_obj_ )) (strcase (strcat "*" "-C-"  "*"    ))) T)
              )
            (progn
              (setq new_vis_ss_pre_filter_set_xx_ (ssadd ss_pre_filter_set_xx_ename_ new_vis_ss_pre_filter_set_xx_)) 
            )
          )
          
          (setq ss_pre_filter_set_xx_i (+ ss_pre_filter_set_xx_i 1))
        )
      ;
    ;
    ;normie obj process
      ;selection_set_for_fillter_blk_name
        (if  ;pre_select_ssget_or_post_select_ssget
          (=
            (setq ss_pre_filter_set_xx_ (ssget "X"
                                              (list
                                                (cons 0 "text,mtext,line,lwpolyline,polyline,hatch,circle,dimension") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
            nil
          )
          (progn
            (setq ss_pre_filter_set_xx_ (ssget "X"
                                              (list
                                                (cons 0 "text,mtext,line,lwpolyline,polyline,hatch,circle,dimension") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (setq new_vis_ss_pre_filter_set_xx_ (ssadd ss_pre_filter_set_xx_ename_ new_vis_ss_pre_filter_set_xx_))
          (setq ss_pre_filter_set_xx_i (+ ss_pre_filter_set_xx_i 1))
        )
      ;
    ;
    (command "bvhide" new_vis_ss_pre_filter_set_xx_  "" "c")
  )
  (defun c:PPLINE_CKST_CSDVilter_ ()
    (setq cons8 "A-ANNO-MATC,G-ANNO-SYMB,A-_ANOTTRGT_--,A-_ANOTSYBL_P-,A-ANNO-SYMB")
    ;blk process
      ;selection_set_for_fillter_blk_name
        (if  ;pre_select_ssget_or_post_select_ssget
          (=
            (setq ss_pre_filter_set_xx_ (ssget "X"
                                              (list
                                                (cons 0 "insert") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
            nil
          )
          (progn
            (setq ss_pre_filter_set_xx_ (ssget "X"
                                              (list
                                                (cons 0 "insert") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if (or   
                (= (wcmatch (strcase (LM:effectivename ss_pre_filter_set_xx_obj_ )) (strcase (strcat "*" "Object ID"  "*"    ))) T)
                (= (wcmatch (strcase (LM:effectivename ss_pre_filter_set_xx_obj_ )) (strcase (strcat "*" "GRID"  "*"    ))) T)
                (= (wcmatch (strcase (LM:effectivename ss_pre_filter_set_xx_obj_ )) (strcase (strcat "*" "-AR-"  "*"    ))) T)
                (= (wcmatch (strcase (LM:effectivename ss_pre_filter_set_xx_obj_ )) (strcase (strcat "*" "-SE-"  "*"    ))) T)
                ;(= (wcmatch (strcase (LM:effectivename ss_pre_filter_set_xx_obj_ )) (strcase (strcat "*" "-C-"  "*"    ))) T)
              )
            (progn
              (vla-move ss_pre_filter_set_xx_obj_  (vlax-3d-point 0 0 0) (vlax-3d-point 0 -50000 0) )
            )
          )
          
          (setq ss_pre_filter_set_xx_i (+ ss_pre_filter_set_xx_i 1))
        )
      ;
    ;
    ;normie obj process
      ;selection_set_for_fillter_blk_name
        (if  ;pre_select_ssget_or_post_select_ssget
          (=
            (setq ss_pre_filter_set_xx_ (ssget "X"
                                              (list
                                                (cons 0 "text,mtext,line,lwpolyline,polyline,hatch,circle,dimension") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
            nil
          )
          (progn
            (setq ss_pre_filter_set_xx_ (ssget "X"
                                              (list
                                                (cons 0 "text,mtext,line,lwpolyline,polyline,hatch,circle,dimension") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (vla-move ss_pre_filter_set_xx_obj_  (vlax-3d-point 0 0 0) (vlax-3d-point 0 -50000 0) )
          (setq ss_pre_filter_set_xx_i (+ ss_pre_filter_set_xx_i 1))
        )
      ;
    ;
  )
  (defun c:PPLINE_CKST_CSDfilter_ ()
    (setq cons8 "A-ANNO-MATC,G-ANNO-SYMB,A-_ANOTTRGT_--,A-_ANOTSYBL_P-")
    ;blk process
      ;selection_set_for_fillter_blk_name
        (if  ;pre_select_ssget_or_post_select_ssget
          (=
            (setq ss_pre_filter_set_xx_ (ssget "X"
                                              (list
                                                (cons 0 "insert") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
            nil
          )
          (progn
            (setq ss_pre_filter_set_xx_ (ssget "X"
                                              (list
                                                (cons 0 "insert") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i)) 
          (setq ss_pre_filter_set_xx_obj_ (vlax-ename->vla-object ss_pre_filter_set_xx_ename_))
          (if (or   
                (= (wcmatch (strcase (LM:effectivename ss_pre_filter_set_xx_obj_ )) (strcase (strcat "*" "Object ID"  "*"    ))) T)
                (= (wcmatch (strcase (LM:effectivename ss_pre_filter_set_xx_obj_ )) (strcase (strcat "*" "GRID"  "*"    ))) T)
                (= (wcmatch (strcase (LM:effectivename ss_pre_filter_set_xx_obj_ )) (strcase (strcat "*" "-AR-"  "*"    ))) T)
                (= (wcmatch (strcase (LM:effectivename ss_pre_filter_set_xx_obj_ )) (strcase (strcat "*" "-SE-"  "*"    ))) T)
                ;(= (wcmatch (strcase (LM:effectivename ss_pre_filter_set_xx_obj_ )) (strcase (strcat "*" "-C-"  "*"    ))) T)
              )
            (progn
              (vla-move ss_pre_filter_set_xx_obj_  (vlax-3d-point 0 0 0) (vlax-3d-point 0 50000 0) )
            )
          )
          
          (setq ss_pre_filter_set_xx_i (+ ss_pre_filter_set_xx_i 1))
        )
      ;
    ;
    ;normie obj process
      ;selection_set_for_fillter_blk_name
        (if  ;pre_select_ssget_or_post_select_ssget
          (=
            (setq ss_pre_filter_set_xx_ (ssget "X"
                                              (list
                                                (cons 0 "text,mtext,line,lwpolyline,polyline,hatch,circle,dimension") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
            nil
          )
          (progn
            (setq ss_pre_filter_set_xx_ (ssget "X"
                                              (list
                                                (cons 0 "text,mtext,line,lwpolyline,polyline,hatch,circle,dimension") ;type of object
                                                (cons -4 "<NOT")
                                                (cons 8 cons8) 
                                                (cons -4 "NOT>")
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (vla-move ss_pre_filter_set_xx_obj_  (vlax-3d-point 0 0 0) (vlax-3d-point 0 50000 0) )
          (setq ss_pre_filter_set_xx_i (+ ss_pre_filter_set_xx_i 1))
        )
      ;
    ;
  )
  (defun c:PPLINE_CKST_CK1RENBLK ()
    (setq namefile_ (getvar "dwgname"))
    (setq blk_ename_ (car (entsel "specify Object")))
    (setq blk_obj_ (vlax-ename->vla-object blk_ename_))
    (setq efname_ (LM:effectivename blk_obj_))
    
    (command "rename" "b" efname_ (LM:StringSubst "" ".dwg" (strcat namefile_ "_CSD-PLAN")) )
  )
  (defun c:PPLINE_CKST_XCV1RENBLK () 
    ;selection_set_for_fillter_blk_name
      (if  ;pre_select_ssget_or_post_select_ssget
        (=
          (setq sstarget_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          ; (setq sstarget_ (ssget
          ;                                   (list
          ;                                     ; (cons 0 "INSERT") ;type of object
          ;                                     ; (cons 8 "000 - GRID")   ;kind of layer
          ;                                     ; (cons 2 "000-GRID_LINE_DYN")       ;kind of nameblock
          ;                                     ; (cons 62 1)           ;kind of color call sign with color code index
          ;                                   )
          ;                             )
          ; )
          G1 ;temp
        )
        (sslength sstarget_)
      )
    ;
    (setvar "osmode" 41)
    (setq pttarget_ (getpoint "specify point for basepoint"))
    (setvar "osmode" 1215)
    (setq namefile_ (getvar "dwgname"))
    (command "_block"   (LM:StringSubst "" ".dwg" (strcat namefile_ "_CSD-PLAN")) pttarget_  sstarget_ "" )
    (TA:vla-insertblock 
      (LM:StringSubst "" ".dwg" (strcat namefile_ "_CSD-PLAN")) 
      pttarget_
      1
      0
    )
    ;new_blk_entlast object
      (setq sss_ename (entlast))
      (setq sss_obj (vlax-ename->vla-object sss_ename))
      (command "_copybase" pttarget_ sss_ename ""    )
    ;
  )
  (defun c:PPLINE_CKST_blockname_finder_csdfind ()
    (if  ;pre_select_ssget_or_post_select_ssget
      (=
        (setq ss_pre_filter_set_xx_ (ssget "x"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (TA:blockname_finder_ ss_pre_filter_set_xx_ 1 (list "CSD-PLAN"))
    (command "pselect"  selection_target_ "" )
  )
  (defun c:PPLINE_CKST_addCSD_ ()
    (command "-layer" ;
            "filter" ;
            "edit" ;
            "CSD" ; (Filter name must be sensitibe case)
            "add" ;
            "*000 - CSD*" ;(add layer name to filter, Can use wildcard for adding)
            "x" "" ;
    )
  )
;
;Method Installation
  (defun c:z63A_text2att () 
    (setq abx_ (entget (car (entsel))))
    (setq abx_ename (cdr (assoc -1 abx_)))
    (setq abx_obj (vlax-ename->vla-object abx_ename))
    ; (setq abx_dump (vlax-dump-object abx_obj))
    (setq abx_obj_text (vla-get-textstring abx_obj))
    (setq abx_obj_text_+val (strcat abx_obj_text "_value"))
    (setq att_xyz-ins (getpoint))

    (command "-attdef" "L" "" abx_obj_text_+val "" "----" "S" "Cetury Gothic" "J" "MC" att_xyz-ins 0)
    (setq att_last_ (entlast))
    (setq att_last_obj (vlax-ename->vla-object att_last_))
    (vla-put-height att_last_obj 1.8)
  )
  (defun c:MATTERIAL_BOX_INCREMENT_NUMBER_MATINC ()

    ;user_input_axis
      (initget "X Y")
      (setq ss_ ;Detect the variable's result in case of a function error
        (vl-catch-all-apply 
          (function 
            (lambda () 
              (setq axis_sort (not (eq "Y" (getkword "\nKeep Existing point with object? [X/Y] <X>: "))))
            )
          )
        )
      )
      (if (= axis_sort T)
        (progn
          (setq axis_sort "X")
        )
        (setq axis_sort "Y")
      )
    ;
    ;user_input_
      (setq increment_number_ (cond ( (getint (strcat "\nSpecify increment_number_   <" (rtos (setq increment_number_ (cond (increment_number_) (1.0) ) ) ) "> : " ) ) ) (increment_number_) ) )
    ;
    ;user_att_in_code_line_
      (setq att_name_1 "NO.BUBBLE_VALUE_1")
      (setq att_name_2 "NO_VALUE_1")
      (setq efname_blk "000 - DYNAMIC_SYMBOL_FAMELINE_MATTERIAL_BOX_AND_BUBBLE" )
    ;

    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget 
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;filter_and_sort_selection_by_efname_
      (setq ss_pre_filter_set_xx_ (TA:EF_Filter_ss_set_ ss_pre_filter_set_xx_ efname_blk))
      (setq ss_pre_filter_set_xx_sorted_ (reverse (TA:standard_list_croodinate_sorting ss_pre_filter_set_xx_ axis_sort )))
    ;
    ;preloop_and_while
      (setq ss_pre_filter_set_xx_sorted_i 0)
      (while (< ss_pre_filter_set_xx_sorted_i (length ss_pre_filter_set_xx_sorted_))
        (setq ss_pre_filter_set_xx_sorted_ename_ (car (nth  ss_pre_filter_set_xx_sorted_i ss_pre_filter_set_xx_sorted_)))
        (setq ss_pre_filter_set_xx_sorted_obj_ (vlax-ename->vla-object ss_pre_filter_set_xx_sorted_ename_))
        
        (LM:vl-setattributevalue ss_pre_filter_set_xx_sorted_obj_ att_name_1 increment_number_ )
        (LM:vl-setattributevalue ss_pre_filter_set_xx_sorted_obj_ att_name_2 increment_number_ )
        
        
        (setq increment_number_ (+ increment_number_ 1))
        (setq ss_pre_filter_set_xx_sorted_i (+ ss_pre_filter_set_xx_sorted_i 1))
      )
    ;
  )
  (defun c:mtext_renumber_mtre_ ()
    

    (setq old_numtext (getstring "specify old_numtext <" old_numtext ">:"))
    (setq new_numtext (getstring "specify new_numtext"))
    (setq mtext_ename_ (car (entsel "specify Object")))
    (setq mtext_obj_ (vlax-ename->vla-object mtext_ename_))

    (setq mtext_obj_textstring_ (vla-get-textstring mtext_obj_))
    (setq old (strcat ";" old_numtext "."))
    (setq new (strcat ";" new_numtext "."))

    (vla-put-textstring mtext_obj_ (LM:StringSubst  new old mtext_obj_textstring_ ))
  )
;

(defun c:Hatch_to_Excel_H2Excel ()
  ;selection_set_for_fillter_blk_name
    (if  ;pre_select_ssget_or_post_select_ssget
      (=
        (setq ss_pre_filter_set_xx_ (ssget "i"
                                          (list
                                            (cons 0 "HATCH") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "HATCH") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq patt_name_mainlist_ ())
    (setq patt_name_name_hatch_list_ ())
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      
      (setq ss_pre_filter_set_xx_obj_patt_name_ (vla-get-patternname ss_pre_filter_set_xx_obj_))
      (setq ss_pre_filter_set_xx_obj_Harea_ (/ (vla-get-area ss_pre_filter_set_xx_obj_) 1000000 ))
      
      (setq patt_name_name_hatch_list_ (cons  ss_pre_filter_set_xx_obj_patt_name_ patt_name_name_hatch_list_))
      (setq patt_name_sublist_ (list ss_pre_filter_set_xx_obj_patt_name_ ss_pre_filter_set_xx_obj_Harea_  ))
      (setq patt_name_mainlist_ (cons patt_name_sublist_ patt_name_mainlist_))
      
      (setq ss_pre_filter_set_xx_i (+ ss_pre_filter_set_xx_i 1))
    )
  ;
  ;preloop_and_while
    (setq mainlist_Ceiling (list 
                            "000_C01"
                            "000_C02"
                            "000_C03"
                            "000_C04"
                            "000_C05"
                            "000_C05A"
                            "000_C06"
                            "000_C07"
                            "000_C08"
                            "000_C09"
                            "000_C10"
                            "000_C11"
                            "000_C12"
                            "000_W01"
                            "000_W02"
                            "000_W03"
                            "000_W04"
                            "000_W05"
                            "000_W06"
                            "000_W07"
                            "000_W08"
                            "000_W09"
                            "000_W10"
                            "000_W11"
                            "000_W12"
                            "000_W13"
                            "000_W14"
                            "000_W15"
                            "000_W16"
                            "000_W17"
                            "000_W18"
                            "000_W19"
                            "000_W20"
                            "000_W21"
                            "000_W22"
                           )
    )
    (setq patt_name_mainlist_area_C01 0
          patt_name_mainlist_area_C02 0
          patt_name_mainlist_area_C03 0
          patt_name_mainlist_area_C04 0
          patt_name_mainlist_area_C05 0
          patt_name_mainlist_area_C05A 0
          patt_name_mainlist_area_C06 0
          patt_name_mainlist_area_C07 0
          patt_name_mainlist_area_C08 0
          patt_name_mainlist_area_C09 0
          patt_name_mainlist_area_C10 0
          patt_name_mainlist_area_C11 0
          patt_name_mainlist_area_C12 0
          patt_name_mainlist_area_W01 0
          patt_name_mainlist_area_W02 0
          patt_name_mainlist_area_W03 0
          patt_name_mainlist_area_W04 0
          patt_name_mainlist_area_W05 0
          patt_name_mainlist_area_W06 0
          patt_name_mainlist_area_W07 0
          patt_name_mainlist_area_W08 0
          patt_name_mainlist_area_W09 0
          patt_name_mainlist_area_W10 0
          patt_name_mainlist_area_W11 0
          patt_name_mainlist_area_W12 0
          patt_name_mainlist_area_W13 0
          patt_name_mainlist_area_W14 0
          patt_name_mainlist_area_W15 0
          patt_name_mainlist_area_W16 0
          patt_name_mainlist_area_W17 0
          patt_name_mainlist_area_W18 0
          patt_name_mainlist_area_W19 0
          patt_name_mainlist_area_W20 0
          patt_name_mainlist_area_W21 0
          patt_name_mainlist_area_W22 0
    )
    ;preloop_and_while
      (setq patt_name_mainlist_i 0)
      (while (< patt_name_mainlist_i (length patt_name_mainlist_))
        (setq patt_name_mainlist_name_ (car (nth  patt_name_mainlist_i patt_name_mainlist_)))
        (setq patt_name_mainlist_area_ (cadr (nth  patt_name_mainlist_i patt_name_mainlist_)))
          (cond 
            ( ;Harea_case_0
            (and (= patt_name_mainlist_name_ (nth 0 mainlist_Ceiling)))
            (progn (setq patt_name_mainlist_area_C01 (+ patt_name_mainlist_area_C01 patt_name_mainlist_area_)))
            )
            ( ;Harea_case_1
            (and (= patt_name_mainlist_name_ (nth 1 mainlist_Ceiling)))
            (progn (setq patt_name_mainlist_area_C02 (+ patt_name_mainlist_area_C02 patt_name_mainlist_area_)))
            )
            ( ;Harea_case_2
            (and (= patt_name_mainlist_name_ (nth 2 mainlist_Ceiling)))
            (progn (setq patt_name_mainlist_area_C03 (+ patt_name_mainlist_area_C03 patt_name_mainlist_area_)))
            )
            ( ;Harea_case_3
            (and (= patt_name_mainlist_name_ (nth 3 mainlist_Ceiling)))
            (progn (setq patt_name_mainlist_area_C04 (+ patt_name_mainlist_area_C04 patt_name_mainlist_area_)))
            )
            ( ;Harea_case_4
            (and (= patt_name_mainlist_name_ (nth 4 mainlist_Ceiling)))
            (progn (setq patt_name_mainlist_area_C05 (+ patt_name_mainlist_area_C05 patt_name_mainlist_area_)))
            )
            ( ;Harea_case_5
            (and (= patt_name_mainlist_name_ (nth 5 mainlist_Ceiling)))
            (progn (setq patt_name_mainlist_area_C05A (+ patt_name_mainlist_area_C05A patt_name_mainlist_area_)))
            )
            ( ;Harea_case_6
            (and (= patt_name_mainlist_name_ (nth 6 mainlist_Ceiling)))
            (progn (setq patt_name_mainlist_area_C06 (+ patt_name_mainlist_area_C06 patt_name_mainlist_area_)))
            )
            ( ;Harea_case_7
            (and (= patt_name_mainlist_name_ (nth 7 mainlist_Ceiling)))
            (progn (setq patt_name_mainlist_area_C07 (+ patt_name_mainlist_area_C07 patt_name_mainlist_area_)))
            )
            ( ;Harea_case_8
            (and (= patt_name_mainlist_name_ (nth 8 mainlist_Ceiling)))
            (progn (setq patt_name_mainlist_area_C08 (+ patt_name_mainlist_area_C08 patt_name_mainlist_area_)))
            )
            ( ;Harea_case_9
            (and (= patt_name_mainlist_name_ (nth 9 mainlist_Ceiling)))
            (progn (setq patt_name_mainlist_area_C09 (+ patt_name_mainlist_area_C09 patt_name_mainlist_area_)))
            )
            ( ;Harea_case_10
            (and (= patt_name_mainlist_name_ (nth 10 mainlist_Ceiling)))
            (progn (setq patt_name_mainlist_area_C10 (+ patt_name_mainlist_area_C10 patt_name_mainlist_area_)))
            )
            ( ;Harea_case_11
            (and (= patt_name_mainlist_name_ (nth 11 mainlist_Ceiling)))
            (progn (setq patt_name_mainlist_area_C11 (+ patt_name_mainlist_area_C11 patt_name_mainlist_area_)))
            )
            ( ;Harea_case_12
            (and (= patt_name_mainlist_name_ (nth 12 mainlist_Ceiling)))
            (progn (setq patt_name_mainlist_area_C12 (+ patt_name_mainlist_area_C12 patt_name_mainlist_area_)))
            )
            ( ;Harea_case_W1
            (and (= patt_name_mainlist_name_ (nth 13 mainlist_Ceiling)))
            (progn (setq patt_name_mainlist_area_W01 (+ patt_name_mainlist_area_W01 patt_name_mainlist_area_)))
            )
            ( ;Harea_case_W2
            (and (= patt_name_mainlist_name_ (nth 14 mainlist_Ceiling)))
            (progn (setq patt_name_mainlist_area_W02 (+ patt_name_mainlist_area_W02 patt_name_mainlist_area_)))
            )
            ( ;Harea_case_W3
            (and (= patt_name_mainlist_name_ (nth 15 mainlist_Ceiling)))
            (progn (setq patt_name_mainlist_area_W03 (+ patt_name_mainlist_area_W03 patt_name_mainlist_area_)))
            )
            ( ;Harea_case_W4
            (and (= patt_name_mainlist_name_ (nth 16 mainlist_Ceiling)))
            (progn (setq patt_name_mainlist_area_W04 (+ patt_name_mainlist_area_W04 patt_name_mainlist_area_)))
            )
            ( ;Harea_case_W5
            (and (= patt_name_mainlist_name_ (nth 17 mainlist_Ceiling)))
            (progn (setq patt_name_mainlist_area_W05 (+ patt_name_mainlist_area_W05 patt_name_mainlist_area_)))
            )
            ( ;Harea_case_W6
            (and (= patt_name_mainlist_name_ (nth 18 mainlist_Ceiling)))
            (progn (setq patt_name_mainlist_area_W06 (+ patt_name_mainlist_area_W06 patt_name_mainlist_area_)))
            )
            ( ;Harea_case_W7
            (and (= patt_name_mainlist_name_ (nth 19 mainlist_Ceiling)))
            (progn (setq patt_name_mainlist_area_W07 (+ patt_name_mainlist_area_W07 patt_name_mainlist_area_)))
            )
            ( ;Harea_case_W8
            (and (= patt_name_mainlist_name_ (nth 20 mainlist_Ceiling)))
            (progn (setq patt_name_mainlist_area_W08 (+ patt_name_mainlist_area_W08 patt_name_mainlist_area_)))
            )
            ( ;Harea_case_W9
            (and (= patt_name_mainlist_name_ (nth 21 mainlist_Ceiling)))
            (progn (setq patt_name_mainlist_area_W09 (+ patt_name_mainlist_area_W09 patt_name_mainlist_area_)))
            )
            ( ;Harea_case_W10
            (and (= patt_name_mainlist_name_ (nth 22 mainlist_Ceiling)))
            (progn (setq patt_name_mainlist_area_W10 (+ patt_name_mainlist_area_W10 patt_name_mainlist_area_)))
            )
            ( ;Harea_case_W11
            (and (= patt_name_mainlist_name_ (nth 23 mainlist_Ceiling)))
            (progn (setq patt_name_mainlist_area_W11 (+ patt_name_mainlist_area_W11 patt_name_mainlist_area_)))
            )
            ( ;Harea_case_W12
            (and (= patt_name_mainlist_name_ (nth 24 mainlist_Ceiling)))
            (progn (setq patt_name_mainlist_area_W12 (+ patt_name_mainlist_area_W12 patt_name_mainlist_area_)))
            )
            ( ;Harea_case_W13
            (and (= patt_name_mainlist_name_ (nth 25 mainlist_Ceiling)))
            (progn (setq patt_name_mainlist_area_W13 (+ patt_name_mainlist_area_W13 patt_name_mainlist_area_)))
            )
            ( ;Harea_case_W14
            (and (= patt_name_mainlist_name_ (nth 26 mainlist_Ceiling)))
            (progn (setq patt_name_mainlist_area_W14 (+ patt_name_mainlist_area_W14 patt_name_mainlist_area_)))
            )
            ( ;Harea_case_W15
            (and (= patt_name_mainlist_name_ (nth 27 mainlist_Ceiling)))
            (progn (setq patt_name_mainlist_area_W15 (+ patt_name_mainlist_area_W15 patt_name_mainlist_area_)))
            )
            ( ;Harea_case_W16
            (and (= patt_name_mainlist_name_ (nth 28 mainlist_Ceiling)))
            (progn (setq patt_name_mainlist_area_W16 (+ patt_name_mainlist_area_W16 patt_name_mainlist_area_)))
            )
            ( ;Harea_case_W17
            (and (= patt_name_mainlist_name_ (nth 29 mainlist_Ceiling)))
            (progn (setq patt_name_mainlist_area_W17 (+ patt_name_mainlist_area_W17 patt_name_mainlist_area_)))
            )
            ( ;Harea_case_W18
            (and (= patt_name_mainlist_name_ (nth 30 mainlist_Ceiling)))
            (progn (setq patt_name_mainlist_area_W18 (+ patt_name_mainlist_area_W18 patt_name_mainlist_area_)))
            )
            ( ;Harea_case_W19
            (and (= patt_name_mainlist_name_ (nth 31 mainlist_Ceiling)))
            (progn (setq patt_name_mainlist_area_W19 (+ patt_name_mainlist_area_W19 patt_name_mainlist_area_)))
            )
            ( ;Harea_case_W20
            (and (= patt_name_mainlist_name_ (nth 32 mainlist_Ceiling)))
            (progn (setq patt_name_mainlist_area_W20 (+ patt_name_mainlist_area_W20 patt_name_mainlist_area_)))
            )
            ( ;Harea_case_W21
            (and (= patt_name_mainlist_name_ (nth 33 mainlist_Ceiling)))
            (progn (setq patt_name_mainlist_area_W21 (+ patt_name_mainlist_area_W21 patt_name_mainlist_area_)))
            )
            ( ;Harea_case_W22
            (and (= patt_name_mainlist_name_ (nth 34 mainlist_Ceiling)))
            (progn (setq patt_name_mainlist_area_W22 (+ patt_name_mainlist_area_W22 patt_name_mainlist_area_)))
            )
          )

        
        (setq patt_name_mainlist_i (+ patt_name_mainlist_i 1))
      )
    ;
    (setq all_area_list_ (list 
                           (list  patt_name_mainlist_area_C01 
                                  patt_name_mainlist_area_C02 
                                  patt_name_mainlist_area_C03 
                                  patt_name_mainlist_area_C04 
                                  patt_name_mainlist_area_C05 
                                  patt_name_mainlist_area_C06 
                                  patt_name_mainlist_area_C07 
                                  patt_name_mainlist_area_C08 
                                  patt_name_mainlist_area_C09 
                                  patt_name_mainlist_area_C10 
                                  patt_name_mainlist_area_C11
                                  patt_name_mainlist_area_C11 
                                  patt_name_mainlist_area_C12 
                                  patt_name_mainlist_area_W01 
                                  patt_name_mainlist_area_W02 
                                  patt_name_mainlist_area_W03 
                                  patt_name_mainlist_area_W04 
                                  patt_name_mainlist_area_W05 
                                  patt_name_mainlist_area_W06 
                                  patt_name_mainlist_area_W07 
                                  patt_name_mainlist_area_W08 
                                  patt_name_mainlist_area_W09
                                  patt_name_mainlist_area_W10 
                                  patt_name_mainlist_area_W11 
                                  patt_name_mainlist_area_W12 
                                  patt_name_mainlist_area_W13 
                                  patt_name_mainlist_area_W14 
                                  patt_name_mainlist_area_W15 
                                  patt_name_mainlist_area_W16 
                                  patt_name_mainlist_area_W17 
                                  patt_name_mainlist_area_W18 
                                  patt_name_mainlist_area_W19 
                                  patt_name_mainlist_area_W20 
                                  patt_name_mainlist_area_W21 
                                  patt_name_mainlist_area_W22
                           )
                         )
    )
    (length (car all_area_list_))
    (setq Excel_lasted_worksheet_obj_ (TA:Excel_Open-Excel_ 1 1))
    (TA:Excel_input_data_R1C1 Excel_lasted_worksheet_obj_ 3 2 (getvar "dwgname"))
    (TA:Excel_foreach_input_list_dataset_R1C1 Excel_lasted_worksheet_obj_ 2 5 (list mainlist_Ceiling ))
    (TA:Excel_foreach_input_list_dataset_R1C1 Excel_lasted_worksheet_obj_ 3 5 all_area_list_)
    (TA:EXCEL_autofit_column_ Excel_lasted_worksheet_obj_ 2)
  ;
)
(defun c:Hatch_to_Excel_H3Excel ()
  ;selection_set_for_fillter_blk_name
    (if  ;pre_select_ssget_or_post_select_ssget
      (=
        (setq ss_pre_filter_set_xx_ (ssget "i"
                                          (list
                                            (cons 0 "HATCH") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "HATCH") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq patt_name_mainlist_ ())
    (setq patt_name_name_hatch_list_ ())
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (setq ss_pre_filter_set_xx_obj_patt_name_ (vla-get-patternname ss_pre_filter_set_xx_obj_))
      (if 
        (or 
          (= (wcmatch ss_pre_filter_set_xx_obj_patt_name_ "000_C*") T)
          (= (wcmatch ss_pre_filter_set_xx_obj_patt_name_ "000_W*") T)
        )
        (progn
          (setq ss_pre_filter_set_xx_obj_Harea_ (/ (vla-get-area ss_pre_filter_set_xx_obj_) 1000000 ))
          (setq patt_name_name_hatch_list_ (cons  ss_pre_filter_set_xx_obj_patt_name_ patt_name_name_hatch_list_))
          (setq patt_name_sublist_ (list ss_pre_filter_set_xx_obj_patt_name_ ss_pre_filter_set_xx_obj_Harea_  ))
          (setq patt_name_mainlist_ (cons patt_name_sublist_ patt_name_mainlist_))
        )
      )
      
      
      
      (setq ss_pre_filter_set_xx_i (+ ss_pre_filter_set_xx_i 1))
    )
  ;
  ;preloop_and_while
    (setq mainlist_Ceiling (list 
                            "000_C01"
                            "000_C02"
                            "000_C03"
                            "000_C04"
                            "000_C05"
                            "000_C05A"
                            "000_C06"
                            "000_C07"
                            "000_C08"
                            "000_C09"
                            "000_C10"
                            "000_C11"
                            "000_C12"
                            "000_W01"
                            "000_W02"
                            "000_W03"
                            "000_W04"
                            "000_W05"
                            "000_W06"
                            "000_W07"
                            "000_W08"
                            "000_W09"
                            "000_W10"
                            "000_W11"
                            "000_W12"
                            "000_W13"
                            "000_W14"
                            "000_W15"
                            "000_W16"
                            "000_W17"
                            "000_W18"
                            "000_W19"
                            "000_W20"
                            "000_W21"
                            "000_W22"
                           )
    )
    (setq patt_name_mainlist_area_C01 0
          patt_name_mainlist_area_C02 0
          patt_name_mainlist_area_C03 0
          patt_name_mainlist_area_C04 0
          patt_name_mainlist_area_C05 0
          patt_name_mainlist_area_C05A 0
          patt_name_mainlist_area_C06 0
          patt_name_mainlist_area_C07 0
          patt_name_mainlist_area_C08 0
          patt_name_mainlist_area_C09 0
          patt_name_mainlist_area_C10 0
          patt_name_mainlist_area_C11 0
          patt_name_mainlist_area_C12 0
          patt_name_mainlist_area_W01 0
          patt_name_mainlist_area_W02 0
          patt_name_mainlist_area_W03 0
          patt_name_mainlist_area_W04 0
          patt_name_mainlist_area_W05 0
          patt_name_mainlist_area_W06 0
          patt_name_mainlist_area_W07 0
          patt_name_mainlist_area_W08 0
          patt_name_mainlist_area_W09 0
          patt_name_mainlist_area_W10 0
          patt_name_mainlist_area_W11 0
          patt_name_mainlist_area_W12 0
          patt_name_mainlist_area_W13 0
          patt_name_mainlist_area_W14 0
          patt_name_mainlist_area_W15 0
          patt_name_mainlist_area_W16 0
          patt_name_mainlist_area_W17 0
          patt_name_mainlist_area_W18 0
          patt_name_mainlist_area_W19 0
          patt_name_mainlist_area_W20 0
          patt_name_mainlist_area_W21 0
          patt_name_mainlist_area_W22 0
    )
    (length (car all_area_list_))
    ;preloop_and_while
      (setq patt_name_mainlist_i 0)
      (while (< patt_name_mainlist_i (length patt_name_mainlist_))
        (setq patt_name_mainlist_name_ (car (nth  patt_name_mainlist_i patt_name_mainlist_)))
        (setq patt_name_mainlist_area_ (cadr (nth  patt_name_mainlist_i patt_name_mainlist_)))
          (cond 
            ( ;Harea_case_0
            (and (= patt_name_mainlist_name_ (nth 0 mainlist_Ceiling)))
            (progn (setq patt_name_mainlist_area_C01 (+ patt_name_mainlist_area_C01 patt_name_mainlist_area_)))
            )
            ( ;Harea_case_1
            (and (= patt_name_mainlist_name_ (nth 1 mainlist_Ceiling)))
            (progn (setq patt_name_mainlist_area_C02 (+ patt_name_mainlist_area_C02 patt_name_mainlist_area_)))
            )
            ( ;Harea_case_2
            (and (= patt_name_mainlist_name_ (nth 2 mainlist_Ceiling)))
            (progn (setq patt_name_mainlist_area_C03 (+ patt_name_mainlist_area_C03 patt_name_mainlist_area_)))
            )
            ( ;Harea_case_3
            (and (= patt_name_mainlist_name_ (nth 3 mainlist_Ceiling)))
            (progn (setq patt_name_mainlist_area_C04 (+ patt_name_mainlist_area_C04 patt_name_mainlist_area_)))
            )
            ( ;Harea_case_4
            (and (= patt_name_mainlist_name_ (nth 4 mainlist_Ceiling)))
            (progn (setq patt_name_mainlist_area_C05 (+ patt_name_mainlist_area_C05 patt_name_mainlist_area_)))
            )
            ( ;Harea_case_5
            (and (= patt_name_mainlist_name_ (nth 5 mainlist_Ceiling)))
            (progn (setq patt_name_mainlist_area_C05A (+ patt_name_mainlist_area_C05A patt_name_mainlist_area_)))
            )
            ( ;Harea_case_6
            (and (= patt_name_mainlist_name_ (nth 6 mainlist_Ceiling)))
            (progn (setq patt_name_mainlist_area_C06 (+ patt_name_mainlist_area_C06 patt_name_mainlist_area_)))
            )
            ( ;Harea_case_7
            (and (= patt_name_mainlist_name_ (nth 7 mainlist_Ceiling)))
            (progn (setq patt_name_mainlist_area_C07 (+ patt_name_mainlist_area_C07 patt_name_mainlist_area_)))
            )
            ( ;Harea_case_8
            (and (= patt_name_mainlist_name_ (nth 8 mainlist_Ceiling)))
            (progn (setq patt_name_mainlist_area_C08 (+ patt_name_mainlist_area_C08 patt_name_mainlist_area_)))
            )
            ( ;Harea_case_9
            (and (= patt_name_mainlist_name_ (nth 9 mainlist_Ceiling)))
            (progn (setq patt_name_mainlist_area_C09 (+ patt_name_mainlist_area_C09 patt_name_mainlist_area_)))
            )
            ( ;Harea_case_10
            (and (= patt_name_mainlist_name_ (nth 10 mainlist_Ceiling)))
            (progn (setq patt_name_mainlist_area_C10 (+ patt_name_mainlist_area_C10 patt_name_mainlist_area_)))
            )
            ( ;Harea_case_11
            (and (= patt_name_mainlist_name_ (nth 11 mainlist_Ceiling)))
            (progn (setq patt_name_mainlist_area_C11 (+ patt_name_mainlist_area_C11 patt_name_mainlist_area_)))
            )
            ( ;Harea_case_12
            (and (= patt_name_mainlist_name_ (nth 12 mainlist_Ceiling)))
            (progn (setq patt_name_mainlist_area_C12 (+ patt_name_mainlist_area_C12 patt_name_mainlist_area_)))
            )
            ( ;Harea_case_W1
            (and (= patt_name_mainlist_name_ (nth 13 mainlist_Ceiling)))
            (progn (setq patt_name_mainlist_area_W01 (+ patt_name_mainlist_area_W01 patt_name_mainlist_area_)))
            )
            ( ;Harea_case_W2
            (and (= patt_name_mainlist_name_ (nth 14 mainlist_Ceiling)))
            (progn (setq patt_name_mainlist_area_W02 (+ patt_name_mainlist_area_W02 patt_name_mainlist_area_)))
            )
            ( ;Harea_case_W3
            (and (= patt_name_mainlist_name_ (nth 15 mainlist_Ceiling)))
            (progn (setq patt_name_mainlist_area_W03 (+ patt_name_mainlist_area_W03 patt_name_mainlist_area_)))
            )
            ( ;Harea_case_W4
            (and (= patt_name_mainlist_name_ (nth 16 mainlist_Ceiling)))
            (progn (setq patt_name_mainlist_area_W04 (+ patt_name_mainlist_area_W04 patt_name_mainlist_area_)))
            )
            ( ;Harea_case_W5
            (and (= patt_name_mainlist_name_ (nth 17 mainlist_Ceiling)))
            (progn (setq patt_name_mainlist_area_W05 (+ patt_name_mainlist_area_W05 patt_name_mainlist_area_)))
            )
            ( ;Harea_case_W6
            (and (= patt_name_mainlist_name_ (nth 18 mainlist_Ceiling)))
            (progn (setq patt_name_mainlist_area_W06 (+ patt_name_mainlist_area_W06 patt_name_mainlist_area_)))
            )
            ( ;Harea_case_W7
            (and (= patt_name_mainlist_name_ (nth 19 mainlist_Ceiling)))
            (progn (setq patt_name_mainlist_area_W07 (+ patt_name_mainlist_area_W07 patt_name_mainlist_area_)))
            )
            ( ;Harea_case_W8
            (and (= patt_name_mainlist_name_ (nth 20 mainlist_Ceiling)))
            (progn (setq patt_name_mainlist_area_W08 (+ patt_name_mainlist_area_W08 patt_name_mainlist_area_)))
            )
            ( ;Harea_case_W9
            (and (= patt_name_mainlist_name_ (nth 21 mainlist_Ceiling)))
            (progn (setq patt_name_mainlist_area_W09 (+ patt_name_mainlist_area_W09 patt_name_mainlist_area_)))
            )
            ( ;Harea_case_W10
            (and (= patt_name_mainlist_name_ (nth 22 mainlist_Ceiling)))
            (progn (setq patt_name_mainlist_area_W10 (+ patt_name_mainlist_area_W10 patt_name_mainlist_area_)))
            )
            ( ;Harea_case_W11
            (and (= patt_name_mainlist_name_ (nth 23 mainlist_Ceiling)))
            (progn (setq patt_name_mainlist_area_W11 (+ patt_name_mainlist_area_W11 patt_name_mainlist_area_)))
            )
            ( ;Harea_case_W12
            (and (= patt_name_mainlist_name_ (nth 24 mainlist_Ceiling)))
            (progn (setq patt_name_mainlist_area_W12 (+ patt_name_mainlist_area_W12 patt_name_mainlist_area_)))
            )
            ( ;Harea_case_W13
            (and (= patt_name_mainlist_name_ (nth 25 mainlist_Ceiling)))
            (progn (setq patt_name_mainlist_area_W13 (+ patt_name_mainlist_area_W13 patt_name_mainlist_area_)))
            )
            ( ;Harea_case_W14
            (and (= patt_name_mainlist_name_ (nth 26 mainlist_Ceiling)))
            (progn (setq patt_name_mainlist_area_W14 (+ patt_name_mainlist_area_W14 patt_name_mainlist_area_)))
            )
            ( ;Harea_case_W15
            (and (= patt_name_mainlist_name_ (nth 27 mainlist_Ceiling)))
            (progn (setq patt_name_mainlist_area_W15 (+ patt_name_mainlist_area_W15 patt_name_mainlist_area_)))
            )
            ( ;Harea_case_W16
            (and (= patt_name_mainlist_name_ (nth 28 mainlist_Ceiling)))
            (progn (setq patt_name_mainlist_area_W16 (+ patt_name_mainlist_area_W16 patt_name_mainlist_area_)))
            )
            ( ;Harea_case_W17
            (and (= patt_name_mainlist_name_ (nth 29 mainlist_Ceiling)))
            (progn (setq patt_name_mainlist_area_W17 (+ patt_name_mainlist_area_W17 patt_name_mainlist_area_)))
            )
            ( ;Harea_case_W18
            (and (= patt_name_mainlist_name_ (nth 30 mainlist_Ceiling)))
            (progn (setq patt_name_mainlist_area_W18 (+ patt_name_mainlist_area_W18 patt_name_mainlist_area_)))
            )
            ( ;Harea_case_W19
            (and (= patt_name_mainlist_name_ (nth 31 mainlist_Ceiling)))
            (progn (setq patt_name_mainlist_area_W19 (+ patt_name_mainlist_area_W19 patt_name_mainlist_area_)))
            )
            ( ;Harea_case_W20
            (and (= patt_name_mainlist_name_ (nth 32 mainlist_Ceiling)))
            (progn (setq patt_name_mainlist_area_W20 (+ patt_name_mainlist_area_W20 patt_name_mainlist_area_)))
            )
            ( ;Harea_case_W21
            (and (= patt_name_mainlist_name_ (nth 33 mainlist_Ceiling)))
            (progn (setq patt_name_mainlist_area_W21 (+ patt_name_mainlist_area_W21 patt_name_mainlist_area_)))
            )
            ( ;Harea_case_W22
            (and (= patt_name_mainlist_name_ (nth 34 mainlist_Ceiling)))
            (progn (setq patt_name_mainlist_area_W22 (+ patt_name_mainlist_area_W22 patt_name_mainlist_area_)))
            )
          )

        
        (setq patt_name_mainlist_i (+ patt_name_mainlist_i 1))
      )
    ;
    (setq all_area_list_ (list 
                           (list  patt_name_mainlist_area_C01 
                                  patt_name_mainlist_area_C02 
                                  patt_name_mainlist_area_C03 
                                  patt_name_mainlist_area_C04 
                                  patt_name_mainlist_area_C05 
                                  patt_name_mainlist_area_C05A 
                                  patt_name_mainlist_area_C06 
                                  patt_name_mainlist_area_C07 
                                  patt_name_mainlist_area_C08 
                                  patt_name_mainlist_area_C09 
                                  patt_name_mainlist_area_C10 
                                  patt_name_mainlist_area_C11
                                  patt_name_mainlist_area_C12 
                                  patt_name_mainlist_area_W01 
                                  patt_name_mainlist_area_W02 
                                  patt_name_mainlist_area_W03 
                                  patt_name_mainlist_area_W04 
                                  patt_name_mainlist_area_W05 
                                  patt_name_mainlist_area_W06 
                                  patt_name_mainlist_area_W07 
                                  patt_name_mainlist_area_W08 
                                  patt_name_mainlist_area_W09
                                  patt_name_mainlist_area_W10 
                                  patt_name_mainlist_area_W11 
                                  patt_name_mainlist_area_W12 
                                  patt_name_mainlist_area_W13 
                                  patt_name_mainlist_area_W14 
                                  patt_name_mainlist_area_W15 
                                  patt_name_mainlist_area_W16 
                                  patt_name_mainlist_area_W17 
                                  patt_name_mainlist_area_W18 
                                  patt_name_mainlist_area_W19 
                                  patt_name_mainlist_area_W20 
                                  patt_name_mainlist_area_W21 
                                  patt_name_mainlist_area_W22
                           )
                         )
    )
    (setq Excel_lasted_worksheet_obj_ (TA:Excel_Open-Excel_ 1 1))
    (TA:EXCEL_autofit_column_ Excel_lasted_worksheet_obj_ 1)
    (TA:Excel_input_data_R1C1 Excel_lasted_worksheet_obj_ 3 2 (getvar "dwgname"))
    (TA:Excel_foreach_input_list_dataset_R1C1 Excel_lasted_worksheet_obj_ 2 6 (list mainlist_Ceiling ))
    (TA:Excel_foreach_input_list_dataset_R1C1 Excel_lasted_worksheet_obj_ 3 6 all_area_list_)
  ;
  (graphscr)
  (c:Special-Hatch_to_Excel_SH2Excel)
  (TA:EXCEL_all-cut-copy_row_ Excel_lasted_worksheet_obj_ 3 'cut)
)
(defun c:select_hacth_SsH ()
  (setq ss_pre_filter_set_xx_ (ssget
                                            (list
                                              (cons 0 "HATCH") ;type of object
                                              ; (cons 8 "000 - GRID")   ;kind of layer
                                              ; (cons 2 "000-GRID_LINE_DYN")       ;kind of nameblock
                                              ; (cons 62 1)           ;kind of color call sign with color code index
                                            )
                                      )
          )

  (command "pselect"  ss_pre_filter_set_xx_  "" )
)
(defun c:select_hacth_SSB ()
  (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )

  (command "pselect"  ss_pre_filter_set_xx_  "" )
)








(defun c:stamplevel_slv_ ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (setq ss_pre_filter_set_xx_obj_ins_ (vlax-safearray->list (vlax-variant-value (vla-get-insertionpoint ss_pre_filter_set_xx_obj_))))
      (setq ss_pre_filter_set_xx_obj_ins_trans_xyz (trans ss_pre_filter_set_xx_obj_ins_ 0 1))
      (LM:vl-setattributevalue ss_pre_filter_set_xx_obj_ "MAT_LV" (rtos (cadr ss_pre_filter_set_xx_obj_ins_trans_xyz) 2 2 ))
      (setq ss_pre_filter_set_xx_i (+ ss_pre_filter_set_xx_i 1))
    )
  ;



)

(defun c:point-to-point_PP2P_ ()
  (setq pl-1_ename_ (car (entsel "specify Object")))
  (setq pl-1_obj_ (vlax-ename->vla-object pl-1_ename_))
  (setq pl-1-obj_vtp_ (cadr(TA:Get_Pline_vertext_ins_point_ pl-1_ename_ )))
  
  (if (/= (setq pl-2_ename_ (car (entsel "specify Object"))) pl-1_ename_ )
    (progn
      (setq pl-2_obj_ (vlax-ename->vla-object pl-2_ename_))
      (setq pl-2-obj_vtp_ (cadr (TA:Get_Pline_vertext_ins_point_ pl-2_ename_ )))
    )
  )


  ;preloop_and_while
    (setq i 0)
    (while (< i (length pl-1-obj_vtp_))
      (setq ename_1 (nth  i pl-1-obj_vtp_))
      (setq ename_2 (nth  i pl-2-obj_vtp_))
      (command "line" ename_1 ename_2 "")
      (setq i (+ i 1))
    )
  ;
)
(defun c:point-to-point_PL2P_ ()
  (setq pl-1_ename_ (car (entsel "specify Object")))
  (setq pl-1_obj_ (vlax-ename->vla-object pl-1_ename_))
  (setq pl-1-obj_vtp_ (cadr(TA:Get_Pline_vertext_ins_point_ pl-1_ename_ )))
  (setq pl-2_ename_ (car (entsel "specify Object")))
  (setq pl-2_obj_ (vlax-ename->vla-object pl-2_ename_))
  (setq pl-2-obj_vtp_ (cadr (TA:Get_Pline_vertext_ins_point_ pl-2_ename_ )))

  ; ;preloop_and_while
  ;   (setq i 0)
  ;   (while (< i (length pl-1-obj_vtp_))
      (setq ename_1 (nth  0 pl-1-obj_vtp_))
      (setq ename_3 (nth  0 pl-2-obj_vtp_))
      (setq ename_2 (nth  (- (length pl-1-obj_vtp_) 1) pl-1-obj_vtp_))
      (setq ename_4 (nth  (- (length pl-1-obj_vtp_) 1) pl-2-obj_vtp_))
      (command "line" ename_1 ename_3 "")
      (command "line" ename_2 ename_4 "")
  ;     (setq i (+ i 1))
  ;   )
  ; ;
)
(defun c:point-to-point_L2REC_ ()
  (setq pl-1_ename_ (car (entsel "specify Object")))
  (setq pl-1_obj_ (vlax-ename->vla-object pl-1_ename_))
  (setq pl-1-obj_vtp_ (cadr(TA:Get_Pline_vertext_ins_point_ pl-1_ename_ )))
  (setq pl-2_ename_ (car (entsel "specify Object")))
  (setq pl-2_obj_ (vlax-ename->vla-object pl-2_ename_))
  (setq pl-2-obj_vtp_ (cadr (TA:Get_Pline_vertext_ins_point_ pl-2_ename_ )))

  ; ;preloop_and_while
  ;   (setq i 0)
  ;   (while (< i (length pl-1-obj_vtp_))
      (setq 1st-1 (car pl-1-obj_vtp_))
      (setq 1st-2 (car (reverse pl-1-obj_vtp_)))
  
      (setq 2nd-1 (car pl-2-obj_vtp_))
      (setq 2nd-2 (cadr pl-2-obj_vtp_))
  
      (command "line" 1st-1 2nd-1 "")
      (command "line" 1st-2 2nd-2 "")

  
  ;     (setq i (+ i 1))
  ;   )
  ; ;
)


;PPLINE - ITD func
  (defun c:Rehatch_color_RHC ()
    ;selection_set_for_fillter_blk_name
      (if  ;pre_select_ssget_or_post_select_ssget
        (=
          (setq ss_pre_filter_set_xx_ (ssget "i"
                                            (list
                                              (cons 0 "hatch") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "hatch") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (setq ssset_ ())
      (setq ssset_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (cond 
          ( ;vla-get-color_case_1
          (and 
            (= (vla-get-patternname ss_pre_filter_set_xx_obj_) "000_C01")
          )
          (progn 
            (vla-put-color ss_pre_filter_set_xx_obj_ 70)
            (setq ssset_ (ssadd ss_pre_filter_set_xx_ename_ ssset_))
            (princ "vla-get-color_case_1")
          )
          )
          ( ;vla-get-color_case_2
          (and 
            (= (vla-get-patternname ss_pre_filter_set_xx_obj_) "000_C02")
          )
          (progn 
            (vla-put-color ss_pre_filter_set_xx_obj_ 90)
            (setq ssset_ (ssadd ss_pre_filter_set_xx_ename_ ssset_))
            (princ "vla-get-color_case_2")
          )
          )
          ( ;vla-get-color_case_3
          (and 
            (= (vla-get-patternname ss_pre_filter_set_xx_obj_) "000_C03")
          )
          (progn 
            (vla-put-color ss_pre_filter_set_xx_obj_ 20)
            (setq ssset_ (ssadd ss_pre_filter_set_xx_ename_ ssset_))
            (princ "vla-get-color_case_3")
          )
          )
          ( ;vla-get-color_case_4
          (and 
            (= (vla-get-patternname ss_pre_filter_set_xx_obj_) "000_C04")
          )
          (progn 
            (vla-put-color ss_pre_filter_set_xx_obj_ 130)
            (setq ssset_ (ssadd ss_pre_filter_set_xx_ename_ ssset_))
            (princ "vla-get-color_case_4")
          )
          )
          ( ;vla-get-color_case_5
          (and 
            (= (vla-get-patternname ss_pre_filter_set_xx_obj_) "000_C05")
          )
          (progn 
            (vla-put-color ss_pre_filter_set_xx_obj_ 20)
            (setq ssset_ (ssadd ss_pre_filter_set_xx_ename_ ssset_))
            (princ "vla-get-color_case_5")
          )
          )
          ( ;vla-get-color_case_5
          (and 
            (= (vla-get-patternname ss_pre_filter_set_xx_obj_) "000_C05A")
          )
          (progn 
            (vla-put-color ss_pre_filter_set_xx_obj_ 20)
            (setq ssset_ (ssadd ss_pre_filter_set_xx_ename_ ssset_))
            (princ "vla-get-color_case_5")
          )
          )
          ( ;vla-get-color_case_6
          (and 
            (= (vla-get-patternname ss_pre_filter_set_xx_obj_) "000_C06")
          )
          (progn 
            (vla-put-color ss_pre_filter_set_xx_obj_ 170)
            (setq ssset_ (ssadd ss_pre_filter_set_xx_ename_ ssset_))
            (princ "vla-get-color_case_6")
          )
          )
          ( ;vla-get-color_case_7
          (and 
            (= (vla-get-patternname ss_pre_filter_set_xx_obj_) "000_C07")
          )
          (progn 
            (vla-put-color ss_pre_filter_set_xx_obj_ 190)
            (setq ssset_ (ssadd ss_pre_filter_set_xx_ename_ ssset_))
            (princ "vla-get-color_case_7")
          )
          )
          ( ;vla-get-color_case_8
          (and 
            (= (vla-get-patternname ss_pre_filter_set_xx_obj_) "000_C08")
          )
          (progn 
            (vla-put-color ss_pre_filter_set_xx_obj_ 210)
            (setq ssset_ (ssadd ss_pre_filter_set_xx_ename_ ssset_))
            (princ "vla-get-color_case_8")
          )
          )
          ( ;vla-get-color_case_9
          (and 
            (= (vla-get-patternname ss_pre_filter_set_xx_obj_) "000_C09")
          )
          (progn 
            (vla-put-color ss_pre_filter_set_xx_obj_ 230)
            (setq ssset_ (ssadd ss_pre_filter_set_xx_ename_ ssset_))
            (princ "vla-get-color_case_9")
          )
          )
          ( ;vla-get-color_case_10
          (and 
            (= (vla-get-patternname ss_pre_filter_set_xx_obj_) "000_C10")
          )
          (progn 
            (vla-put-color ss_pre_filter_set_xx_obj_ 235)
            (setq ssset_ (ssadd ss_pre_filter_set_xx_ename_ ssset_))
            (princ "vla-get-color_case_10")
          )
          )
          ( ;vla-get-color_case_11
          (and 
            (= (vla-get-patternname ss_pre_filter_set_xx_obj_) "000_C11")
          )
          (progn 
            (vla-put-color ss_pre_filter_set_xx_obj_ 240)
            (setq ssset_ (ssadd ss_pre_filter_set_xx_ename_ ssset_))
            (princ "vla-get-color_case_11")
          )
          )
          ( ;vla-get-color_case_12
          (and 
            (= (vla-get-patternname ss_pre_filter_set_xx_obj_) "000_W01")
          )
          (progn 
            (vla-put-color ss_pre_filter_set_xx_obj_ 20)
            (setq ssset_ (ssadd ss_pre_filter_set_xx_ename_ ssset_))
            (princ "vla-get-color_case_12")
          )
          )
          ( ;vla-get-color_case_13
          (and 
            (= (vla-get-patternname ss_pre_filter_set_xx_obj_) "000_W02")
          )
          (progn 
            (vla-put-color ss_pre_filter_set_xx_obj_ 40)
            (setq ssset_ (ssadd ss_pre_filter_set_xx_ename_ ssset_))
            (princ "vla-get-color_case_13")
          )
          )
          ( ;vla-get-color_case_14
          (and 
            (= (vla-get-patternname ss_pre_filter_set_xx_obj_) "000_W03")
          )
          (progn 
            (vla-put-color ss_pre_filter_set_xx_obj_ 60)
            (setq ssset_ (ssadd ss_pre_filter_set_xx_ename_ ssset_))
            (princ "vla-get-color_case_14")
          )
          )
          ( ;vla-get-color_case_15
          (and 
            (= (vla-get-patternname ss_pre_filter_set_xx_obj_) "000_W04")
          )
          (progn 
            (vla-put-color ss_pre_filter_set_xx_obj_ 80)
            (setq ssset_ (ssadd ss_pre_filter_set_xx_ename_ ssset_))
            (princ "vla-get-color_case_15")
          )
          )
          ( ;vla-get-color_case_16
          (and 
            (= (vla-get-patternname ss_pre_filter_set_xx_obj_) "000_W05")
          )
          (progn 
            (vla-put-color ss_pre_filter_set_xx_obj_ 100)
            (setq ssset_ (ssadd ss_pre_filter_set_xx_ename_ ssset_))
            (princ "vla-get-color_case_16")
          )
          )
          ( ;vla-get-color_case_17
          (and 
            (= (vla-get-patternname ss_pre_filter_set_xx_obj_) "000_W06")
          )
          (progn 
            (vla-put-color ss_pre_filter_set_xx_obj_ 120)
            (setq ssset_ (ssadd ss_pre_filter_set_xx_ename_ ssset_))
            (princ "vla-get-color_case_17")
          )
          )
          ( ;vla-get-color_case_18
          (and 
            (= (vla-get-patternname ss_pre_filter_set_xx_obj_) "000_W07")
          )
          (progn 
            (vla-put-color ss_pre_filter_set_xx_obj_ 140)
            (setq ssset_ (ssadd ss_pre_filter_set_xx_ename_ ssset_))
            (princ "vla-get-color_case_18")
          )
          )
          ( ;vla-get-color_case_19
          (and 
            (= (vla-get-patternname ss_pre_filter_set_xx_obj_) "000_W08")
          )
          (progn 
            (vla-put-color ss_pre_filter_set_xx_obj_ 20)
            (setq ssset_ (ssadd ss_pre_filter_set_xx_ename_ ssset_))
            (princ "vla-get-color_case_19")
          )
          )
          ( ;vla-get-color_case_20
          (and 
            (= (vla-get-patternname ss_pre_filter_set_xx_obj_) "000_W09")
          )
          (progn 
            (vla-put-color ss_pre_filter_set_xx_obj_ 180)
            (setq ssset_ (ssadd ss_pre_filter_set_xx_ename_ ssset_))
            (princ "vla-get-color_case_20")
          )
          )
          ( ;vla-get-color_case_21
          (and 
            (= (vla-get-patternname ss_pre_filter_set_xx_obj_) "000_W10")
          )
          (progn 
            (vla-put-color ss_pre_filter_set_xx_obj_ 200)
            (setq ssset_ (ssadd ss_pre_filter_set_xx_ename_ ssset_))
            (princ "vla-get-color_case_21")
          )
          )
          ( ;vla-get-color_case_22
          (and 
            (= (vla-get-patternname ss_pre_filter_set_xx_obj_) "000_W11")
          )
          (progn 
            (vla-put-color ss_pre_filter_set_xx_obj_ 220)
            (setq ssset_ (ssadd ss_pre_filter_set_xx_ename_ ssset_))
            (princ "vla-get-color_case_22")
          )
          )
          ( ;vla-get-color_case_23
          (and 
            (= (vla-get-patternname ss_pre_filter_set_xx_obj_) "000_W12")
          )
          (progn 
            (vla-put-color ss_pre_filter_set_xx_obj_ 240)
            (setq ssset_ (ssadd ss_pre_filter_set_xx_ename_ ssset_))
            (princ "vla-get-color_case_23")
          )
          )
          ( ;vla-get-color_case_24
          (and 
            (= (vla-get-patternname ss_pre_filter_set_xx_obj_) "000_W13")
          )
          (progn 
            (vla-put-color ss_pre_filter_set_xx_obj_ 20)
            (setq ssset_ (ssadd ss_pre_filter_set_xx_ename_ ssset_))
            (princ "vla-get-color_case_24")
          )
          )
          ( ;vla-get-color_case_25
          (and 
            (= (vla-get-patternname ss_pre_filter_set_xx_obj_) "000_W14")
          )
          (progn 
            (vla-put-color ss_pre_filter_set_xx_obj_ 40)
            (setq ssset_ (ssadd ss_pre_filter_set_xx_ename_ ssset_))
            (princ "vla-get-color_case_25")
          )
          )
          ( ;vla-get-color_case_26
          (and 
            (= (vla-get-patternname ss_pre_filter_set_xx_obj_) "000_W15")
          )
          (progn 
            (vla-put-color ss_pre_filter_set_xx_obj_ 60)
            (setq ssset_ (ssadd ss_pre_filter_set_xx_ename_ ssset_))
            (princ "vla-get-color_case_26")
          )
          )
          ( ;vla-get-color_case_27
          (and 
            (= (vla-get-patternname ss_pre_filter_set_xx_obj_) "000_W16")
          )
          (progn 
            (vla-put-color ss_pre_filter_set_xx_obj_ 80)
            (setq ssset_ (ssadd ss_pre_filter_set_xx_ename_ ssset_))
            (princ "vla-get-color_case_27")
          )
          )
          ( ;vla-get-color_case_28
          (and 
            (= (vla-get-patternname ss_pre_filter_set_xx_obj_) "000_W17")
          )
          (progn 
            (vla-put-color ss_pre_filter_set_xx_obj_ 100)
            (setq ssset_ (ssadd ss_pre_filter_set_xx_ename_ ssset_))
            (princ "vla-get-color_case_28")
          )
          )
          ( ;vla-get-color_case_29
          (and 
            (= (vla-get-patternname ss_pre_filter_set_xx_obj_) "000_W18")
          )
          (progn 
            (vla-put-color ss_pre_filter_set_xx_obj_ 120)
            (setq ssset_ (ssadd ss_pre_filter_set_xx_ename_ ssset_))
            (princ "vla-get-color_case_29")
          )
          )
          ( ;vla-get-color_case_30
          (and 
            (= (vla-get-patternname ss_pre_filter_set_xx_obj_) "000_W19")
          )
          (progn 
            (vla-put-color ss_pre_filter_set_xx_obj_ 140)
            (setq ssset_ (ssadd ss_pre_filter_set_xx_ename_ ssset_))
            (princ "vla-get-color_case_30")
          )
          )
          ( ;vla-get-color_case_31
          (and 
            (= (vla-get-patternname ss_pre_filter_set_xx_obj_) "000_W20")
          )
          (progn 
            (vla-put-color ss_pre_filter_set_xx_obj_ 160)
            (setq ssset_ (ssadd ss_pre_filter_set_xx_ename_ ssset_))
            (princ "vla-get-color_case_31")
          )
          )
          ( ;vla-get-color_case_32
          (and 
            (= (vla-get-patternname ss_pre_filter_set_xx_obj_) "000_W21")
          )
          (progn 
            (vla-put-color ss_pre_filter_set_xx_obj_ 180)
            (setq ssset_ (ssadd ss_pre_filter_set_xx_ename_ ssset_))
            (princ "vla-get-color_case_32")
          )
          )
          ( ;vla-get-color_case_33
          (and 
            (= (vla-get-patternname ss_pre_filter_set_xx_obj_) "000_W22")
          )
          (progn 
            (vla-put-color ss_pre_filter_set_xx_obj_ 200)
            (setq ssset_ (ssadd ss_pre_filter_set_xx_ename_ ssset_))
            (princ "vla-get-color_case_33")
          )
          )
        )
        
        (setq ss_pre_filter_set_xx_i (+ ss_pre_filter_set_xx_i 1))
      )
      (command "pselect"  ssset_ "" )
    ;
  )
  (defun c:Rehatch_color_RHCx ()
    ;selection_set_for_fillter_blk_name
      (if  ;pre_select_ssget_or_post_select_ssget
        (=
          (setq ss_pre_filter_set_xx_ (ssget "x"
                                            (list
                                              (cons 0 "hatch") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "hatch") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (setq ssset_ ())
      (setq ssset_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (cond 
          ( ;vla-get-color_case_1
          (and 
            (= (vla-get-patternname ss_pre_filter_set_xx_obj_) "000_C01")
          )
          (progn 
            (vla-put-color ss_pre_filter_set_xx_obj_ 70)
            (setq ssset_ (ssadd ss_pre_filter_set_xx_ename_ ssset_))
            (princ "vla-get-color_case_1")
          )
          )
          ( ;vla-get-color_case_2
          (and 
            (= (vla-get-patternname ss_pre_filter_set_xx_obj_) "000_C02")
          )
          (progn 
            (vla-put-color ss_pre_filter_set_xx_obj_ 90)
            (setq ssset_ (ssadd ss_pre_filter_set_xx_ename_ ssset_))
            (princ "vla-get-color_case_2")
          )
          )
          ( ;vla-get-color_case_3
          (and 
            (= (vla-get-patternname ss_pre_filter_set_xx_obj_) "000_C03")
          )
          (progn 
            (vla-put-color ss_pre_filter_set_xx_obj_ 20)
            (setq ssset_ (ssadd ss_pre_filter_set_xx_ename_ ssset_))
            (princ "vla-get-color_case_3")
          )
          )
          ( ;vla-get-color_case_4
          (and 
            (= (vla-get-patternname ss_pre_filter_set_xx_obj_) "000_C04")
          )
          (progn 
            (vla-put-color ss_pre_filter_set_xx_obj_ 130)
            (setq ssset_ (ssadd ss_pre_filter_set_xx_ename_ ssset_))
            (princ "vla-get-color_case_4")
          )
          )
          ( ;vla-get-color_case_5
          (and 
            (= (vla-get-patternname ss_pre_filter_set_xx_obj_) "000_C05")
          )
          (progn 
            (vla-put-color ss_pre_filter_set_xx_obj_ 20)
            (setq ssset_ (ssadd ss_pre_filter_set_xx_ename_ ssset_))
            (princ "vla-get-color_case_5")
          )
          )
          ( ;vla-get-color_case_5
          (and 
            (= (vla-get-patternname ss_pre_filter_set_xx_obj_) "000_C05A")
          )
          (progn 
            (vla-put-color ss_pre_filter_set_xx_obj_ 20)
            (setq ssset_ (ssadd ss_pre_filter_set_xx_ename_ ssset_))
            (princ "vla-get-color_case_5")
          )
          )
          ( ;vla-get-color_case_6
          (and 
            (= (vla-get-patternname ss_pre_filter_set_xx_obj_) "000_C06")
          )
          (progn 
            (vla-put-color ss_pre_filter_set_xx_obj_ 170)
            (setq ssset_ (ssadd ss_pre_filter_set_xx_ename_ ssset_))
            (princ "vla-get-color_case_6")
          )
          )
          ( ;vla-get-color_case_7
          (and 
            (= (vla-get-patternname ss_pre_filter_set_xx_obj_) "000_C07")
          )
          (progn 
            (vla-put-color ss_pre_filter_set_xx_obj_ 190)
            (setq ssset_ (ssadd ss_pre_filter_set_xx_ename_ ssset_))
            (princ "vla-get-color_case_7")
          )
          )
          ( ;vla-get-color_case_8
          (and 
            (= (vla-get-patternname ss_pre_filter_set_xx_obj_) "000_C08")
          )
          (progn 
            (vla-put-color ss_pre_filter_set_xx_obj_ 210)
            (setq ssset_ (ssadd ss_pre_filter_set_xx_ename_ ssset_))
            (princ "vla-get-color_case_8")
          )
          )
          ( ;vla-get-color_case_9
          (and 
            (= (vla-get-patternname ss_pre_filter_set_xx_obj_) "000_C09")
          )
          (progn 
            (vla-put-color ss_pre_filter_set_xx_obj_ 230)
            (setq ssset_ (ssadd ss_pre_filter_set_xx_ename_ ssset_))
            (princ "vla-get-color_case_9")
          )
          )
          ( ;vla-get-color_case_10
          (and 
            (= (vla-get-patternname ss_pre_filter_set_xx_obj_) "000_C10")
          )
          (progn 
            (vla-put-color ss_pre_filter_set_xx_obj_ 235)
            (setq ssset_ (ssadd ss_pre_filter_set_xx_ename_ ssset_))
            (princ "vla-get-color_case_10")
          )
          )
          ( ;vla-get-color_case_11
          (and 
            (= (vla-get-patternname ss_pre_filter_set_xx_obj_) "000_C11")
          )
          (progn 
            (vla-put-color ss_pre_filter_set_xx_obj_ 240)
            (setq ssset_ (ssadd ss_pre_filter_set_xx_ename_ ssset_))
            (princ "vla-get-color_case_11")
          )
          )
          ( ;vla-get-color_case_12
          (and 
            (= (vla-get-patternname ss_pre_filter_set_xx_obj_) "000_W01")
          )
          (progn 
            (vla-put-color ss_pre_filter_set_xx_obj_ 20)
            (setq ssset_ (ssadd ss_pre_filter_set_xx_ename_ ssset_))
            (princ "vla-get-color_case_12")
          )
          )
          ( ;vla-get-color_case_13
          (and 
            (= (vla-get-patternname ss_pre_filter_set_xx_obj_) "000_W02")
          )
          (progn 
            (vla-put-color ss_pre_filter_set_xx_obj_ 40)
            (setq ssset_ (ssadd ss_pre_filter_set_xx_ename_ ssset_))
            (princ "vla-get-color_case_13")
          )
          )
          ( ;vla-get-color_case_14
          (and 
            (= (vla-get-patternname ss_pre_filter_set_xx_obj_) "000_W03")
          )
          (progn 
            (vla-put-color ss_pre_filter_set_xx_obj_ 60)
            (setq ssset_ (ssadd ss_pre_filter_set_xx_ename_ ssset_))
            (princ "vla-get-color_case_14")
          )
          )
          ( ;vla-get-color_case_15
          (and 
            (= (vla-get-patternname ss_pre_filter_set_xx_obj_) "000_W04")
          )
          (progn 
            (vla-put-color ss_pre_filter_set_xx_obj_ 80)
            (setq ssset_ (ssadd ss_pre_filter_set_xx_ename_ ssset_))
            (princ "vla-get-color_case_15")
          )
          )
          ( ;vla-get-color_case_16
          (and 
            (= (vla-get-patternname ss_pre_filter_set_xx_obj_) "000_W05")
          )
          (progn 
            (vla-put-color ss_pre_filter_set_xx_obj_ 100)
            (setq ssset_ (ssadd ss_pre_filter_set_xx_ename_ ssset_))
            (princ "vla-get-color_case_16")
          )
          )
          ( ;vla-get-color_case_17
          (and 
            (= (vla-get-patternname ss_pre_filter_set_xx_obj_) "000_W06")
          )
          (progn 
            (vla-put-color ss_pre_filter_set_xx_obj_ 120)
            (setq ssset_ (ssadd ss_pre_filter_set_xx_ename_ ssset_))
            (princ "vla-get-color_case_17")
          )
          )
          ( ;vla-get-color_case_18
          (and 
            (= (vla-get-patternname ss_pre_filter_set_xx_obj_) "000_W07")
          )
          (progn 
            (vla-put-color ss_pre_filter_set_xx_obj_ 140)
            (setq ssset_ (ssadd ss_pre_filter_set_xx_ename_ ssset_))
            (princ "vla-get-color_case_18")
          )
          )
          ( ;vla-get-color_case_19
          (and 
            (= (vla-get-patternname ss_pre_filter_set_xx_obj_) "000_W08")
          )
          (progn 
            (vla-put-color ss_pre_filter_set_xx_obj_ 20)
            (setq ssset_ (ssadd ss_pre_filter_set_xx_ename_ ssset_))
            (princ "vla-get-color_case_19")
          )
          )
          ( ;vla-get-color_case_20
          (and 
            (= (vla-get-patternname ss_pre_filter_set_xx_obj_) "000_W09")
          )
          (progn 
            (vla-put-color ss_pre_filter_set_xx_obj_ 180)
            (setq ssset_ (ssadd ss_pre_filter_set_xx_ename_ ssset_))
            (princ "vla-get-color_case_20")
          )
          )
          ( ;vla-get-color_case_21
          (and 
            (= (vla-get-patternname ss_pre_filter_set_xx_obj_) "000_W10")
          )
          (progn 
            (vla-put-color ss_pre_filter_set_xx_obj_ 200)
            (setq ssset_ (ssadd ss_pre_filter_set_xx_ename_ ssset_))
            (princ "vla-get-color_case_21")
          )
          )
          ( ;vla-get-color_case_22
          (and 
            (= (vla-get-patternname ss_pre_filter_set_xx_obj_) "000_W11")
          )
          (progn 
            (vla-put-color ss_pre_filter_set_xx_obj_ 220)
            (setq ssset_ (ssadd ss_pre_filter_set_xx_ename_ ssset_))
            (princ "vla-get-color_case_22")
          )
          )
          ( ;vla-get-color_case_23
          (and 
            (= (vla-get-patternname ss_pre_filter_set_xx_obj_) "000_W12")
          )
          (progn 
            (vla-put-color ss_pre_filter_set_xx_obj_ 240)
            (setq ssset_ (ssadd ss_pre_filter_set_xx_ename_ ssset_))
            (princ "vla-get-color_case_23")
          )
          )
          ( ;vla-get-color_case_24
          (and 
            (= (vla-get-patternname ss_pre_filter_set_xx_obj_) "000_W13")
          )
          (progn 
            (vla-put-color ss_pre_filter_set_xx_obj_ 20)
            (setq ssset_ (ssadd ss_pre_filter_set_xx_ename_ ssset_))
            (princ "vla-get-color_case_24")
          )
          )
          ( ;vla-get-color_case_25
          (and 
            (= (vla-get-patternname ss_pre_filter_set_xx_obj_) "000_W14")
          )
          (progn 
            (vla-put-color ss_pre_filter_set_xx_obj_ 40)
            (setq ssset_ (ssadd ss_pre_filter_set_xx_ename_ ssset_))
            (princ "vla-get-color_case_25")
          )
          )
          ( ;vla-get-color_case_26
          (and 
            (= (vla-get-patternname ss_pre_filter_set_xx_obj_) "000_W15")
          )
          (progn 
            (vla-put-color ss_pre_filter_set_xx_obj_ 60)
            (setq ssset_ (ssadd ss_pre_filter_set_xx_ename_ ssset_))
            (princ "vla-get-color_case_26")
          )
          )
          ( ;vla-get-color_case_27
          (and 
            (= (vla-get-patternname ss_pre_filter_set_xx_obj_) "000_W16")
          )
          (progn 
            (vla-put-color ss_pre_filter_set_xx_obj_ 80)
            (setq ssset_ (ssadd ss_pre_filter_set_xx_ename_ ssset_))
            (princ "vla-get-color_case_27")
          )
          )
          ( ;vla-get-color_case_28
          (and 
            (= (vla-get-patternname ss_pre_filter_set_xx_obj_) "000_W17")
          )
          (progn 
            (vla-put-color ss_pre_filter_set_xx_obj_ 100)
            (setq ssset_ (ssadd ss_pre_filter_set_xx_ename_ ssset_))
            (princ "vla-get-color_case_28")
          )
          )
          ( ;vla-get-color_case_29
          (and 
            (= (vla-get-patternname ss_pre_filter_set_xx_obj_) "000_W18")
          )
          (progn 
            (vla-put-color ss_pre_filter_set_xx_obj_ 120)
            (setq ssset_ (ssadd ss_pre_filter_set_xx_ename_ ssset_))
            (princ "vla-get-color_case_29")
          )
          )
          ( ;vla-get-color_case_30
          (and 
            (= (vla-get-patternname ss_pre_filter_set_xx_obj_) "000_W19")
          )
          (progn 
            (vla-put-color ss_pre_filter_set_xx_obj_ 140)
            (setq ssset_ (ssadd ss_pre_filter_set_xx_ename_ ssset_))
            (princ "vla-get-color_case_30")
          )
          )
          ( ;vla-get-color_case_31
          (and 
            (= (vla-get-patternname ss_pre_filter_set_xx_obj_) "000_W20")
          )
          (progn 
            (vla-put-color ss_pre_filter_set_xx_obj_ 160)
            (setq ssset_ (ssadd ss_pre_filter_set_xx_ename_ ssset_))
            (princ "vla-get-color_case_31")
          )
          )
          ( ;vla-get-color_case_32
          (and 
            (= (vla-get-patternname ss_pre_filter_set_xx_obj_) "000_W21")
          )
          (progn 
            (vla-put-color ss_pre_filter_set_xx_obj_ 180)
            (setq ssset_ (ssadd ss_pre_filter_set_xx_ename_ ssset_))
            (princ "vla-get-color_case_32")
          )
          )
          ( ;vla-get-color_case_33
          (and 
            (= (vla-get-patternname ss_pre_filter_set_xx_obj_) "000_W22")
          )
          (progn 
            (vla-put-color ss_pre_filter_set_xx_obj_ 200)
            (setq ssset_ (ssadd ss_pre_filter_set_xx_ename_ ssset_))
            (princ "vla-get-color_case_33")
          )
          )
        )
        (setq ss_pre_filter_set_xx_i (+ ss_pre_filter_set_xx_i 1))
      )
    ;
    (command "pselect"  ssset_ "" )
  )
  (defun c:PPLINE-ITD_detect_wall_Sym_dewall ()
    ;selection_set_for_fillter_blk_name
      (if  ;pre_select_ssget_or_post_select_ssget
        (=
          (setq ss_pre_filter_set_xx_ (ssget "x"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ; (setq ss_pre_filter_set_xx_filter_ (TA:EF_Filter_ss_set_ ss_pre_filter_set_xx_ "A$C441E3E01")) ;METHOD 1
    (setq ss_pre_filter_set_xx_filter_ (TA:EF_Filter_ss_set_ ss_pre_filter_set_xx_ "A$C441E3E01")) ;METHOD 2
    ;preloop_and_while
      (setq ss_pre_filter_set_xx_filter_i 0)
      (while (< ss_pre_filter_set_xx_filter_i (sslength ss_pre_filter_set_xx_filter_))
        (setq ss_pre_filter_set_xx_filter_ename_ (ssname ss_pre_filter_set_xx_filter_ ss_pre_filter_set_xx_filter_i))
        (setq ss_pre_filter_set_xx_filter_obj_ (vlax-ename->vla-object ss_pre_filter_set_xx_filter_ename_))
        (setq att_name "w10")
          (cond 
          ;
            (;vla-get-color_case_12a
              (and
                (= (LM:vl-getattributevalue ss_pre_filter_set_xx_filter_obj_ att_name ) "W00")
              )
              (progn
                (vla-put-color ss_pre_filter_set_xx_filter_obj_ 251)
                (princ "vla-get-color_case_12")
              )
            )
            (;vla-get-color_case_12
              (and
                (= (LM:vl-getattributevalue ss_pre_filter_set_xx_filter_obj_ att_name ) "W01")
              )
              (progn
                (vla-put-color ss_pre_filter_set_xx_filter_obj_ 251)
                (princ "vla-get-color_case_12")
              )
            )
            (;vla-get-color_case_13
              (and
                (= (LM:vl-getattributevalue ss_pre_filter_set_xx_filter_obj_ att_name ) "W02")
              )
              (progn
                (vla-put-color ss_pre_filter_set_xx_filter_obj_ 251)
                (princ "vla-get-color_case_13")
              )
            )
            (;vla-get-color_case_14
              (and
                (= (LM:vl-getattributevalue ss_pre_filter_set_xx_filter_obj_ att_name ) "W03")
              )
              (progn
                (vla-put-color ss_pre_filter_set_xx_filter_obj_ 251)
                (princ "vla-get-color_case_14")
              )
            )
            (;vla-get-color_case_15
              (and
                (= (LM:vl-getattributevalue ss_pre_filter_set_xx_filter_obj_ att_name ) "W04")
              )
              (progn
                (vla-put-color ss_pre_filter_set_xx_filter_obj_ 251)
                (princ "vla-get-color_case_15")
              )
            )
            (;vla-get-color_case_16
              (and
                (= (LM:vl-getattributevalue ss_pre_filter_set_xx_filter_obj_ att_name ) "W05")
              )
              (progn
                (vla-put-color ss_pre_filter_set_xx_filter_obj_ 251)
                (princ "vla-get-color_case_16")
              )
            )
          ;
            (;vla-get-color_case_17
              (and
                (= (LM:vl-getattributevalue ss_pre_filter_set_xx_filter_obj_ att_name ) "W06")
              )
              (progn
                (vla-put-color ss_pre_filter_set_xx_filter_obj_ 120)
                (princ "vla-get-color_case_17")
              )
            )
          ;
            (;vla-get-color_case_18
              (and
                (= (LM:vl-getattributevalue ss_pre_filter_set_xx_filter_obj_ att_name ) "W07")
              )
              (progn
                (vla-put-color ss_pre_filter_set_xx_filter_obj_ 251)
                (princ "vla-get-color_case_18")
              )
            )
          ;
            (;vla-get-color_case_19
              (and
                (= (LM:vl-getattributevalue ss_pre_filter_set_xx_filter_obj_ att_name ) "W08")
              )
              (progn
                (vla-put-color ss_pre_filter_set_xx_filter_obj_ 20)
                (princ "vla-get-color_case_19")
              )
            )
            (;vla-get-color_case_20
              (and
                (= (LM:vl-getattributevalue ss_pre_filter_set_xx_filter_obj_ att_name ) "W09")
              )
              (progn
                (vla-put-color ss_pre_filter_set_xx_filter_obj_ 180)
                (princ "vla-get-color_case_20")
              )
            )
            (;vla-get-color_case_21
              (and
                (= (LM:vl-getattributevalue ss_pre_filter_set_xx_filter_obj_ att_name ) "W10")
              )
              (progn
                (vla-put-color ss_pre_filter_set_xx_filter_obj_ 200)
                (princ "vla-get-color_case_21")
              )
            )
            (;vla-get-color_case_22
              (and
                (= (LM:vl-getattributevalue ss_pre_filter_set_xx_filter_obj_ att_name ) "W11")
              )
              (progn
                (vla-put-color ss_pre_filter_set_xx_filter_obj_ 220)
                (princ "vla-get-color_case_22")
              )
            )
            (;vla-get-color_case_23
              (and
                (= (LM:vl-getattributevalue ss_pre_filter_set_xx_filter_obj_ att_name ) "W12")
              )
              (progn
                (vla-put-color ss_pre_filter_set_xx_filter_obj_ 240)
                (princ "vla-get-color_case_23")
              )
            )
            ;
              (;vla-get-color_case_24
                (and
                  (= (LM:vl-getattributevalue ss_pre_filter_set_xx_filter_obj_ att_name ) "W13")
                )
                (progn
                  (vla-put-color ss_pre_filter_set_xx_filter_obj_ 251)
                  (princ "vla-get-color_case_24")
                )
              )
              (;vla-get-color_case_25
                (and
                  (= (LM:vl-getattributevalue ss_pre_filter_set_xx_filter_obj_ att_name ) "W14")
                )
                (progn
                  (vla-put-color ss_pre_filter_set_xx_filter_obj_ 251)
                  (princ "vla-get-color_case_25")
                )
              )
              (;vla-get-color_case_26
                (and
                  (= (LM:vl-getattributevalue ss_pre_filter_set_xx_filter_obj_ att_name ) "W15")
                )
                (progn
                  (vla-put-color ss_pre_filter_set_xx_filter_obj_ 251)
                  (princ "vla-get-color_case_26")
                )
              )
              (;vla-get-color_case_27
                (and
                  (= (LM:vl-getattributevalue ss_pre_filter_set_xx_filter_obj_ att_name ) "W16")
                )
                (progn
                  (vla-put-color ss_pre_filter_set_xx_filter_obj_ 251)
                  (princ "vla-get-color_case_27")
                )
              )
              (;vla-get-color_case_28
                (and
                  (= (LM:vl-getattributevalue ss_pre_filter_set_xx_filter_obj_ att_name )  att_name)
                )
                (progn
                  (vla-put-color ss_pre_filter_set_xx_filter_obj_ 251)
                  (princ "vla-get-color_case_28")
                )
              )
            ;
            (;vla-get-color_case_29
              (and
                (= (LM:vl-getattributevalue ss_pre_filter_set_xx_filter_obj_ att_name ) "W18")
              )
              (progn
                (vla-put-color ss_pre_filter_set_xx_filter_obj_ 120)
                (princ "vla-get-color_case_29")
              )
            )
            ;
              (;vla-get-color_case_30
                (and
                  (= (LM:vl-getattributevalue ss_pre_filter_set_xx_filter_obj_ att_name ) "W19")
                )
                (progn
                  (vla-put-color ss_pre_filter_set_xx_filter_obj_ 251)
                  (princ "vla-get-color_case_30")
                )
              )
            ;
            (;vla-get-color_case_31
              (and
                (= (LM:vl-getattributevalue ss_pre_filter_set_xx_filter_obj_ att_name ) "W20")
              )
              (progn
                (vla-put-color ss_pre_filter_set_xx_filter_obj_ 160)
                (princ "vla-get-color_case_31")
              )
            )
            (;vla-get-color_case_32
              (and
                (= (LM:vl-getattributevalue ss_pre_filter_set_xx_filter_obj_ att_name ) "W21")
              )
              (progn
                (vla-put-color ss_pre_filter_set_xx_filter_obj_ 180)
                (princ "vla-get-color_case_32")
              )
            )
            ;
              (;vla-get-color_case_33
                (and
                  (= (LM:vl-getattributevalue ss_pre_filter_set_xx_filter_obj_ att_name ) "W22")
                )
                (progn
                  (vla-put-color ss_pre_filter_set_xx_filter_obj_ 251)
                  (princ "vla-get-color_case_33")
                )
              )
            ;

          )
        
        (setq ss_pre_filter_set_xx_filter_i (+ ss_pre_filter_set_xx_filter_i 1))
      )
    ;
  )
  (defun c:PPLINE-ITD_detect_celing_Sym_cewall () 
    ;selection_set_for_fillter_blk_name
    (if  ;pre_select_ssget_or_post_select_ssget
      (= 
        (setq ss_pre_filter_set_xx_ (ssget "x" 
                                          (list 
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn 
        (setq ss_pre_filter_set_xx_ (ssget 
                                      (list 
                                        (cons 0 "INSERT") ;type of object
                                        ; (cons 8 "000 - GRID")   ;kind of layer
                                        ; (cons 2 "000-GRID_LINE_DYN")       ;kind of nameblock
                                        ; (cons 62 1)           ;kind of color call sign with color code index
                                      )
                                    )
        )
      )
      (sslength ss_pre_filter_set_xx_)
    )
    ;
    ; (setq ss_pre_filter_set_xx_filter_ (TA:EF_Filter_ss_set_ ss_pre_filter_set_xx_ "A$C441E3E01")) ;METHOD 1
    (setq ss_pre_filter_set_xx_filter_ (TA:EF_Filter_ss_set_ ss_pre_filter_set_xx_ "qerg" ) ) ;METHOD 2
    ;preloop_and_while
    (setq ss_pre_filter_set_xx_filter_i 0)
    (while (< ss_pre_filter_set_xx_filter_i (sslength ss_pre_filter_set_xx_filter_)) 
      (setq ss_pre_filter_set_xx_filter_ename_ (ssname ss_pre_filter_set_xx_filter_ 
                                                      ss_pre_filter_set_xx_filter_i
                                              )
      )
      (setq ss_pre_filter_set_xx_obj_ (vlax-ename->vla-object ss_pre_filter_set_xx_filter_ename_))

      (cond 
        ( ;vla-get-color_case_
        (and 
          (= (LM:vl-getattributevalue ss_pre_filter_set_xx_obj_ "C00") "C00")
        )
        (progn 
          (vla-put-color ss_pre_filter_set_xx_obj_ 251)
          (princ "vla-get-color_case_1")
        )
        )
        ( ;vla-get-color_case_1
        (and 
          (= (LM:vl-getattributevalue ss_pre_filter_set_xx_obj_ "C00") "C01")
        )
        (progn 
          (vla-put-color ss_pre_filter_set_xx_obj_ 70)
          (princ "vla-get-color_case_1")
        )
        )
        ( ;vla-get-color_case_2
        (and 
          (= (LM:vl-getattributevalue ss_pre_filter_set_xx_obj_ "C00") "C02")
        )
        (progn 
          (vla-put-color ss_pre_filter_set_xx_obj_ 90)
          (princ "vla-get-color_case_2")
        )
        )
        ( ;vla-get-color_case_3
        (and 
          (= (LM:vl-getattributevalue ss_pre_filter_set_xx_obj_ "C00") "C03")
        )
        (progn 
          (vla-put-color ss_pre_filter_set_xx_obj_ 20)
          (princ "vla-get-color_case_3")
        )
        )
        ( ;vla-get-color_case_4
        (and 
          (= (LM:vl-getattributevalue ss_pre_filter_set_xx_obj_ "C00") "C04")
        )
        (progn 
          (vla-put-color ss_pre_filter_set_xx_obj_ 130)
          (princ "vla-get-color_case_4")
        )
        )
        ( ;vla-get-color_case_5
        (and 
          (= (LM:vl-getattributevalue ss_pre_filter_set_xx_obj_ "C00") "C05")
        )
        (progn 
          (vla-put-color ss_pre_filter_set_xx_obj_ 20)
          (princ "vla-get-color_case_5")
        )
        )
        ( ;vla-get-color_case_5
        (and 
          (= (LM:vl-getattributevalue ss_pre_filter_set_xx_obj_ "C00") "C05A")
        )
        (progn 
          (vla-put-color ss_pre_filter_set_xx_obj_ 20)
          (princ "vla-get-color_case_5")
        )
        )
        ( ;vla-get-color_case_6
        (and 
          (= (LM:vl-getattributevalue ss_pre_filter_set_xx_obj_ "C00") "C06")
        )
        (progn 
          (vla-put-color ss_pre_filter_set_xx_obj_ 170)
          (princ "vla-get-color_case_6")
        )
        )
        ( ;vla-get-color_case_7
        (and 
          (= (LM:vl-getattributevalue ss_pre_filter_set_xx_obj_ "C00") "C07")
        )
        (progn 
          (vla-put-color ss_pre_filter_set_xx_obj_ 190)
          (princ "vla-get-color_case_7")
        )
        )
        ( ;vla-get-color_case_8
        (and 
          (= (LM:vl-getattributevalue ss_pre_filter_set_xx_obj_ "C00") "C08")
        )
        (progn 
          (vla-put-color ss_pre_filter_set_xx_obj_ 210)
          (princ "vla-get-color_case_8")
        )
        )
        ( ;vla-get-color_case_9
        (and 
          (= (LM:vl-getattributevalue ss_pre_filter_set_xx_obj_ "C00") "C09")
        )
        (progn 
          (vla-put-color ss_pre_filter_set_xx_obj_ 230)
          (princ "vla-get-color_case_9")
        )
        )
        ( ;vla-get-color_case_10
        (and 
          (= (LM:vl-getattributevalue ss_pre_filter_set_xx_obj_ "C00") "C10")
        )
        (progn 
          (vla-put-color ss_pre_filter_set_xx_obj_ 235)
          (princ "vla-get-color_case_10")
        )
        )
        ( ;vla-get-color_case_11
        (and 
          (= (LM:vl-getattributevalue ss_pre_filter_set_xx_obj_ "C00") "C11")
        )
        (progn 
          (vla-put-color ss_pre_filter_set_xx_obj_ 240)
          (princ "vla-get-color_case_11")
        )
        )
      )


      (setq ss_pre_filter_set_xx_filter_i (+ ss_pre_filter_set_xx_filter_i 1))
    )
    ;
  )
  (defun c:PPLINE-ITD_detect_bubble_Sym_asf ()
    ;selection_set_for_fillter_blk_name
      (if  ;pre_select_ssget_or_post_select_ssget
        (=
          (setq ss_pre_filter_set_xx_ (ssget "x"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_filter_ (TA:EF_Filter_ss_set_ ss_pre_filter_set_xx_ "ROOM"))
    ;preloop_and_while
      (setq ss_pre_filter_set_xx_filter_i 0)
      (while (< ss_pre_filter_set_xx_filter_i (sslength ss_pre_filter_set_xx_filter_))
        (setq ss_pre_filter_set_xx_filter_ename_ (ssname ss_pre_filter_set_xx_filter_ ss_pre_filter_set_xx_filter_i))
        (setq ss_pre_filter_set_xx_filter_obj_ (vlax-ename->vla-object ss_pre_filter_set_xx_filter_ename_))
        
          (cond
            (;vla-get-color_case_17
              (or 
                (= (wcmatch (LM:vl-getattributevalue ss_pre_filter_set_xx_filter_obj_ "room_name") (strcat "*" "TICKET"    "*"))   T)
                (= (wcmatch (LM:vl-getattributevalue ss_pre_filter_set_xx_filter_obj_ "room_name") (strcat "*" "ESCAPE SHAFT"    "*"))   T)
                (= (wcmatch (LM:vl-getattributevalue ss_pre_filter_set_xx_filter_obj_ "room_name") (strcat "*" "SOR. RM."    "*"))   T)
                
                (= (wcmatch (LM:vl-getattributevalue ss_pre_filter_set_xx_filter_obj_ "room_name") (strcat "*" "OPERATIONS"    "*"))   T)
  
              )
              (progn
                (vla-put-color ss_pre_filter_set_xx_filter_obj_ 241)
                (setq ssbox (TA:ename+vla-getboundingbox  ss_pre_filter_set_xx_filter_obj_))
                (command "ATTSYNC" "S" ss_pre_filter_set_xx_filter_ename_ "Y" )
                
                (setq ssssset_ (ssget "C" (cadr ssbox)  (caddr ssbox)
                                              (list 
                                                (cons 0 "LEADER") ;type of object
                                                ; (cons 8 "000 - GRID")   ;kind of layer
                                                ; (cons 2 "000-GRID_LINE_DYN")       ;kind of nameblock
                                                ; (cons 62 1)           ;kind of color call sign with color code index
                                              )
                                            )
                )
                ;preloop_and_while
                  (setq ssssset_i 0)
                  (while (and (/= ssssset_ nil )(< ssssset_i (sslength ssssset_)))
                    (setq ssssset_ename_ (ssname ssssset_ ssssset_i))
                    (setq ssssset_obj_ (vlax-ename->vla-object ssssset_ename_))
                      (if 
                        (= (vla-get-objectname ssssset_obj_) "AcDbLeader")
                        (progn 
                          (vla-put-color ssssset_obj_ 241)
                          (vla-put-dimensionlinecolor ssssset_obj_ 241)
                          
                        )
                      )
                    (setq ssssset_i (+ ssssset_i 1))
                  )
                ;
                (princ "vla-get-color_case_17")
              )
            )
          )
          
        
        (setq ss_pre_filter_set_xx_filter_i (+ ss_pre_filter_set_xx_filter_i 1))
      )
    ;
    (c:PPLINE-ITD_detect_room_num_Rsf)
  )
  (defun c:PPLINE-ITD_detect_bubble_Sym_bsf ()
    ;selection_set_for_fillter_blk_name
      (if  ;pre_select_ssget_or_post_select_ssget
        (=
          (setq ss_pre_filter_set_xx_ (ssget "x"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ; (setq ss_pre_filter_set_xx_filter_ (TA:EF_Filter_ss_set_ ss_pre_filter_set_xx_ "A$C51E56039"))
    ; (setq ss_pre_filter_set_xx_filter_ (TA:EF_Filter_ss_set_ ss_pre_filter_set_xx_ "q"))
    (setq ss_pre_filter_set_xx_filter_ ss_pre_filter_set_xx_)
    ;preloop_and_while
      (setq ss_pre_filter_set_xx_filter_i 0)
      (while (< ss_pre_filter_set_xx_filter_i (sslength ss_pre_filter_set_xx_filter_))
        (setq ss_pre_filter_set_xx_filter_ename_ (ssname ss_pre_filter_set_xx_filter_ ss_pre_filter_set_xx_filter_i))
        (setq ss_pre_filter_set_xx_filter_obj_ (vlax-ename->vla-object ss_pre_filter_set_xx_filter_ename_))
        (if 
          (and 
            (= (vla-get-hasattributes ss_pre_filter_set_xx_filter_obj_) :vlax-true)
            (/= (LM:vl-getattributevalue ss_pre_filter_set_xx_filter_obj_ "NOOO") nil)
          )
          (progn
            (cond
              (;vla-get-color_case_17
                (or 
                  (= (wcmatch (LM:vl-getattributevalue ss_pre_filter_set_xx_filter_obj_ "NOOO") (strcat "*" "6004"    "*"))   T)
                  
                  (= (wcmatch (LM:vl-getattributevalue ss_pre_filter_set_xx_filter_obj_ "NOOO") (strcat "*" "6103"    "*"))   T)
                  (= (wcmatch (LM:vl-getattributevalue ss_pre_filter_set_xx_filter_obj_ "NOOO") (strcat "*" "6104"    "*"))   T)
                  (= (wcmatch (LM:vl-getattributevalue ss_pre_filter_set_xx_filter_obj_ "NOOO") (strcat "*" "6150"    "*"))   T)
                  (= (wcmatch (LM:vl-getattributevalue ss_pre_filter_set_xx_filter_obj_ "NOOO") (strcat "*" "6151"    "*"))   T)
                  (= (wcmatch (LM:vl-getattributevalue ss_pre_filter_set_xx_filter_obj_ "NOOO") (strcat "*" "6152"    "*"))   T)
                  (= (wcmatch (LM:vl-getattributevalue ss_pre_filter_set_xx_filter_obj_ "NOOO") (strcat "*" "6153"    "*"))   T)

                  (= (wcmatch (LM:vl-getattributevalue ss_pre_filter_set_xx_filter_obj_ "NOOO") (strcat "*" "6250"    "*"))   T)
                  (= (wcmatch (LM:vl-getattributevalue ss_pre_filter_set_xx_filter_obj_ "NOOO") (strcat "*" "6251"    "*"))   T)
                  (= (wcmatch (LM:vl-getattributevalue ss_pre_filter_set_xx_filter_obj_ "NOOO") (strcat "*" "6252"    "*"))   T)
                  (= (wcmatch (LM:vl-getattributevalue ss_pre_filter_set_xx_filter_obj_ "NOOO") (strcat "*" "6255"    "*"))   T)
                  (= (wcmatch (LM:vl-getattributevalue ss_pre_filter_set_xx_filter_obj_ "NOOO") (strcat "*" "6257"    "*"))   T)
                  (= (wcmatch (LM:vl-getattributevalue ss_pre_filter_set_xx_filter_obj_ "NOOO") (strcat "*" "6264"    "*"))   T)
                  (= (wcmatch (LM:vl-getattributevalue ss_pre_filter_set_xx_filter_obj_ "NOOO") (strcat "*" "6271"    "*"))   T)
                  (= (wcmatch (LM:vl-getattributevalue ss_pre_filter_set_xx_filter_obj_ "NOOO") (strcat "*" "6272"    "*"))   T)
                  (= (wcmatch (LM:vl-getattributevalue ss_pre_filter_set_xx_filter_obj_ "NOOO") (strcat "*" "6274"    "*"))   T)

                  (= (wcmatch (LM:vl-getattributevalue ss_pre_filter_set_xx_filter_obj_ "NOOO") (strcat "*" "6301"    "*"))   T)
                  (= (wcmatch (LM:vl-getattributevalue ss_pre_filter_set_xx_filter_obj_ "NOOO") (strcat "*" "6307"    "*"))   T)

                  (= (wcmatch (LM:vl-getattributevalue ss_pre_filter_set_xx_filter_obj_ "NOOO") (strcat "*" "6403"  "*"))   T)
                  (= (wcmatch (LM:vl-getattributevalue ss_pre_filter_set_xx_filter_obj_ "NOOO") (strcat "*" "6408"  "*"))   T)
                  (= (wcmatch (LM:vl-getattributevalue ss_pre_filter_set_xx_filter_obj_ "NOOO") (strcat "*" "6409"  "*"))   T)
                  (= (wcmatch (LM:vl-getattributevalue ss_pre_filter_set_xx_filter_obj_ "NOOO") (strcat "*" "6414"  "*"))   T)

                  (= (wcmatch (LM:vl-getattributevalue ss_pre_filter_set_xx_filter_obj_ "NOOO") (strcat "*" "6500"    "*"))   T)
                  (= (wcmatch (LM:vl-getattributevalue ss_pre_filter_set_xx_filter_obj_ "NOOO") (strcat "*" "6507"    "*"))   T)
                  
                  (= (wcmatch (LM:vl-getattributevalue ss_pre_filter_set_xx_filter_obj_ "NOOO") (strcat "*" "6505"    "*"))   T)
                  (= (wcmatch (LM:vl-getattributevalue ss_pre_filter_set_xx_filter_obj_ "NOOO") (strcat "*" "6555"    "*"))   T)
                  
                  (= (wcmatch (LM:vl-getattributevalue ss_pre_filter_set_xx_filter_obj_ "NOOO") (strcat "*" "6600"    "*"))   T)
                )
                (progn
                  (vla-put-color ss_pre_filter_set_xx_filter_obj_ 241)
                  (setq ssbox (TA:ename+vla-getboundingbox  ss_pre_filter_set_xx_filter_obj_))
                  (command "ATTSYNC" "S" ss_pre_filter_set_xx_filter_ename_ "Y" )
                  
                  (setq ssssset_ (ssget "C" (cadr ssbox)  (caddr ssbox)
                                                (list 
                                                  (cons 0 "LEADER") ;type of object
                                                  ; (cons 8 "000 - GRID")   ;kind of layer
                                                  ; (cons 2 "000-GRID_LINE_DYN")       ;kind of nameblock
                                                  ; (cons 62 1)           ;kind of color call sign with color code index
                                                )
                                              )
                  )
                  ;preloop_and_while
                    (setq ssssset_i 0)
                    (while (and (/= ssssset_ nil )(< ssssset_i (sslength ssssset_)))
                      (setq ssssset_ename_ (ssname ssssset_ ssssset_i))
                      (setq ssssset_obj_ (vlax-ename->vla-object ssssset_ename_))
                        (if 
                          (= (vla-get-objectname ssssset_obj_) "AcDbLeader")
                          (progn 
                            (vla-put-color ssssset_obj_ 241)
                            (vla-put-dimensionlinecolor ssssset_obj_ 241)
                            
                          )
                        )
                      (setq ssssset_i (+ ssssset_i 1))
                    )
                  ;
                  (princ "vla-get-color_case_17")
                )
              )
            )
          )
        )
          
        
        (setq ss_pre_filter_set_xx_filter_i (+ ss_pre_filter_set_xx_filter_i 1))
      )
    ;
  )
  (defun c:PPLINE-ITD_detect_bubble_Sym_bbsf ()
    ;selection_set_for_fillter_blk_name
      (if  ;pre_select_ssget_or_post_select_ssget
        (=
          (setq ss_pre_filter_set_xx_ (ssget "x"
                                            (list
                                              (cons 0 "INSERT,mtext,text") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT,mtext,text") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ; (setq ss_pre_filter_set_xx_filter_ (TA:EF_Filter_ss_set_ ss_pre_filter_set_xx_ "A$C51E56039"))
    ; (setq ss_pre_filter_set_xx_filter_ (TA:EF_Filter_ss_set_ ss_pre_filter_set_xx_ "q"))
    (setq ss_pre_filter_set_xx_filter_ ss_pre_filter_set_xx_)
    ;preloop_and_while
      (setq ss_pre_filter_set_xx_filter_i 0)
      (while (< ss_pre_filter_set_xx_filter_i (sslength ss_pre_filter_set_xx_filter_))
        (setq ss_pre_filter_set_xx_filter_ename_ (ssname ss_pre_filter_set_xx_filter_ ss_pre_filter_set_xx_filter_i))
        (setq ss_pre_filter_set_xx_filter_obj_ (vlax-ename->vla-object ss_pre_filter_set_xx_filter_ename_))
        (cond
          (;att-case
            (and 
              (= (vla-get-objectname ss_pre_filter_set_xx_filter_obj_) "AcDbBlockReference")
              (= (vla-get-hasattributes ss_pre_filter_set_xx_filter_obj_) :vlax-true)
              (/= (LM:vl-getattributevalue-val-TA-Modifies ss_pre_filter_set_xx_filter_obj_) nil)
            )
            (progn
              (cond
                (
                  (or
                    
                    (= (wcmatch (LM:lst->str (LM:vl-getattributevalue-val-TA-Modifies ss_pre_filter_set_xx_filter_obj_ ) "_" ) (strcat "*" "DISABLED" "*") )   T)
                    (= (wcmatch (LM:lst->str (LM:vl-getattributevalue-val-TA-Modifies ss_pre_filter_set_xx_filter_obj_ ) "_" ) (strcat "*" "OPERATIONS RM." "*") )   T)
                    (= (wcmatch (LM:lst->str (LM:vl-getattributevalue-val-TA-Modifies ss_pre_filter_set_xx_filter_obj_ ) "_" ) (strcat "*" "TICKET OFFICE" "*") )   T)
                    (= (wcmatch (LM:lst->str (LM:vl-getattributevalue-val-TA-Modifies ss_pre_filter_set_xx_filter_obj_ ) "_" ) (strcat "*" "SOR. RM." "*") )   T)
                    (= (wcmatch (LM:lst->str (LM:vl-getattributevalue-val-TA-Modifies ss_pre_filter_set_xx_filter_obj_ ) "_" ) (strcat "*" "STORE" "*") )   T)
                    (= (wcmatch (LM:lst->str (LM:vl-getattributevalue-val-TA-Modifies ss_pre_filter_set_xx_filter_obj_ ) "_" ) (strcat "*" "SERVICE COLUMN" "*") )   T)
                    (= (wcmatch (LM:lst->str (LM:vl-getattributevalue-val-TA-Modifies ss_pre_filter_set_xx_filter_obj_ ) "_" ) (strcat "*" "ESCAPE SHAFT" "*") )   T)
                    
                    (= (wcmatch (LM:lst->str (LM:vl-getattributevalue-val-TA-Modifies ss_pre_filter_set_xx_filter_obj_ ) "_" ) (strcat "*" "6004"    "*"))   T)
                    (= (wcmatch (LM:lst->str (LM:vl-getattributevalue-val-TA-Modifies ss_pre_filter_set_xx_filter_obj_ ) "_" ) (strcat "*" "6050"    "*"))   T)
                  
                    (= (wcmatch (LM:lst->str (LM:vl-getattributevalue-val-TA-Modifies ss_pre_filter_set_xx_filter_obj_ ) "_" ) (strcat "*" "6103"    "*"))   T)
                    (= (wcmatch (LM:lst->str (LM:vl-getattributevalue-val-TA-Modifies ss_pre_filter_set_xx_filter_obj_ ) "_" ) (strcat "*" "6104"    "*"))   T)
                    (= (wcmatch (LM:lst->str (LM:vl-getattributevalue-val-TA-Modifies ss_pre_filter_set_xx_filter_obj_ ) "_" ) (strcat "*" "6104"    "*"))   T)
                    (= (wcmatch (LM:lst->str (LM:vl-getattributevalue-val-TA-Modifies ss_pre_filter_set_xx_filter_obj_ ) "_" ) (strcat "*" "6150"    "*"))   T)
                    (= (wcmatch (LM:lst->str (LM:vl-getattributevalue-val-TA-Modifies ss_pre_filter_set_xx_filter_obj_ ) "_" ) (strcat "*" "6151"    "*"))   T)
                    (= (wcmatch (LM:lst->str (LM:vl-getattributevalue-val-TA-Modifies ss_pre_filter_set_xx_filter_obj_ ) "_" ) (strcat "*" "6152"    "*"))   T)
                    (= (wcmatch (LM:lst->str (LM:vl-getattributevalue-val-TA-Modifies ss_pre_filter_set_xx_filter_obj_ ) "_" ) (strcat "*" "6153"    "*"))   T)

                    (= (wcmatch (LM:lst->str (LM:vl-getattributevalue-val-TA-Modifies ss_pre_filter_set_xx_filter_obj_ ) "_" ) (strcat "*" "6205"    "*"))   T)
                    
                    (= (wcmatch (LM:lst->str (LM:vl-getattributevalue-val-TA-Modifies ss_pre_filter_set_xx_filter_obj_ ) "_" ) (strcat "*" "6250"    "*"))   T)
                    (= (wcmatch (LM:lst->str (LM:vl-getattributevalue-val-TA-Modifies ss_pre_filter_set_xx_filter_obj_ ) "_" ) (strcat "*" "6251"    "*"))   T)
                    (= (wcmatch (LM:lst->str (LM:vl-getattributevalue-val-TA-Modifies ss_pre_filter_set_xx_filter_obj_ ) "_" ) (strcat "*" "6252"    "*"))   T)
                    (= (wcmatch (LM:lst->str (LM:vl-getattributevalue-val-TA-Modifies ss_pre_filter_set_xx_filter_obj_ ) "_" ) (strcat "*" "6255"    "*"))   T)
                    (= (wcmatch (LM:lst->str (LM:vl-getattributevalue-val-TA-Modifies ss_pre_filter_set_xx_filter_obj_ ) "_" ) (strcat "*" "6257"    "*"))   T)
                    (= (wcmatch (LM:lst->str (LM:vl-getattributevalue-val-TA-Modifies ss_pre_filter_set_xx_filter_obj_ ) "_" ) (strcat "*" "6264"    "*"))   T)
                    (= (wcmatch (LM:lst->str (LM:vl-getattributevalue-val-TA-Modifies ss_pre_filter_set_xx_filter_obj_ ) "_" ) (strcat "*" "6267"    "*"))   T)
                    (= (wcmatch (LM:lst->str (LM:vl-getattributevalue-val-TA-Modifies ss_pre_filter_set_xx_filter_obj_ ) "_" ) (strcat "*" "6269"    "*"))   T)
                    (= (wcmatch (LM:lst->str (LM:vl-getattributevalue-val-TA-Modifies ss_pre_filter_set_xx_filter_obj_ ) "_" ) (strcat "*" "6271"    "*"))   T)
                    (= (wcmatch (LM:lst->str (LM:vl-getattributevalue-val-TA-Modifies ss_pre_filter_set_xx_filter_obj_ ) "_" ) (strcat "*" "6272"    "*"))   T)
                    (= (wcmatch (LM:lst->str (LM:vl-getattributevalue-val-TA-Modifies ss_pre_filter_set_xx_filter_obj_ ) "_" ) (strcat "*" "6274"    "*"))   T)

                    (= (wcmatch (LM:lst->str (LM:vl-getattributevalue-val-TA-Modifies ss_pre_filter_set_xx_filter_obj_ ) "_" ) (strcat "*" "6301"    "*"))   T)
                    (= (wcmatch (LM:lst->str (LM:vl-getattributevalue-val-TA-Modifies ss_pre_filter_set_xx_filter_obj_ ) "_" ) (strcat "*" "6303"    "*"))   T)
                    (= (wcmatch (LM:lst->str (LM:vl-getattributevalue-val-TA-Modifies ss_pre_filter_set_xx_filter_obj_ ) "_" ) (strcat "*" "6306"    "*"))   T)
                    (= (wcmatch (LM:lst->str (LM:vl-getattributevalue-val-TA-Modifies ss_pre_filter_set_xx_filter_obj_ ) "_" ) (strcat "*" "6307"    "*"))   T)

                    (= (wcmatch (LM:lst->str (LM:vl-getattributevalue-val-TA-Modifies ss_pre_filter_set_xx_filter_obj_ ) "_" ) (strcat "*" "6403"  "*"))   T)
                    (= (wcmatch (LM:lst->str (LM:vl-getattributevalue-val-TA-Modifies ss_pre_filter_set_xx_filter_obj_ ) "_" ) (strcat "*" "6408"  "*"))   T)
                    (= (wcmatch (LM:lst->str (LM:vl-getattributevalue-val-TA-Modifies ss_pre_filter_set_xx_filter_obj_ ) "_" ) (strcat "*" "6409"  "*"))   T)
                    (= (wcmatch (LM:lst->str (LM:vl-getattributevalue-val-TA-Modifies ss_pre_filter_set_xx_filter_obj_ ) "_" ) (strcat "*" "6411"  "*"))   T)
                    (= (wcmatch (LM:lst->str (LM:vl-getattributevalue-val-TA-Modifies ss_pre_filter_set_xx_filter_obj_ ) "_" ) (strcat "*" "6413"  "*"))   T)
                    (= (wcmatch (LM:lst->str (LM:vl-getattributevalue-val-TA-Modifies ss_pre_filter_set_xx_filter_obj_ ) "_" ) (strcat "*" "6414"  "*"))   T)
                    (= (wcmatch (LM:lst->str (LM:vl-getattributevalue-val-TA-Modifies ss_pre_filter_set_xx_filter_obj_ ) "_" ) (strcat "*" "6416"  "*"))   T)

                    (= (wcmatch (LM:lst->str (LM:vl-getattributevalue-val-TA-Modifies ss_pre_filter_set_xx_filter_obj_ ) "_" ) (strcat "*" "6500"    "*"))   T)
                    (= (wcmatch (LM:lst->str (LM:vl-getattributevalue-val-TA-Modifies ss_pre_filter_set_xx_filter_obj_ ) "_" ) (strcat "*" "6507"    "*"))   T)
                    
                    (= (wcmatch (LM:lst->str (LM:vl-getattributevalue-val-TA-Modifies ss_pre_filter_set_xx_filter_obj_ ) "_" ) (strcat "*" "6505"    "*"))   T)
                    (= (wcmatch (LM:lst->str (LM:vl-getattributevalue-val-TA-Modifies ss_pre_filter_set_xx_filter_obj_ ) "_" ) (strcat "*" "6555"    "*"))   T)
                    (= (wcmatch (LM:lst->str (LM:vl-getattributevalue-val-TA-Modifies ss_pre_filter_set_xx_filter_obj_ ) "_" ) (strcat "*" "6569"    "*"))   T)
                    
                    (= (wcmatch (LM:lst->str (LM:vl-getattributevalue-val-TA-Modifies ss_pre_filter_set_xx_filter_obj_ ) "_" ) (strcat "*" "6600"    "*"))   T)
                  )
                  (progn
                    (vla-put-color ss_pre_filter_set_xx_filter_obj_ 241)
                    (setq ssbox (TA:ename+vla-getboundingbox  ss_pre_filter_set_xx_filter_obj_))
                    
                    (setq ss_pre_filter_set_xx_filter_min_ (list (- (car (cadr ssbox) ) 12) (- (cadr (cadr ssbox) ) 12) 0))
                    
                    (setq ss_pre_filter_set_xx_filter_max_ (list (+ (car (caddr ssbox) ) 12) (+ (cadr (caddr ssbox) ) 12) 0))
                    (setq ssbox (list "just input no reason" ss_pre_filter_set_xx_filter_min_ ss_pre_filter_set_xx_filter_max_))
                    (command "ATTSYNC" "S" ss_pre_filter_set_xx_filter_ename_ "Y" )           
                    (setq ssssset_ (ssget "C" (cadr ssbox)  (caddr ssbox)
                                                  (list 
                                                    (cons 0 "LEADER,LINE,LWPOLYLINE,POLYLINE") ;type of object
                                                    ; (cons 8 "000 - GRID")   ;kind of layer
                                                    ; (cons 2 "000-GRID_LINE_DYN")       ;kind of nameblock
                                                    ; (cons 62 1)           ;kind of color call sign with color code index
                                                  )
                                                )
                    )
                    ;preloop_and_while
                      (setq ssssset_i 0)
                      (while (and (/= ssssset_ nil )(< ssssset_i (sslength ssssset_)))
                        (setq ssssset_ename_ (ssname ssssset_ ssssset_i))
                        (setq ssssset_obj_ (vlax-ename->vla-object ssssset_ename_))
                          (if 
                            (= (vla-get-objectname ssssset_obj_) "AcDbLeader")
                            (progn 
                              (vla-put-color ssssset_obj_ 241)
                              (vla-put-dimensionlinecolor ssssset_obj_ 0)
                              
                            )
                          )
                          (if 
                            (or 
                              (= (vla-get-objectname ssssset_obj_) "AcDbPolyline")
                              (= (vla-get-objectname ssssset_obj_) "AcDbLine")
                            )
                            (progn 
                              (vla-put-color ssssset_obj_ 241)
                            )
                          )
                        (setq ssssset_i (+ ssssset_i 1))
                      )
                    ;
                    (princ "vla-get-color_case_17")
                  )
                )
              )
            )
          )
          (;text-mtext-case
            (or
              (= (vla-get-objectname ss_pre_filter_set_xx_filter_obj_) "AcDbText" )
              (= (vla-get-objectname ss_pre_filter_set_xx_filter_obj_) "AcDbMText" )
            )
            (progn
              (cond
                (;att-case
                  (or
                    ; (= (wcmatch (vla-get-textstring ss_pre_filter_set_xx_filter_obj_) (strcat "*" "DISABLED" "*") )   T)
                    ; (= (wcmatch (vla-get-textstring ss_pre_filter_set_xx_filter_obj_) (strcat "*" "ESC" "*") )   T)
                    (= (wcmatch (vla-get-textstring ss_pre_filter_set_xx_filter_obj_) (strcat "*" "6563" "*") )   T)
                    (= (wcmatch (vla-get-textstring ss_pre_filter_set_xx_filter_obj_) (strcat "*" "6565" "*") )   T)
                    (= (wcmatch (vla-get-textstring ss_pre_filter_set_xx_filter_obj_) (strcat "*" "6569" "*") )   T)
                  )
                  (progn
                    (vla-put-color ss_pre_filter_set_xx_filter_obj_ 241)
                    (setq ss_pre_filter_set_xx_filter_obj_getboundingbox (vla-getboundingbox ss_pre_filter_set_xx_filter_obj_ 'min_ 'max_)) 
                    (setq ss_pre_filter_set_xx_filter_min_ (vlax-safearray->list min_)) 
                    (setq ss_pre_filter_set_xx_filter_min_ (list (- (car ss_pre_filter_set_xx_filter_min_ ) 12) (- (cadr ss_pre_filter_set_xx_filter_min_ ) 12) 0))
                    (setq ss_pre_filter_set_xx_filter_max_ (vlax-safearray->list max_)) 
                    (setq ss_pre_filter_set_xx_filter_max_ (list (+ (car ss_pre_filter_set_xx_filter_max_ ) 12) (+ (cadr ss_pre_filter_set_xx_filter_max_ ) 12) 0))
                    (setq ssbox (list "just input no reason" ss_pre_filter_set_xx_filter_min_ ss_pre_filter_set_xx_filter_max_))
                    
                    (setq ssssset_ (ssget "C" (cadr ssbox)  (caddr ssbox)
                                                  (list 
                                                    (cons 0 "LEADER") ;type of object
                                                    ; (cons 8 "000 - GRID")   ;kind of layer
                                                    ; (cons 2 "000-GRID_LINE_DYN")       ;kind of nameblock
                                                    ; (cons 62 1)           ;kind of color call sign with color code index
                                                  )
                                                )
                    )
                    ;preloop_and_while
                      (setq ssssset_i 0)
                      (while (and (/= ssssset_ nil )(< ssssset_i (sslength ssssset_)))
                        (setq ssssset_ename_ (ssname ssssset_ ssssset_i))
                        (setq ssssset_obj_ (vlax-ename->vla-object ssssset_ename_))
                          (if 
                            (= (vla-get-objectname ssssset_obj_) "AcDbLeader")
                            (progn 
                              (vla-put-color ssssset_obj_ 241)
                              (vla-put-dimensionlinecolor ssssset_obj_ 0)
                              
                            )
                          )
                        (setq ssssset_i (+ ssssset_i 1))
                      )
                    ;
                    (princ "vla-get-color_case_17")
                  )
                )
              )
            )
          )
        )
          
        
        (setq ss_pre_filter_set_xx_filter_i (+ ss_pre_filter_set_xx_filter_i 1))
      )
    ;
  )
  (defun c:PPLINE-ITD_detect_room_num_Rsf ()
    ;selection_set_for_fillter_blk_name
      (if  ;pre_select_ssget_or_post_select_ssget
        (=
          (setq ss_pre_filter_set_xx_ (ssget "x"
                                            (list
                                              (cons 0 "mtext,text") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "mtext,text") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (setq ss_pre_filter_set_xx_text_val_ (vla-get-textstring ss_pre_filter_set_xx_obj_))
        (if 
          (or 
            (= (wcmatch ss_pre_filter_set_xx_text_val_ (strcat "*" "6563"    "*"))   T)
            (= (wcmatch ss_pre_filter_set_xx_text_val_ (strcat "*" "6562"    "*"))   T)
            (= (wcmatch ss_pre_filter_set_xx_text_val_ (strcat "*" "6569"    "*"))   T)
            (= (wcmatch ss_pre_filter_set_xx_text_val_ (strcat "*" "6665"    "*"))   T)
            (= (wcmatch ss_pre_filter_set_xx_text_val_ (strcat "*" "6555"    "*"))   T)
          )
          (progn
            (vla-put-color ss_pre_filter_set_xx_obj_ 241)
          )
        )
    
        (setq ss_pre_filter_set_xx_i (+ ss_pre_filter_set_xx_i 1))
      )
    ;
  )
  (defun c:PPLINE-ITD_REPLACE_WALL-SYM_REPWALL_ ()
      (if  ;pre_select_ssget_or_post_select_ssget
        (=
          (setq ss_pre_filter_set_xx_ (ssget "x"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ (LM:effectivename (vlax-ename->vla-object (car (entsel "specify Object"))))))
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if (= (vla-get-hasattributes ss_pre_filter_set_xx_obj_) :vlax-true)
            (progn
              (setq ss_pre_filter_set_xx_obj_ins_ (vlax-safearray->list (vlax-variant-value (vla-get-insertionpoint ss_pre_filter_set_xx_obj_))))
              (setq ss_pre_filter_set_xx_obj_rotation_ (vla-get-rotation ss_pre_filter_set_xx_obj_ ))
              (setq wallnum_ (LM:vl-getattributevalue ss_pre_filter_set_xx_obj_ "W10" ))
              (TA:vla-insertblock "A$C441E3E01" ss_pre_filter_set_xx_obj_ins_ 1 ss_pre_filter_set_xx_obj_rotation_ )
              ;new_blk_entlast object
                (setq blknew_ename_ (entlast))
                (setq blknew_obj_ (vlax-ename->vla-object blknew_ename_))
                (LM:vl-setattributevalue blknew_obj_  att_name  wallnum_)
              ;
              ;delete existing object
                (vla-delete  ss_pre_filter_set_xx_obj_ )
              ;
            )
            
            
          )
          (setq ss_pre_filter_set_xx_i (+ ss_pre_filter_set_xx_i 1))
        )
      ;
  )
  (defun c:PPLINE-ITD_REPLACE_WALL-SYM_REPC1ELL_ ()
      (if  ;pre_select_ssget_or_post_select_ssget
        (=
          (setq ss_pre_filter_set_xx_ (ssget "x"
                                            (list
                                              (cons 0 "ATTDEF") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "ATTDEF") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ; (setq ss_pre_filter_set_xx_ (TA:EF_Filter_ss_set_ ss_pre_filter_set_xx_ (LM:effectivename (vlax-ename->vla-object (car (entsel "specify Object"))))))
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if (= (wcmatch (setq wallnum_ (vla-get-tagstring ss_pre_filter_set_xx_obj_  )) "*C*") T)
            (progn
              ; (setq ss_pre_filter_set_xx_obj_ins_ (vlax-safearray->list (vlax-variant-value (vla-get-insertionpoint ss_pre_filter_set_xx_obj_))))
              (setq ss_pre_filter_set_xx_obj_ins_ (vlax-safearray->list (vlax-variant-value (vla-get-textalignmentpoint ss_pre_filter_set_xx_obj_))))
              
              (setq ss_pre_filter_set_xx_obj_rotation_ (vla-get-rotation ss_pre_filter_set_xx_obj_ ))
              (setq wallnum_ (vla-get-tagstring ss_pre_filter_set_xx_obj_  ))
              (TA:vla-insertblock "qerg" ss_pre_filter_set_xx_obj_ins_ 1 ss_pre_filter_set_xx_obj_rotation_ )
              ;new_blk_entlast object
                (setq blknew_ename_ (entlast))
                (setq blknew_obj_ (vlax-ename->vla-object blknew_ename_))
                (LM:vl-setattributevalue blknew_obj_ "C00"  wallnum_)
              ;
              ;delete existing object
                (vla-delete  ss_pre_filter_set_xx_obj_ )
              ;
            )
            
            
          )
          (setq ss_pre_filter_set_xx_i (+ ss_pre_filter_set_xx_i 1))
        )
      ;
  )
  (defun c:PPLINE-ITD_REPLACE_WALL-SYM_REPC2ELL_ ()
      (if  ;pre_select_ssget_or_post_select_ssget
        (=
          (setq ss_pre_filter_set_xx_ (ssget "x"
                                            (list
                                              (cons 0 "insert") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "insert") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ (LM:effectivename (vlax-ename->vla-object (car (entsel "specify Object"))))))
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if 
            ; (= (wcmatch (setq wallnum_ (vla-get-tagstring ss_pre_filter_set_xx_obj_  )) "*C0*") T)
            (= 1 1 )
            (progn
              (setq ss_pre_filter_set_xx_obj_ins_ (vlax-safearray->list (vlax-variant-value (vla-get-insertionpoint ss_pre_filter_set_xx_obj_))))
              
              (setq ss_pre_filter_set_xx_obj_rotation_ (vla-get-rotation ss_pre_filter_set_xx_obj_ ))
              (setq wallnum_ (LM:vl-getattributevalue ss_pre_filter_set_xx_obj_ "C03" ))
              (TA:vla-insertblock "qerg" ss_pre_filter_set_xx_obj_ins_ 1 ss_pre_filter_set_xx_obj_rotation_ )
              ;new_blk_entlast object
                (setq blknew_ename_ (entlast))
                (setq blknew_obj_ (vlax-ename->vla-object blknew_ename_))
                (LM:vl-setattributevalue blknew_obj_ "C00"  wallnum_)
              ;
              ;delete existing object
                (vla-delete  ss_pre_filter_set_xx_obj_ )
              ;
            )
            
            
          )
          (setq ss_pre_filter_set_xx_i (+ ss_pre_filter_set_xx_i 1))
        )
      ;
  )
  (defun C:selection_return_axis_Z0_SSreaz_ ()
    ;return Z 0
      ;selection_set_for_fillter_blk_name
        (if  ;pre_select_ssget_or_post_select_ssget
          (=
            (setq ss_pre_filter_set_xx_ (ssget "i"
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                                (cons 410 (getvar "CTAB"))
                                              )
                                        )
            )
            nil
          )
          (progn
            (setq ss_pre_filter_set_xx_ (ssget  
                                              (list
                                                ; (cons 0 "INSERT") ;type of object
                                                ; (cons 8 "000 - GRID")   ;kind of layer
                                                ; (cons 2 "000-GRID_LINE_DYN")       ;kind of nameblock
                                                ; (cons 62 1)           ;kind of color call sign with color code index
                                                (cons 410 (getvar "CTAB"))
                                              )
                                        )
            )
          )
          
        )
      ;
      ;preloop_and_while
        (textscr)
        ; (getstring "\nHit \nHit \nHit [ENTER] to continue...")
        (setq ss_pre_filter_set_xx_i 0)
        (while (and 
                  (/= ss_pre_filter_set_xx_ nil)
                  (< ss_pre_filter_set_xx_i (sslength ss_pre_filter_set_xx_))
                )
          (setq ss_pre_filter_set_xx_ename_ (ssname ss_pre_filter_set_xx_ ss_pre_filter_set_xx_i))
          (setq ss_pre_filter_set_xx_obj_ (vlax-ename->vla-object ss_pre_filter_set_xx_ename_))
          ;main_idea_
            (cond
              (;type_name_object_case_1
                (and
                    (= (wcmatch (vl-princ-to-string ss_pre_filter_set_xx_obj_) (strcat "*" "IAcadLine" "*")) T)
                    (= (wcmatch (vla-get-objectname ss_pre_filter_set_xx_obj_) "AcDbLine" ) T)
                )
                (progn
                  (setq ss_pre_filter_set_xx_obj_start_end_pt_ (list
                                                  (setq ss_pre_filter_set_xx_obj_startpt_ (vlax-safearray->list
                                                                              (vlax-variant-value ( vla-get-startpoint ss_pre_filter_set_xx_obj_ ))
                                                                            )
                                                  )
                                                  (setq ss_pre_filter_set_xx_obj_endpt_ (vlax-safearray->list
                                                                            (vlax-variant-value ( vla-get-endpoint ss_pre_filter_set_xx_obj_ ))
                                                                          )
                                                  )
                                                )
                  )
                  (vla-put-startpoint ss_pre_filter_set_xx_obj_ (vlax-3d-point (car ss_pre_filter_set_xx_obj_startpt_) (cadr ss_pre_filter_set_xx_obj_startpt_) 0))
                  (vla-put-endpoint ss_pre_filter_set_xx_obj_ (vlax-3d-point (car ss_pre_filter_set_xx_obj_endpt_) (cadr ss_pre_filter_set_xx_obj_endpt_) 0))
                  (princ "type_name_object_case_1")
                )
              )
              (;type_name_object_case_2
                (and
                    (= (wcmatch (vl-princ-to-string ss_pre_filter_set_xx_obj_) (strcat "*" "IAcadLWPolyline" "*")) T)
                    (= (wcmatch (vla-get-objectname ss_pre_filter_set_xx_obj_) "AcDbPolyline") T)
                )
                (progn
                  (vla-put-elevation ss_pre_filter_set_xx_obj_ 0)
                  (princ "type_name_object_case_2")
                )
              )
              (;type_name_object_case_3
                (and
                    (= (wcmatch (vl-princ-to-string ss_pre_filter_set_xx_obj_) (strcat "*" "IAcadBlockReference " "*")) T)
                    (= (wcmatch (vla-get-objectname ss_pre_filter_set_xx_obj_) "AcDbBlockReference") T)
                )
                (progn
                  (setq ss_pre_filter_set_xx_obj_ins_ (vlax-safearray->list (vlax-variant-value (vla-get-insertionpoint ss_pre_filter_set_xx_obj_))))
                  (vla-put-insertionpoint ss_pre_filter_set_xx_obj_ (vlax-3d-point (car ss_pre_filter_set_xx_obj_ins_) (cadr ss_pre_filter_set_xx_obj_ins_) 0) )
                  (princ "type_name_object_case_3")
                )
              )
              (;type_name_object_case_4
                (and
                    (= (wcmatch (vl-princ-to-string ss_pre_filter_set_xx_obj_) (strcat "*" "IAcadHatch" "*")) T)
                    (= (wcmatch (vla-get-objectname ss_pre_filter_set_xx_obj_) "AcDbHatch") T)
                )
                (progn
                  (vla-put-elevation ss_pre_filter_set_xx_obj_  0)
                  (princ "type_name_object_case_4")
                )
              )
              (;type_name_object_case_5
                (and
                    (setq ss_pre_filter_set_xx_obj_ (vlax-ename->vla-object ss_pre_filter_set_xx_ename_))
                    (= (wcmatch (vl-princ-to-string ss_pre_filter_set_xx_obj_) (strcat "*" "IAcadArc" "*")) T)
                    (= (wcmatch (vla-get-objectname ss_pre_filter_set_xx_obj_) "AcDbArc") T)
                )
                (progn
                  (setq ss_pre_filter_set_xx_obj_center_ (vlax-safearray->list (vlax-variant-value (vla-get-center ss_pre_filter_set_xx_obj_) ) ) )
                  (vla-put-center ss_pre_filter_set_xx_obj_ (vlax-3d-point (car ss_pre_filter_set_xx_obj_center_) (cadr ss_pre_filter_set_xx_obj_center_) 0 ) )
                  (princ "type_name_object_case_5")
                )
              )
            )
          ;
          (setq percent (fix (* (/ (float ss_pre_filter_set_xx_i) (sslength ss_pre_filter_set_xx_)) 100)))
          (if (= (substr (rtos (/ (float ss_pre_filter_set_xx_i) 2 ) 2 1) 3 1) "0")
            (progn
              (princ (strcat "tranfering " (rtos ss_pre_filter_set_xx_i 2 0) "/" (rtos (sslength ss_pre_filter_set_xx_) 2 0)  " (" (rtos percent 2 0) "%" ")" "\n"))
            )
            (princ (strcat "                                tranfering " (rtos ss_pre_filter_set_xx_i 2 0) "/" (rtos (sslength ss_pre_filter_set_xx_) 2 0)  " (" (rtos percent 2 0) "%" ")" "\n"))
          )
          (setq ss_pre_filter_set_xx_i (+ ss_pre_filter_set_xx_i 1))
        )
      ;
    ;
    ;add on FUNC. 
      (graphscr)
    ;
  )

  (defun c:Center_measure_ccmea_ () ;command base on c:PPLINE_300HK_insCHanging_
    ;selection_set_for_fillter_blk_name
      (if  ;pre_select_ssget_or_post_select_ssget
        (=
          (setq ss_pre_filter_set_xx_ (ssget "i"
                                            (list
                                              (cons 0 "ARC,LWPOLYLINE,LINE,arc") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "ARC,LWPOLYLINE,LINE,arc") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ;user_input_
        ; (setq distance_measure_ 1200) ;input by code
        (setq fargment_gap_length_ 10) ;input by user
        (setq distance_measure_ (cond ( (getreal (strcat "\nspecify distance_measure_ <" (rtos (setq distance_measure_ (cond (distance_measure_) (10) ) ) ) "> : " ) ) ) (distance_measure_) ) ) ;input by user
        ; (setq EFname_string_ ;Get-string by keep previous value
        ;     (if
        ;       (or
        ;         (/= (setq EFname_string_val (getstring (strcat "\nSpecify Pattern name <" (if EFname_string_ EFname_string_ "") ">: ") ) ) "" )
        ;       )
        ;         (progn
        ;           (setq EFname_string_ EFname_string_val)
        ;           (setq EFname_string_keep_val_ EFname_string_val)
        ;         )
        ;       (setq EFname_string_val EFname_string_keep_val_)
        ;     )
        ; )
        (setq blk_ename_ (car (entsel "specify REF blk Object")))
        (setq blk_obj_ (vlax-ename->vla-object blk_ename_))
        (setq EFname_string_ (LM:effectivename blk_obj_))
        
      ;
      ;preloop_and_while
        (setq ss_pre_filter_set_xx_i 0)
        (while (< ss_pre_filter_set_xx_i (sslength ss_pre_filter_set_xx_))
          ;main Line PLine Properties
            (setq ss_pre_filter_set_xx_ename_ (ssname ss_pre_filter_set_xx_ ss_pre_filter_set_xx_i))
            (setq ss_pre_filter_set_xx_obj_ (vlax-ename->vla-object ss_pre_filter_set_xx_ename_))
            (cond 
              ; ( ;object type condition_case_1 ปิดชั่วคราว อรอพัฒนา
              ;  (and 
              ;    (= (vla-get-objectname ss_pre_filter_set_xx_obj_) "AcDbArc")
              ;  )
              ;  (progn 
              ;    (setq ss_pre_filter_set_xx_obj_length (vla-get-arclength ss_pre_filter_set_xx_obj_))
              ;    (princ "object type condition_case_1")
              ;  )
              ; )
              ( ;object type condition_case_2
              (and
                (= (vla-get-objectname ss_pre_filter_set_xx_obj_) "AcDbLine")
              )
              (progn 
                (setq ss_pre_filter_set_xx_obj_angle (vla-get-angle ss_pre_filter_set_xx_obj_))
                (setq ss_pre_filter_set_xx_obj_length (vla-get-length ss_pre_filter_set_xx_obj_))
                (princ "object type condition_case_2")
              )
              )
              ( ;object type condition_case_3
              (and
                (= (vla-get-objectname ss_pre_filter_set_xx_obj_) "AcDbPolyline")
                (<= (length (cadr (TA:Get_Pline_vertext_ins_point_ ss_pre_filter_set_xx_ename_))) 2)
              )
              (progn 
                (setq ss_pre_filter_set_xx_obj_length (vla-get-length ss_pre_filter_set_xx_obj_))
                (setq ss_pre_filter_set_xx_obj_angle (angle (car (cadr (TA:Get_Pline_vertext_ins_point_ ss_pre_filter_set_xx_ename_))) (cadr (cadr (TA:Get_Pline_vertext_ins_point_ ss_pre_filter_set_xx_ename_)))))
                (princ "object type condition_case_3")
              )
              )
              ( ;object type condition_case_4
              (and
                (= (vla-get-objectname ss_pre_filter_set_xx_obj_) "AcDbArc")
                (<= (length (cadr (TA:Get_Pline_vertext_ins_point_ ss_pre_filter_set_xx_ename_))) 2)
              )
              (progn 
                (setq ss_pre_filter_set_xx_obj_length (vla-get-arclength ss_pre_filter_set_xx_obj_))
                (princ "object type condition_case_4")
              )
              )
            )
            
            (setq distance_measure_ (if (< ss_pre_filter_set_xx_obj_length distance_measure_pre) (progn (fix (- ss_pre_filter_set_xx_obj_length fargment_gap_length_ ))) distance_measure_pre)) 
            (setq ss_pre_filter_set_xx_obj_fragment_length_ (/ (- ss_pre_filter_set_xx_obj_length (* (fix (/ ss_pre_filter_set_xx_obj_length distance_measure_)) distance_measure_) ) 2))
            (setq ss_pre_filter_set_xx_obj_time_full_length_ (fix (/ ss_pre_filter_set_xx_obj_length distance_measure_)))
            (if (= ss_pre_filter_set_xx_obj_fragment_length_ 0) ;incase for number spcaing distance
              (progn
                (setq ss_pre_filter_set_xx_obj_time_full_length_ (+ 3 ss_pre_filter_set_xx_obj_time_full_length_) )
              )
              (setq ss_pre_filter_set_xx_obj_time_full_length_ (+ 2 ss_pre_filter_set_xx_obj_time_full_length_) )
            )
            ;preloop_and_while measure_spcaing_distance
              (setq measure_length_ ())
              (setq time_i 0)
              (while (< time_i ss_pre_filter_set_xx_obj_time_full_length_)
                (if 
                  (or (= time_i 0) (= time_i (- ss_pre_filter_set_xx_obj_time_full_length_ 1)) )
                  (progn
                    (setq measure_length_ (cons ss_pre_filter_set_xx_obj_fragment_length_ measure_length_))
                  )
                  (setq measure_length_ (cons distance_measure_ measure_length_))
                )
                (setq time_i (+ time_i 1))
              )       
            ;
            ;preloop_and_while measure_val_distance
              (setq measure_length_i 0)
              (setq finish_measure_length_ 0)
              (setq finish_measure_length_result ())
              (while (< measure_length_i (length measure_length_))
                (setq measure_length_ename_ (nth  measure_length_i measure_length_))
                (setq finish_measure_length_ (+ finish_measure_length_ measure_length_ename_)) 
                (setq finish_measure_length_result (cons finish_measure_length_ finish_measure_length_result))
                (setq measure_length_i (+ measure_length_i 1))
              )
            ;
          ;
          ;insertion_process
            (if (> distance_measure_ 0)
              (progn
                (foreach x (vl-remove (nth (- (length finish_measure_length_result) 1) (reverse finish_measure_length_result) ) (reverse finish_measure_length_result) )
                  (TA:vla-insertblock 
                    EFname_string_
                    (vlax-curve-getpointatdist ss_pre_filter_set_xx_obj_ x)
                    1
                    ss_pre_filter_set_xx_obj_angle
                  )
                  ;new_blk_entlast object
                    (setq newblk_ename (entlast))
                    (setq newblk_obj (vlax-ename->vla-object newblk_ename))
                    ; (LM:setdynpropvalue newblk_obj (LM:getvisibilityparametername new_hanging_obj_) "2_top_view" )
                  ;
                )
              )
            )
          ;
          (setq ss_pre_filter_set_xx_i (+ ss_pre_filter_set_xx_i 1))
        )
      ;
    ;
  )
  (defun c:Center_measure_ccm2_ () ;command base on c:PPLINE_300HK_insCHanging_
    ;selection_set_for_fillter_blk_name
      (if  ;pre_select_ssget_or_post_select_ssget
        (=
          (setq ss_pre_filter_set_xx_ (ssget "i"
                                            (list
                                              (cons 0 "ARC,LWPOLYLINE,LINE,arc") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "ARC,LWPOLYLINE,LINE,arc") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ;user_input_
        ; (setq distance_measure_ 1200) ;input by code
        (setq fargment_gap_length_ 1 ) ;input by user
        (setq distance_measure_ (cond ( (getreal (strcat "\nspecify distance_measure_ <" (rtos (setq distance_measure_ (cond (distance_measure_) (10) ) ) ) "> : " ) ) ) (distance_measure_) ) ) ;input by user
        (setq EFname_string_ "xx1")
      ;
      ;preloop_and_while
        (setq ss_pre_filter_set_xx_i 0)
        (while (< ss_pre_filter_set_xx_i (sslength ss_pre_filter_set_xx_))
          ;main Line PLine Properties
            (setq ss_pre_filter_set_xx_ename_ (ssname ss_pre_filter_set_xx_ ss_pre_filter_set_xx_i))
            (setq ss_pre_filter_set_xx_obj_ (vlax-ename->vla-object ss_pre_filter_set_xx_ename_))
            (cond 
              ; ( ;object type condition_case_1 ปิดชั่วคราว อรอพัฒนา
              ;  (and 
              ;    (= (vla-get-objectname ss_pre_filter_set_xx_obj_) "AcDbArc")
              ;  )
              ;  (progn 
              ;    (setq ss_pre_filter_set_xx_obj_length (vla-get-arclength ss_pre_filter_set_xx_obj_))
              ;    (princ "object type condition_case_1")
              ;  )
              ; )
              ( ;object type condition_case_2
              (and
                (= (vla-get-objectname ss_pre_filter_set_xx_obj_) "AcDbLine")
              )
              (progn 
                (setq ss_pre_filter_set_xx_obj_angle (vla-get-angle ss_pre_filter_set_xx_obj_))
                (setq ss_pre_filter_set_xx_obj_length (vla-get-length ss_pre_filter_set_xx_obj_))
                (princ "object type condition_case_2")
              )
              )
              ( ;object type condition_case_3
              (and
                (= (vla-get-objectname ss_pre_filter_set_xx_obj_) "AcDbPolyline")
                (<= (length (cadr (TA:Get_Pline_vertext_ins_point_ ss_pre_filter_set_xx_ename_))) 2)
              )
              (progn 
                (setq ss_pre_filter_set_xx_obj_length (vla-get-length ss_pre_filter_set_xx_obj_))
                (setq ss_pre_filter_set_xx_obj_angle (angle (car (cadr (TA:Get_Pline_vertext_ins_point_ ss_pre_filter_set_xx_ename_))) (cadr (cadr (TA:Get_Pline_vertext_ins_point_ ss_pre_filter_set_xx_ename_)))))
                (princ "object type condition_case_3")
              )
              )
              ( ;object type condition_case_4
              (and
                (= (vla-get-objectname ss_pre_filter_set_xx_obj_) "AcDbArc")
                (<= (length (cadr (TA:Get_Pline_vertext_ins_point_ ss_pre_filter_set_xx_ename_))) 2)
              )
              (progn 
                (setq ss_pre_filter_set_xx_obj_length (vla-get-arclength ss_pre_filter_set_xx_obj_))
                (princ "object type condition_case_4")
              )
              )
            )
            
            (setq distance_measure_ (if (< ss_pre_filter_set_xx_obj_length distance_measure_) (progn (fix (- ss_pre_filter_set_xx_obj_length fargment_gap_length_ ))) distance_measure_)) 
            (setq ss_pre_filter_set_xx_obj_fragment_length_ (/ (- ss_pre_filter_set_xx_obj_length (* (fix (/ ss_pre_filter_set_xx_obj_length distance_measure_)) distance_measure_) ) 2))
            (setq ss_pre_filter_set_xx_obj_time_full_length_ (fix (/ ss_pre_filter_set_xx_obj_length distance_measure_)))
            (if (= ss_pre_filter_set_xx_obj_fragment_length_ 0) ;incase for number spcaing distance
              (progn
                (setq ss_pre_filter_set_xx_obj_time_full_length_ (+ 3 ss_pre_filter_set_xx_obj_time_full_length_) )
              )
              (setq ss_pre_filter_set_xx_obj_time_full_length_ (+ 2 ss_pre_filter_set_xx_obj_time_full_length_) )
            )
            ;preloop_and_while measure_spcaing_distance
              (setq measure_length_ ())
              (setq time_i 0)
              (while (< time_i ss_pre_filter_set_xx_obj_time_full_length_)
                (if 
                  (or (= time_i 0) (= time_i (- ss_pre_filter_set_xx_obj_time_full_length_ 1)) )
                  (progn
                    (setq measure_length_ (cons ss_pre_filter_set_xx_obj_fragment_length_ measure_length_))
                  )
                  (setq measure_length_ (cons distance_measure_ measure_length_))
                )
                (setq time_i (+ time_i 1))
              )       
            ;
            ;preloop_and_while measure_val_distance
              (setq measure_length_i 0)
              (setq finish_measure_length_ 0)
              (setq finish_measure_length_result ())
              (while (< measure_length_i (length measure_length_))
                (setq measure_length_ename_ (nth  measure_length_i measure_length_))
                (setq finish_measure_length_ (+ finish_measure_length_ measure_length_ename_)) 
                (setq finish_measure_length_result (cons finish_measure_length_ finish_measure_length_result))
                (setq measure_length_i (+ measure_length_i 1))
              )
            ;
          ;
          ;insertion_process
            (if (> distance_measure_ 0)
              (progn
                (foreach x (vl-remove (nth (- (length finish_measure_length_result) 1) (reverse finish_measure_length_result) ) (reverse finish_measure_length_result) )
                  (TA:vla-insertblock 
                    EFname_string_
                    (vlax-curve-getpointatdist ss_pre_filter_set_xx_obj_ x)
                    1
                    ss_pre_filter_set_xx_obj_angle
                  )
                  ;new_blk_entlast object
                    (setq newblk_ename (entlast))
                    (setq newblk_obj (vlax-ename->vla-object newblk_ename))
                    ; (LM:setdynpropvalue newblk_obj (LM:getvisibilityparametername new_hanging_obj_) "2_top_view" )
                  ;
                )
              )
            )
          ;
          (setq ss_pre_filter_set_xx_i (+ ss_pre_filter_set_xx_i 1))
        )
      ;
    ;
  )

  (defun c:w12 () 
    ;selection_set_for_fillter_blk_name
      (if  ;pre_select_ssget_or_post_select_ssget
        (=
          (setq ss_pre_filter_set_xx_ (ssget "i"
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (vla-put-color ss_pre_filter_set_xx_obj_ 240)
          (vlax-dump-object ss_pre_filter_set_xx_obj_)
        (vla-put-ConstantWidth ss_pre_filter_set_xx_obj_ 150)
        (setq ss_pre_filter_set_xx_i (+ ss_pre_filter_set_xx_i 1))
      )
    ;
    
    
  )
  (defun c:w8 () 
    ;selection_set_for_fillter_blk_name
      (if  ;pre_select_ssget_or_post_select_ssget
        (=
          (setq ss_pre_filter_set_xx_ (ssget "i"
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (vla-put-color ss_pre_filter_set_xx_obj_ 20)
          (vlax-dump-object ss_pre_filter_set_xx_obj_)
        (vla-put-ConstantWidth ss_pre_filter_set_xx_obj_ 150)
        (setq ss_pre_filter_set_xx_i (+ ss_pre_filter_set_xx_i 1))
      )
    ;
    
    
  )
;



(defun c:connect_line_CONL ()
  (setq T1_ename_ (car (entsel "specify Object")))
  (setq T1_obj_ (vlax-ename->vla-object T1_ename_))
  (setq T2_ename_ (car (entsel "specify Object")))
  (setq T2_obj_ (vlax-ename->vla-object T2_ename_))
  (setq T1_obj_start_end_pt_ (list
                                  (setq T1_obj_startpt_ (vlax-safearray->list
                                                             (vlax-variant-value ( vla-get-startpoint T1_obj_ ))
                                                           )
                                  )
                                  (setq T1_obj_endpt_ (vlax-safearray->list
                                                            (vlax-variant-value ( vla-get-endpoint T1_obj_ ))
                                                         )
                                  )
                                )
  )
  (setq T2_obj_start_end_pt_ (list
                                  (setq T2_obj_startpt_ (vlax-safearray->list
                                                             (vlax-variant-value ( vla-get-startpoint T2_obj_ ))
                                                           )
                                  )
                                  (setq T2_obj_endpt_ (vlax-safearray->list
                                                            (vlax-variant-value ( vla-get-endpoint T2_obj_ ))
                                                         )
                                  )
                                )
  )
  (command "pline" T1_obj_startpt_ T2_obj_startpt_ "" )
  ;new_blk_entlast object
    (setq L1_ename (entlast))
    (setq L1_obj (vlax-ename->vla-object L1_ename))
  ;
  (command "pline" T1_obj_endpt_ T2_obj_endpt_  "")
  ;new_blk_entlast object
    (setq L2_ename (entlast))
    (setq L2_obj (vlax-ename->vla-object L2_ename))
  ;
  (setq newSS_ (ssadd))
  (sslength newSS_)
  (setq newSS_ (ssadd T1_ename_   newSS_) )
  (setq newSS_ (ssadd T2_ename_   newSS_) )
  (setq newSS_ (ssadd L1_ename   newSS_) )
  (setq newSS_ (ssadd L2_ename   newSS_) )
  (command "pedit"  "m" newSS_ "" "Y" "J" "" ""  )
  
  
)

(defun c:Arc_to_Pline_A2P ()
  (setq arc_ename_ (car (entsel "specify Object")))
  (setq arc_obj_ (vlax-ename->vla-object arc_ename_))
  (command "pedit"  "m" arc_ename_ ""  "Y" "" )
  ;new_blk_entlast object
    (setq pline_ename (entlast))
    (setq pline_obj (vlax-ename->vla-object pline_ename))
    (vla-put-ConstantWidth pline_obj 3)
  ;
  
)

(defun c:match_elevation_MEL_ ()
  ;selection_set_for_fillter_blk_name
    (if  ;pre_select_ssget_or_post_select_ssget
      (=
        (setq ss_pre_filter_set_xx_ (ssget "i"
                                          (list
                                            (cons 0 "lwpolyline,polyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "lwpolyline,polyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq sum_length_ 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (setq sum_length_ (+ (vla-get-length ss_pre_filter_set_xx_obj_) sum_length_ ))
      
      (setq ss_pre_filter_set_xx_i (+ ss_pre_filter_set_xx_i 1))
    )
  ;
  (setq target_ename_ (car (entsel "specify Object")))
  (setq target_obj_ (vlax-ename->vla-object target_ename_))
  (if (or 
        (= (vla-get-objectname target_obj_ ) "AcDbPolyline")
        (= (vla-get-objectname target_obj_ ) "AcDbLine")
      )
    (progn
      (vla-put-elevation target_obj_ (fix sum_length_))
    )
  )
  
  
  
)

(defun c:blk_angle_to_point_ang2pt ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;user_input
    (setq target_point_ (getpoint "specify point"))
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (setq ss_pre_filter_set_xx_obj_ins_ (vlax-safearray->list (vlax-variant-value (vla-get-insertionpoint ss_pre_filter_set_xx_obj_))))
      
      ;calculate process
        
      ;
      
      (vla-put-rotation ss_pre_filter_set_xx_obj_ (angle target_point_ ss_pre_filter_set_xx_obj_ins_))
      
      
      
      (setq ss_pre_filter_set_xx_i (+ ss_pre_filter_set_xx_i 1))
    )
  ;
)
(defun c:CSDRUN ()
  ;csd FUNC
      (command "ucsicon" "or")
      ;tempolary_code for working w/ CKST CSD PLAN
      (setq cons8 "A-ANNO-MATC,G-ANNO-SYMB,A-_ANOTTRGT_--,A-_ANOTSYBL_P-")
      ;ch line
        ;selection_set_for_fillter_blk_name
          (if  ;pre_select_ssget_or_post_select_ssget
            (=
              (setq ss_pre_filter_set_xx_ (ssget "x"
                                                (list
                                                  (cons 0 "line") ;type of object
                                                  (cons 8 cons8)   ;kind of layer
                                                  ; (cons 2 "000-GRID_LINE_DYN")       ;kind of nameblock
                                                  ; (cons 62 1)           ;kind of color call sign with color code index
                                                )
                                          )
              )
              nil
            )
            (progn
              (setq ss_pre_filter_set_xx_ 
                                            (ssget
                                                (list
                                                  (cons 0 "line") ;type of object
                                                  (cons 8 cons8)   ;kind of layer
                                                  ; (cons 2 "000-GRID_LINE_DYN")       ;kind of nameblock
                                                  ; (cons 62 1)           ;kind of color call sign with color code index
                                                )
                                          )
              )
            )
            
          )
        ;
        ;preloop_and_while
          (if (/= ss_pre_filter_set_xx_ nil) 
            (progn 
              (setq ss_pre_filter_set_xx_i 0)
              (while (< ss_pre_filter_set_xx_i (sslength ss_pre_filter_set_xx_)) 
                (setq ss_pre_filter_set_xx_ename_ (ssname ss_pre_filter_set_xx_ ss_pre_filter_set_xx_i ) )
                (setq ss_pre_filter_set_xx_obj_ (vlax-ename->vla-object ss_pre_filter_set_xx_ename_))

                (vla-put-color ss_pre_filter_set_xx_obj_ 2)


                (setq ss_pre_filter_set_xx_i (+ ss_pre_filter_set_xx_i 1))
              )
              ;
            )
          )
        ;
      ;
      ;ch mtext
        ;selection_set_for_fillter_blk_name
          (if  ;pre_select_ssget_or_post_select_ssget
            (=
              (setq ss_pre_filter_set_xx_ (ssget "x"
                                                (list
                                                  (cons 0 "mtext") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "mtext") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object ss_pre_filter_set_xx_ename_))
            (vla-put-backgroundfill ss_pre_filter_set_xx_obj_ 0)
            (vla-put-color ss_pre_filter_set_xx_obj_ 8)
            (setq ss_pre_filter_set_xx_i (+ ss_pre_filter_set_xx_i 1))
          )
        ;
      ;
      ;ch background block
        ;selection_set_for_fillter_blk_name
          (if  ;pre_select_ssget_or_post_select_ssget
            (=
              (setq ss_pre_filter_set_xx_ (ssget "x"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        ;
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object ss_pre_filter_set_xx_ename_))

              (if (= (wcmatch (LM:effectivename ss_pre_filter_set_xx_obj_ ) "*View Reference - M_View Reference*") T)
                (progn
                  (setq blk_obj_ (vlax-ename->vla-object (entnext  ss_pre_filter_set_xx_ename_ )))
                    (if (= (vla-get-objectname ss_pre_filter_set_xx_obj_) "AcDbBlockReference")
                      (progn
                        (setq blkname (cdr (assoc 2 (entget ss_pre_filter_set_xx_ename_))))
                        (setq bdef (tblobjname "BLOCK" blkname))
                        (if (= (vl-prin1-to-string (type bdef)) "ENAME")
                          (progn
                            (setq nested (entnext bdef))
                            (vla-put-color (vlax-ename->vla-object nested) 8)
                            (vla-put-backgroundfill (vlax-ename->vla-object nested) 0)
                            
                          )
                        )
                      )
                    )
                )
              )

            (setq ss_pre_filter_set_xx_i (+ ss_pre_filter_set_xx_i 1))
          )
        ;
      ;
      (c:go-to-model_2model)



      ;selection for mk blk
        ;selection_set_for_fillter_blk_name
          (if  ;pre_select_ssget_or_post_select_ssget
            (=
              (setq ss_pre_filter_set_xx_ (ssget "x"
                                                (list
                                                  ; (cons 0 "INSERT") ;type of object
                                                  ; (cons 8 "000 - GRID")   ;kind of layer
                                                  ; (cons 2 "000-GRID_LINE_DYN")       ;kind of nameblock
                                                  ; (cons 62 1)           ;kind of color call sign with color code index
                                                  (cons 410 "model")
                                                )
                                          )
              )
              nil
            )
            (progn
              (setq ss_pre_filter_set_xx_ (ssget
                                                (list
                                                  ; (cons 0 "INSERT") ;type of object
                                                  ; (cons 8 "000 - GRID")   ;kind of layer
                                                  ; (cons 2 "000-GRID_LINE_DYN")       ;kind of nameblock
                                                  ; (cons 62 1)           ;kind of color call sign with color code index
                                                  (cons 410 "model")
                                                )
                                          )
              )
            )
            (sslength ss_pre_filter_set_xx_)
          )
        ;
        (defun LM:ssboundingbox ( sel / idx llp ls1 ls2 obj urp )
              (repeat (setq idx (sslength sel))
                  (setq obj (vlax-ename->vla-object (ssname sel (setq idx (1- idx)))))
                  (if (and (vlax-method-applicable-p obj 'getboundingbox)
                          (not (vl-catch-all-error-p (vl-catch-all-apply 'vla-getboundingbox (list obj 'llp 'urp))))
                      )
                      (setq ls1 (cons (vlax-safearray->list llp) ls1)
                            ls2 (cons (vlax-safearray->list urp) ls2)
                      )
                  )
              )
              (if (and ls1 ls2)
                  (mapcar '(lambda ( a b ) (apply 'mapcar (cons a b))) '(min max) (list ls1 ls2))
              )
          )
        (setq sss (LM:ssboundingbox ss_pre_filter_set_xx_))
        (c:PPLINE_CKST_CSDfilter_)

        (command "pselect"  (setq g1 (ssget "C" (car sss) (cadr sss))) "" )
        (c:PPLINE_CKST_CSDvilter_)
        (defun c:gf1 ()
          (command "pselect"  g1 "" )
        )
        (c:PPLINE_CKST_XCV1RENBLK)
      ;
  ;
) 



;cuting_plan_FUNC_
  (defun c:make_cuting_plan_x_axis_mkhand_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    
    ;preloop_and_while
      (setq ss_pre_filter_set_xx_i 0)
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object ss_pre_filter_set_xx_ename_))
          (if 
            (or
              (= (LM:effectivename ss_pre_filter_set_xx_obj_ ) "001 - DYNAMIC REC&SSQ SHAPE SOLID_startpoint")
              (= (wcmatch (strcase (LM:effectivename ss_pre_filter_set_xx_obj_ )) (strcase (strcat "*" "SP_PANEL_" "*"))))
            )
            (progn
              (LM:vl-setattributevalue ss_pre_filter_set_xx_obj_ "ON_PANEL_SIZE_NO." (vla-get-handle ss_pre_filter_set_xx_obj_ ))
            )
          )
          

          (setq ss_pre_filter_set_xx_i (+ ss_pre_filter_set_xx_i 1))
        )
    ;
  )

  (defun c:make_cuting_plan_x_axis_mkxCPL ()
    ;selection_set_for_fillter_blk_name
      (if  ;pre_select_ssget_or_post_select_ssget
        (=
          (setq ssPA_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ssPA_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ssPA_pre_filter_set_xx_)
      )
    ;
    (setq ssPA_pre_filter_set_xx_ (TA:EF_Filter_ss_set_ ssPA_pre_filter_set_xx_ "001 - DYNAMIC REC&SSQ SHAPE SOLID_startpoint"))
    ;preloop_and_while
      (setq ssPA_pre_filter_set_xx_i 0)
      (setq panel_list_ ())
      (while (< ssPA_pre_filter_set_xx_i (sslength ssPA_pre_filter_set_xx_))
        (setq ssPA_pre_filter_set_xx_ename_ (ssname ssPA_pre_filter_set_xx_ ssPA_pre_filter_set_xx_i))
        (setq ssPA_pre_filter_set_xx_obj_ (vlax-ename->vla-object ssPA_pre_filter_set_xx_ename_))
        (setq panel_list_
          (cons 
            (list 
              ssPA_pre_filter_set_xx_ename_
              ssPA_pre_filter_set_xx_obj_
              (LM:getdynpropvalue ssPA_pre_filter_set_xx_obj_ "W")
            )
            panel_list_
          )
        )
        (setq ssPA_pre_filter_set_xx_i (+ ssPA_pre_filter_set_xx_i 1))
      )
    ;
    ;
    ;TA:stanndard_lambda_sorting
      (setq panel_list_sorted_ (vl-sort panel_list_  ;bigest open indent list
                                                (function 
                                                  (lambda (a b) 
                                                    (> (caddr a) (caddr b))
                                                  )
                                                )
                            ) ;bigest close indent list
      )
    ;
    ;preloop_and_while
      (setq panel_list_sorted_i 0)
      (setq x_move 0)
      (while (< panel_list_sorted_i (length panel_list_sorted_))
        (setq panel_list_sorted_ename_ (car (nth  panel_list_sorted_i panel_list_sorted_)))
        (setq panel_list_sorted_obj_ (vlax-ename->vla-object panel_list_sorted_ename_))
        (if (/= panel_list_sorted_i 0)
          (progn
              (vla-move 
                panel_list_sorted_obj_ 
                (vlax-3d-point (setq panel_list_sorted_obj_ins_ (vlax-safearray->list (vlax-variant-value (vla-get-insertionpoint panel_list_sorted_obj_)))))
                (vlax-3d-point 
                  (+ (car panel_list_sorted_obj_ins_) x_move)
                  (cadr panel_list_sorted_obj_ins_)
                  (caddr panel_list_sorted_obj_ins_)
                )
              )
              (setq x_move (+ (+ (+ (caddr (nth panel_list_sorted_i panel_list_sorted_)) x_move) 0.04) 0.005))
          )
          (setq x_move (+(+ (+ (caddr (nth panel_list_sorted_i panel_list_sorted_)) x_move ) 0.04 ) 0.005 ) )
        )
        (setq panel_list_sorted_i (+ panel_list_sorted_i 1))
      )
    ;
  )
  (defun c:make_cuting_plan_y_axis_mkyCPL ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "001 - DYNAMIC REC&SSQ SHAPE SOLID_startpoint"))
    ;preloop_and_while
      (setq ss_pre_filter_set_xx_i 0)
      (setq panel_list_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (setq panel_list_
          (cons 
            (list 
              ss_pre_filter_set_xx_ename_
              ss_pre_filter_set_xx_obj_
              (LM:getdynpropvalue ss_pre_filter_set_xx_obj_ "H")
            )
            panel_list_
          )
        )
        (setq ss_pre_filter_set_xx_i (+ ss_pre_filter_set_xx_i 1))
      )
    ;

    ;TA:stanndard_lambda_sorting
      (setq panel_list_sorted_ (vl-sort panel_list_  ;bigest open indent list
                                                (function 
                                                  (lambda (a b) 
                                                    (> (caddr a) (caddr b))
                                                  )
                                                )
                            ) ;bigest close indent list
      )
    ;
    ;preloop_and_while
      (setq panel_list_sorted_i 0)
      (setq x_move 0)
      (while (< panel_list_sorted_i (length panel_list_sorted_))
        (setq panel_list_sorted_ename_ (car (nth  panel_list_sorted_i panel_list_sorted_)))
        (setq panel_list_sorted_obj_ (vlax-ename->vla-object panel_list_sorted_ename_))
        (if (/= panel_list_sorted_i 0)
          (progn
              (vla-move 
                panel_list_sorted_obj_ 
                (vlax-3d-point (setq panel_list_sorted_obj_ins_ (vlax-safearray->list (vlax-variant-value (vla-get-insertionpoint panel_list_sorted_obj_)))))
                (vlax-3d-point 
                  (car panel_list_sorted_obj_ins_)
                  (+ (cadr panel_list_sorted_obj_ins_) x_move)
                  (caddr panel_list_sorted_obj_ins_)
                )
              )
              (setq x_move (+ (+ (+ (caddr (nth (- panel_list_sorted_i 1) panel_list_sorted_)) x_move) 0.04) 0.005))
          )
          (setq x_move (+(+ (+ (caddr (nth panel_list_sorted_i panel_list_sorted_)) x_move ) 0.04 ) 0.005 ) )
        )
        (setq panel_list_sorted_i (+ panel_list_sorted_i 1))
      )
    ;
  )


  (defun TA:make_cuting_plan_XY_axis_mkyCPL (ss_pre_filter_set_xx_ mode_xy)
    ; ;selection_set_for_fillter_blk_name
    ;   (if  ;pre_select_ssget_or_post_select_ssget
    ;     (=
    ;       (setq ss_pre_filter_set_xx_ (ssget "i"
    ;                                         (list
    ;                                           (cons 0 "INSERT") ;type of object
    ;                                           ; (cons 8 "000 - GRID")   ;kind of layer
    ;                                           ; (cons 2 "000-GRID_LINE_DYN")       ;kind of nameblock
    ;                                           ; (cons 62 1)           ;kind of color call sign with color code index
    ;                                         )
    ;                                   )
    ;       )
    ;       nil
    ;     )
    ;     (progn
    ;       (setq ss_pre_filter_set_xx_ (ssget
    ;                                         (list
    ;                                           (cons 0 "INSERT") ;type of object
    ;                                           ; (cons 8 "000 - GRID")   ;kind of layer
    ;                                           ; (cons 2 "000-GRID_LINE_DYN")       ;kind of nameblock
    ;                                           ; (cons 62 1)           ;kind of color call sign with color code index
    ;                                         )
    ;                                   )
    ;       )
    ;     )
    ;     (sslength ss_pre_filter_set_xx_)
    ;   )
    ; ;
    (setq ss_pre_filter_set_xx_ (TA:EF_Filter_ss_set_ ss_pre_filter_set_xx_ "001 - DYNAMIC REC&SSQ SHAPE SOLID_startpoint"))
    ;preloop_and_while
      (setq ss_pre_filter_set_xx_i 0)
      (setq panel_list_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object ss_pre_filter_set_xx_ename_))
        (setq panel_list_
          (cons 
            (list 
              ss_pre_filter_set_xx_ename_
              ss_pre_filter_set_xx_obj_
              (LM:getdynpropvalue ss_pre_filter_set_xx_obj_ 
                (if (= mode_xy "x")
                  (progn
                    "W"
                  )
                  "H"
                )
              )
            )
            panel_list_
          )
        )
        (setq ss_pre_filter_set_xx_i (+ ss_pre_filter_set_xx_i 1))
      )
    ;

    ;TA:stanndard_lambda_sorting
      (setq panel_list_sorted_ (vl-sort panel_list_  ;bigest open indent list
                                                (function 
                                                  (lambda (a b) 
                                                    (> (caddr a) (caddr b))
                                                  )
                                                )
                            ) ;bigest close indent list
      )
    ;
    ;preloop_and_while
      (setq panel_list_sorted_i 0)
      (setq x_move 0)
      (while (< panel_list_sorted_i (length panel_list_sorted_))
        (setq panel_list_sorted_ename_ (car (nth  panel_list_sorted_i panel_list_sorted_)))
        (setq panel_list_sorted_obj_ (vlax-ename->vla-object panel_list_sorted_ename_))
        (if (/= panel_list_sorted_i 0)
          (progn
              (vla-move 
                panel_list_sorted_obj_ 
                (vlax-3d-point (setq panel_list_sorted_obj_ins_ (vlax-safearray->list (vlax-variant-value (vla-get-insertionpoint panel_list_sorted_obj_)))))
                (if (= mode_xy "x")
                  (progn
                    (vlax-3d-point 
                      (+ (car panel_list_sorted_obj_ins_) x_move)
                      (cadr panel_list_sorted_obj_ins_)
                      (caddr panel_list_sorted_obj_ins_)
                    )
                  )
                  (vlax-3d-point 
                    (car panel_list_sorted_obj_ins_)
                    (+ (cadr panel_list_sorted_obj_ins_) x_move)
                    (caddr panel_list_sorted_obj_ins_)
                  )
                )
                
              )
              (setq x_move (+ (+ (+ (caddr (nth (- panel_list_sorted_i 1) panel_list_sorted_)) x_move) 0.04) 0.005))
          )
          (setq x_move (+(+ (+ (caddr (nth panel_list_sorted_i panel_list_sorted_)) x_move ) 0.04 ) 0.005 ) )
        )
        (setq panel_list_sorted_i (+ panel_list_sorted_i 1))
      )
    ;
  )

  (defun c:make_cuting_plan_xy_MKXXYYCPL ()
    ;selection_set_for_fillter_blk_name
      (if  ;pre_select_ssget_or_post_select_ssget
        (=
          (setq ss_pre_filter_set_xx_ (ssget "i"
                                            (list
                                              (cons 0 "INSERT") ;type of object
                                              (cons 8 "000 - CUTTING_SYMBOL")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              (cons 8 "000 - CUTTING_SYMBOL")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:corrd_sorting_group (TA:standard_list_croodinate+ename (TA:EF_Filter_ss_set_ ss_pre_filter_set_xx_ "PANEL_SET.NO." )) 1 ))
    ;preloop_and_while
      (setq ss_pre_filter_set_xxx_i 0)
      (while (< ss_pre_filter_set_xxx_i (+ 1 (length ss_pre_filter_set_xx_)))
        (setq ss_pre_filter_set_xx_list_ (nth  ss_pre_filter_set_xxx_i ss_pre_filter_set_xx_))
        ;preloop_and_while
          (setq ss_pre_filter_set_xx_list_i 0)
          (while (< ss_pre_filter_set_xx_list_i (length ss_pre_filter_set_xx_list_))
            (setq ss_pre_filter_set_xx_list_ename_ (cadr (nth  ss_pre_filter_set_xx_list_i ss_pre_filter_set_xx_list_)))
            (setq ss_pre_filter_set_xx_list_obj_ (vlax-ename->vla-object ss_pre_filter_set_xx_list_ename_))
            (setq ss_pre_filter_set_xx_list_obj_getboundingbox (vla-getboundingbox ss_pre_filter_set_xx_list_obj_ 'min_ 'max_)) 
            (setq ss_pre_filter_set_xx_list_min_ (vlax-safearray->list min_)) 
            (setq ss_pre_filter_set_xx_list_max_ (vlax-safearray->list max_)) 
            
            (command "zoom" "o" ss_pre_filter_set_xx_list_ename_ "")
            (LM:vl-setattributevalue 
              ss_pre_filter_set_xx_list_obj_ 
              "sort_axis"  
              (setq axis_string_ ;Get-string by keep previous value
                  (if
                    (or
                      (/= (setq axis_string_val (getstring (strcat "\nSpecify Pattern name <" (if axis_string_ axis_string_ "") ">: ") ) ) "" )
                    )
                      (progn
                        (setq axis_string_ axis_string_val)
                        (setq axis_string_keep_val_ axis_string_val)
                      )
                    (setq axis_string_val axis_string_keep_val_)
                  )
              ) 
            )
            
            (setq ssPA_pre_filter_set_xx_ (ssget "w"  ss_pre_filter_set_xx_list_min_  ss_pre_filter_set_xx_list_max_
                                            (list
                                              (cons 0 "INSERT") ;type of object
                                              (cons 8 "A11_ALU.SOLID SHEET")   ;kind of layer
                                              ; (cons 2 "000-GRID_LINE_DYN")       ;kind of nameblock
                                              ; (cons 62 1)           ;kind of color call sign with color code index
                                            )
                                      )
            )
            (sslength ssPA_pre_filter_set_xx_)
            (setq ssPA_pre_filter_set_xx_ (TA:EF_Filter_ss_set_ ssPA_pre_filter_set_xx_ "001 - DYNAMIC REC&SSQ SHAPE SOLID_startpoint" ))
            (setq mode_xy (LM:vl-getattributevalue ss_pre_filter_set_xx_list_obj_ "sort_axis" ))
            (TA:make_cuting_plan_XY_axis_mkyCPL ssPA_pre_filter_set_xx_ mode_xy )


            






            
            

            
            (setq ss_pre_filter_set_xx_list_i (+ ss_pre_filter_set_xx_list_i 1))
          )
        ;
        (setq ss_pre_filter_set_xxx_i (+ ss_pre_filter_set_xxx_i 1))
      )
    ;
  )

  (defun c:sent_panel_to_cuting-plan_Pa2CP ()
    ;selection_set_for_fillter_blk_name
      (if  ;pre_select_ssget_or_post_select_ssget
        (=
          (setq fullsize_ss_set_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq fullsize_ss_set_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength fullsize_ss_set_)
      )
    ;
    (setq fullsize_ss_set_ (TA:corrd_sorting_group (TA:standard_list_croodinate+ename (TA:EF_Filter_ss_set_ fullsize_ss_set_ "PANEL_SET.NO." )) 1 ))
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "001 - DYNAMIC REC&SSQ SHAPE SOLID_startpoint" ))
    ; ;preloop_and_while
    ;   (setq max-num_ ())
    ;   (setq ss_pre_filter_set_xx_i 0)
    ;   (while (< ss_pre_filter_set_xx_i (sslength ss_pre_filter_set_xx_))
    ;     (setq ss_pre_filter_set_xx_ename_ (ssname ss_pre_filter_set_xx_ ss_pre_filter_set_xx_i))
    ;     (setq ss_pre_filter_set_xx_obj_ (vlax-ename->vla-object ss_pre_filter_set_xx_ename_))
    ;     (setq max-num_ (vl-sort (cons (atof (LM:vl-getattributevalue ss_pre_filter_set_xx_obj_ "FULL_SIZE_NO.")) max-num_) '<)  )
    ;     (setq ss_pre_filter_set_xx_i (+ ss_pre_filter_set_xx_i 1))
    ;   )
    ; ;
    ; ;preloop_and_while
    ;   (setq max-num_i 0)
    ;   (while (< max-num_i (length max-num_))
    ;     (setvar "osmode" 1024)
    ;     (setq TGP (getpoint "specify point for insert full size"))
    ;     (setvar "osmode" 1215)
    ;     ;preloop_and_while
    ;       (setq ss_pre_filter_set_xx_i 0)
        
    ;       (while (< ss_pre_filter_set_xx_i (sslength ss_pre_filter_set_xx_))
    ;         (setq ss_pre_filter_set_xx_ename_ (ssname ss_pre_filter_set_xx_ ss_pre_filter_set_xx_i))
    ;         (setq ss_pre_filter_set_xx_obj_ (vlax-ename->vla-object ss_pre_filter_set_xx_ename_))
    ;         (setq ss_pre_filter_set_xx_obj_number_ (LM:vl-getattributevalue ss_pre_filter_set_xx_obj_ "FULL_SIZE_NO."))
    ;           (if (= (atof ss_pre_filter_set_xx_obj_number_)  max-num_i)
    ;             (progn
    ;               (vla-copy ss_pre_filter_set_xx_obj_)
    ;               (vla-move 
    ;                 (setq newblk_obj_ (vlax-ename->vla-object (entlast))) 
    ;                 (vlax-3d-point (vlax-safearray->list (vlax-variant-value (vla-get-insertionpoint newblk_obj_))))
    ;                 (vlax-3d-point TGP)
                    
    ;               )
    ;             )
    ;           )
    ;         (setq ss_pre_filter_set_xx_i (+ ss_pre_filter_set_xx_i 1))
    ;       )
    ;     ;
    ;     (setq max-num_i (+ max-num_i 1))
    ;   )
    ; ;
    ;preloop_and_while
      (setq fullsize_ss_set_i 0)
      (while (< fullsize_ss_set_i (length fullsize_ss_set_))
        (setq fullsize_ss_set_list_ (nth fullsize_ss_set_i fullsize_ss_set_))
        ;preloop_and_while
          (setq fullsize_ss_set_list_i 0)
          (while (< fullsize_ss_set_list_i (length fullsize_ss_set_list_))
            (setq fullsize_ss_set_list_ename_ (cadr (nth  fullsize_ss_set_list_i fullsize_ss_set_list_)))
            (setq fullsize_ss_set_list_obj_ (vlax-ename->vla-object fullsize_ss_set_list_ename_))
            (setq fullsize_ss_set_list_obj_panel_no_ (atof (LM:vl-getattributevalue fullsize_ss_set_list_obj_ "PANEL_SET.NO." )))
              ;preloop_and_while
                (setq ss_pre_filter_set_xx_i 0)
              
                (while (< ss_pre_filter_set_xx_i (sslength ss_pre_filter_set_xx_))
                  (setq ss_pre_filter_set_xx_ename_ (ssname ss_pre_filter_set_xx_ ss_pre_filter_set_xx_i))
                  (setq ss_pre_filter_set_xx_obj_ (vlax-ename->vla-object ss_pre_filter_set_xx_ename_))
                  (setq ss_pre_filter_set_xx_obj_number_ (LM:vl-getattributevalue ss_pre_filter_set_xx_obj_ "FULL_SIZE_NO."))
                    (if (= (atof ss_pre_filter_set_xx_obj_number_)  fullsize_ss_set_list_obj_panel_no_)
                      (progn
                        (vla-copy ss_pre_filter_set_xx_obj_)
                        (vla-move 
                          (setq newblk_obj_ (vlax-ename->vla-object (entlast))) 
                          (vlax-3d-point (vlax-safearray->list (vlax-variant-value (vla-get-insertionpoint newblk_obj_))))
                          (vlax-3d-point (car (nth  fullsize_ss_set_list_i fullsize_ss_set_list_)))
                          
                        )
                      )
                    )
                  (setq ss_pre_filter_set_xx_i (+ ss_pre_filter_set_xx_i 1))
                )
              ;
            
            (setq fullsize_ss_set_list_i (+ fullsize_ss_set_list_i 1))
          )
        ;
        (setq fullsize_ss_set_i (+ fullsize_ss_set_i 1))
      )
    ;
  )
  (defun c:make_cuting_plan_handle_updatePanel ()
    ;selection_set_for_fillter_blk_name
      (if  ;pre_select_ssget_or_post_select_ssget
        (=
          (setq ss_pre_filter_set_xx_ (ssget "i"
                                            (list
                                              (cons 0 "INSERT") ;type of object
                                              (cons 8 "000 - CUTTING_SYMBOL")   ;kind of layer
                                              ; (cons 2 "000-GRID_LINE_DYN")       ;kind of nameblock
                                              ; (cons 62 1)           ;kind of color call sign with color code index
                                            )
                                      )
          )
          nil
        )
        (progn
          (setq ss_pre_filter_set_xx_   (ssget
                                            (list
                                              (cons 0 "INSERT") ;type of object
                                              (cons 8 "000 - CUTTING_SYMBOL")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:corrd_sorting_group (TA:standard_list_croodinate+ename (TA:EF_Filter_ss_set_ ss_pre_filter_set_xx_ "PANEL_SET.NO." )) 1 ))
    ;preloop_and_while
      (setq ss_pre_filter_set_xxx_i 0)
      (while (< ss_pre_filter_set_xxx_i (+ 1 (length ss_pre_filter_set_xx_)))
        (setq ss_pre_filter_set_xx_list_ (nth  ss_pre_filter_set_xxx_i ss_pre_filter_set_xx_))
        ;preloop_and_while
          (setq ss_pre_filter_set_xx_list_i 0)
          (while (< ss_pre_filter_set_xx_list_i (length ss_pre_filter_set_xx_list_))
            (setq ss_pre_filter_set_xx_list_ename_ (cadr (nth  ss_pre_filter_set_xx_list_i ss_pre_filter_set_xx_list_)))
            (setq ss_pre_filter_set_xx_list_obj_ (vlax-ename->vla-object ss_pre_filter_set_xx_list_ename_))
            (setq ss_pre_filter_set_xx_list_obj_getboundingbox (vla-getboundingbox ss_pre_filter_set_xx_list_obj_ 'min_ 'max_)) 
            (setq ss_pre_filter_set_xx_list_min_ (vlax-safearray->list min_)) 
            (setq ss_pre_filter_set_xx_list_max_ (vlax-safearray->list max_)) 
            
            (setq PANEL_SET (LM:vl-getattributevalue ss_pre_filter_set_xx_list_obj_ "PANEL_SET.NO." ) )
            
            (setq ssPA_pre_filter_set_xx_ (ssget "w"  ss_pre_filter_set_xx_list_min_  ss_pre_filter_set_xx_list_max_
                                            (list
                                              (cons 0 "INSERT") ;type of object
                                              (cons 8 "A11_ALU.SOLID SHEET")   ;kind of layer
                                              ; (cons 2 "000-GRID_LINE_DYN")       ;kind of nameblock
                                              ; (cons 62 1)           ;kind of color call sign with color code index
                                            )
                                      )
            )
            (sslength ssPA_pre_filter_set_xx_)
            ;preloop_and_while
              (setq ssPA_pre_filter_set_xx_i 0)
              (while (and 
                       (/= ssPA_pre_filter_set_xx_ nil)
                       (< ssPA_pre_filter_set_xx_i (sslength ssPA_pre_filter_set_xx_))
                       
                     )
                (setq ssPA_pre_filter_set_xx_ename_ (ssname ssPA_pre_filter_set_xx_ ssPA_pre_filter_set_xx_i))
                (setq ssPA_pre_filter_set_xx_obj_ (vlax-ename->vla-object  ssPA_pre_filter_set_xx_ename_))
                (LM:vl-setattributevalue ssPA_pre_filter_set_xx_obj_ "FULL_SIZE_NO." PANEL_SET)
                
                (LM:vl-setattributevalue (vlax-ename->vla-object(handent (LM:vl-getattributevalue ssPA_pre_filter_set_xx_obj_ "ON_PANEL_SIZE_NO." ))) "FULL_SIZE_NO." PANEL_SET )
                (setq ssPA_pre_filter_set_xx_i (+ ssPA_pre_filter_set_xx_i 1))
              )
            ;      
            (setq ss_pre_filter_set_xx_list_i (+ ss_pre_filter_set_xx_list_i 1))
          )
        ;
        (setq ss_pre_filter_set_xxx_i (+ ss_pre_filter_set_xxx_i 1))
      )
    ;
  )
  (defun c:make_cutting_plan_select_blank_box_ssblbx ()
    ;selection_set_for_fillter_blk_name
      (if  ;pre_select_ssget_or_post_select_ssget
        (=
          (setq ss_pre_filter_set_xx_ (ssget "i"
                                            (list
                                              (cons 0 "INSERT") ;type of object
                                              (cons 8 "000 - CUTTING_SYMBOL")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              (cons 8 "000 - CUTTING_SYMBOL")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "PANEL_SET.NO."))
    ;preloop_and_while
      (setq ss_pre_filter_set_xx_i 0)
      (setq new_ss (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_obj_min_ (vlax-safearray->list min_)) 
        (setq ss_pre_filter_set_xx_obj_max_ (vlax-safearray->list max_)) 
        (setq ssPA_pre_filter_set_xx_ (ssget "w"  ss_pre_filter_set_xx_obj_min_  ss_pre_filter_set_xx_obj_max_
                                          (list
                                            (cons 0 "INSERT") ;type of object
                                            (cons 8 "A11_ALU.SOLID SHEET")   ;kind of layer
                                            ; (cons 2 "000-GRID_LINE_DYN")       ;kind of nameblock
                                            ; (cons 62 1)           ;kind of color call sign with color code index
                                          )
                                    )
          )
          (if (= ssPA_pre_filter_set_xx_ nil)
            (progn
              (setq new_ss (ssadd ss_pre_filter_set_xx_ename_ new_ss ))
            )
          )
          
        (setq ss_pre_filter_set_xx_i (+ ss_pre_filter_set_xx_i 1))
      )
    ;
    (command "pselect"  new_ss "" )
  )
  (defun c:make_cutting_plan_rectangle_to_block_ssmkrec2cp ()
    ;selection_set_for_fillter_blk_name
      (if  ;pre_select_ssget_or_post_select_ssget
        (=
          (setq ss_pre_filter_set_xx_ (ssget "i"
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (vlax-safearray->list min_)) 
        (setq ss_pre_filter_set_xx_max_ (vlax-safearray->list max_)) 
        
        (TA:vla-insertblock "001 - DYNAMIC REC&SSQ SHAPE SOLID_startpoint" ss_pre_filter_set_xx_min_ 1 0 )
        ;new_blk_entlast object
          (setq new_ename (entlast))
          (setq new_obj (vlax-ename->vla-object new_ename))
          (LM:setdynpropvalue new_obj "w" (distance ss_pre_filter_set_xx_min_ (list (car ss_pre_filter_set_xx_max_) (cadr ss_pre_filter_set_xx_min_) 0 ) ))
          (LM:setdynpropvalue new_obj "h" (distance ss_pre_filter_set_xx_min_ (list (car ss_pre_filter_set_xx_min_) (cadr ss_pre_filter_set_xx_max_) 0 ) ))
        ;
        (vla-delete ss_pre_filter_set_xx_obj_ )
        (setq ss_pre_filter_set_xx_i (+ ss_pre_filter_set_xx_i 1))
      )
    ;
  )
  (defun c:make_cutting_plan_find_panel_mkfipl_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "001 - DYNAMIC REC&SSQ SHAPE SOLID_startpoint"))
    (setq input_panel_num_ (cond ( (getint (strcat "\nspecify get color \n<" (rtos (setq input_panel_num_ (cond (input_panel_num_) (1.0) ) ) ) "> : " ) ) ) (input_panel_num_) ) )
    ;preloop_and_while
      (setq ss_pre_filter_set_xx_i 0)
      (setq selection_target_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (= input_panel_num_ (atoi (LM:vl-getattributevalue ss_pre_filter_set_xx_obj_ "FULL_SIZE_NO.")) )
          (progn
            (setq selection_target_ (ssadd ss_pre_filter_set_xx_ename_ selection_target_))
          )
        )
        (setq ss_pre_filter_set_xx_i (+ ss_pre_filter_set_xx_i 1))
      )
    ;
    (command "pselect"  selection_target_ "" )
  )
  (defun c:make_cutting_plan_find_panel_mkfihandle_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "001 - DYNAMIC REC&SSQ SHAPE SOLID_startpoint"))
    ;preloop_and_while
      (setq ss_pre_filter_set_xx_i 0)
      (setq handle_ref_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_handle_ (LM:vl-getattributevalue ss_pre_filter_set_xx_obj_ "ON_PANEL_SIZE_NO."))
        (setq handle_ref_ (cons ss_pre_filter_set_xx_obj_handle_ handle_ref_))
        (setq ss_pre_filter_set_xx_i (+ ss_pre_filter_set_xx_i 1))
      )
    ;
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (setq ss_pre_filter_set_xx_ (TA:EF_Filter_ss_set_ ss_pre_filter_set_xx_ "001 - DYNAMIC REC&SSQ SHAPE SOLID_startpoint"))
    ;preloop_and_while
      (setq handle_ref_i 0)
      (setq selection_target_ (ssadd))
      (while (< handle_ref_i (length handle_ref_))
        (setq handle_ref_ename_ (nth  handle_ref_i handle_ref_))
        
        ;preloop_and_while
          (setq ss_pre_filter_set_xx_i 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object  ss_pre_filter_set_xx_ename_))
            (setq ss_pre_filter_set_xx_obj_handle_ (LM:vl-getattributevalue ss_pre_filter_set_xx_obj_ "ON_PANEL_SIZE_NO."))
            (if (= ss_pre_filter_set_xx_obj_handle_ handle_ref_ename_)
              (progn
                (setq selection_target_ (ssadd ss_pre_filter_set_xx_ename_ selection_target_))
              )
            )
            (setq ss_pre_filter_set_xx_i (+ ss_pre_filter_set_xx_i 1))
          )
        ;
        (setq handle_ref_i (+ handle_ref_i 1))
      )
    ;
    (command "pselect"  selection_target_ "" )
  )
  (defun c:make_cutting_plan_stamp_direction_paint_mkdip ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "001 - DYNAMIC REC&SSQ SHAPE SOLID_startpoint"))
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))

        (setq W (LM:getdynpropvalue ss_pre_filter_set_xx_obj_ "w" ))
        (setq H (LM:getdynpropvalue ss_pre_filter_set_xx_obj_ "h" ))
        (LM:vl-setattributevalue ss_pre_filter_set_xx_obj_ "h" (rtos H 2 2) )
        (LM:vl-setattributevalue ss_pre_filter_set_xx_obj_ "W" (rtos W 2 2) )
        

        (LM:setdynpropvalue ss_pre_filter_set_xx_obj_ "coil_direction_move_ x" (/ W 2))
        (LM:setdynpropvalue ss_pre_filter_set_xx_obj_   "coil_direction_move_ y" (/ h 2))
        (LM:setdynpropvalue ss_pre_filter_set_xx_obj_ "coil_direction_sc_" (/   w 7 ))
        (if (or 
              (> H W)
              (> (*  (- H W) -1) 100)
            )
          (progn
            (LM:setdynpropvalue ss_pre_filter_set_xx_obj_ "distance1" (fix (/   W 4)))
          )
          (LM:setdynpropvalue ss_pre_filter_set_xx_obj_ "distance1" (fix (/ h 25)))
        )
        (setq ss_pre_filter_set_xx_i (+ ss_pre_filter_set_xx_i 1))
      )
    ;
  )
  (defun c:make_cutting_plan_stamp_direction_paint_mkd2ip ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "001 - DYNAMIC REC&SSQ SHAPE SOLID_startpoint"))
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))

        (setq W (LM:getdynpropvalue ss_pre_filter_set_xx_obj_ "w" ))
        (setq H (LM:getdynpropvalue ss_pre_filter_set_xx_obj_ "h" ))
        (LM:vl-setattributevalue ss_pre_filter_set_xx_obj_ "h" (rtos H 2 2) )
        (LM:vl-setattributevalue ss_pre_filter_set_xx_obj_ "W" (rtos W 2 2) )
        

        (LM:setdynpropvalue ss_pre_filter_set_xx_obj_ "coil_direction_move_ x" (/ W 2))
        (LM:setdynpropvalue ss_pre_filter_set_xx_obj_   "coil_direction_move_ y" (/ h 2))
        (LM:setdynpropvalue ss_pre_filter_set_xx_obj_ "coil_direction_sc_" (/   h 10 ))
        (if (or 
              (> H W)
              (> (*  (- H W) -1) 100)
            )
          (progn
            (LM:setdynpropvalue ss_pre_filter_set_xx_obj_ "distance1" (fix (/   w 4)))
          )
          (LM:setdynpropvalue ss_pre_filter_set_xx_obj_ "distance1" (fix (/ h 2)))
        )
        (setq ss_pre_filter_set_xx_i (+ ss_pre_filter_set_xx_i 1))
      )
    ;
  )

;


(defun c:make_cutting_plan_cutlistp_ ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_ ss_pre_filter_set_xx_ "001 - DYNAMIC REC&SSQ SHAPE SOLID_startpoint"))
  ;preloop_and_while
    (setq ss_pre_filter_set_xx_i 0)
    (setq ss_panel_set_ ( ))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      (setq ss_panel_set_ (cons 
                            (list 
                              ss_pre_filter_set_xx_ename_
                              (setq W (+ (+ (LM:getdynpropvalue ss_pre_filter_set_xx_obj_ "W" ) 0.04) 0.005))
                              (setq H (+ (+ (LM:getdynpropvalue ss_pre_filter_set_xx_obj_ "H" ) 0.04) 0.005))
                              
                            )
                            ss_panel_set_
                          )
      )
      (setq ss_pre_filter_set_xx_i (+ ss_pre_filter_set_xx_i 1))
    )
  ;
  ;TA:stanndard_lambda_sorting
    (setq ss_panel_set_sorted_ (vl-sort ss_panel_set_  ;bigest open indent list
                                              (function 
                                                (lambda (a b) 
                                                  (> (cadr a) (cadr b))
                                                )
                                              )
                          ) ;bigest close indent list
    )
  ;
  ;preloop_and_while
    (setq ss_panel_set_sorted_i 1)
    (setq level_time 1)
    (setq x_checker 0)
    (setq x_checker (cadr (nth  0 ss_panel_set_sorted_)))
    ; (setq ss_pre_filter_set_xx_ (ssdel  (car (nth  0 ss_panel_set_sorted_)) ss_pre_filter_set_xx_ ))
    (while (< ss_panel_set_sorted_i (length ss_panel_set_sorted_))
      (setq ss_panel_set_sorted_ename_ (car (nth  ss_panel_set_sorted_i ss_panel_set_sorted_))) 
      (setq ss_panel_set_sorted_obj_ (vlax-ename->vla-object  ss_panel_set_sorted_ename_))
      (command "pselect"  ss_panel_set_sorted_ename_ "" )
      (setq ss_panel_set_sorted_obj_ins_ (vlax-safearray->list (vlax-variant-value (vla-get-insertionpoint ss_panel_set_sorted_obj_))))
      
      (setq y_checker (caddr (nth  (- ss_panel_set_sorted_i 1) ss_panel_set_sorted_)))
      (if 
        (and 
          (/= ss_panel_set_sorted_i 0)
          (< (setq x_checker (+ x_checker (cadr (nth  ss_panel_set_sorted_i ss_panel_set_sorted_)))) 1.250 )
          (setq level_time ( + level_time 1))
        )
        (progn   
          (if (>= level_time 2)
            (progn
              (setq x_checkery (cadr (nth  (-  ss_panel_set_sorted_i 1) ss_panel_set_sorted_)))
              (vla-move ss_panel_set_sorted_obj_ 
                        (vlax-3d-point ss_panel_set_sorted_obj_ins_) 
                        (vlax-3d-point 
                          (vlax-safearray->list (vlax-variant-value (vla-get-insertionpoint (vlax-ename->vla-object (car (nth  (- ss_panel_set_sorted_i 1) ss_panel_set_sorted_))))))
                        ) 
              )
              (vla-move ss_panel_set_sorted_obj_ (vlax-3d-point 0 0 0) (vlax-3d-point x_checkery 0 0) )
            )
            (vla-move ss_panel_set_sorted_obj_ (vlax-3d-point 0 0 0) (vlax-3d-point x_checker 0 0) )
          )
        )
        (if (and (/= ss_panel_set_sorted_i 0) (> x_checker 1.250))
          (progn
            (setq ss        (vla-move ss_panel_set_sorted_obj_ (vlax-3d-point 0 0 0) (vlax-3d-point 0 y_checker 0) )
                  x_checker (cadr (nth  (- ss_panel_set_sorted_i 1)  ss_panel_set_sorted_))
            )
            ;preloop_and_while
              (setq ss_panel_set_sorted_ii (+ 1 ss_panel_set_sorted_i))
              ; (setq x_checker (+ x_checker (cadr (nth  ss_panel_set_sorted_ii ss_panel_set_sorted_))))
              (while (< ss_panel_set_sorted_ii (length ss_panel_set_sorted_))
                (setq sstemp_panel_set_sorted_ename_ (car (nth  ss_panel_set_sorted_ii ss_panel_set_sorted_))) 
                ; (command "pselect"   ss_panel_set_sorted_ename_ "" )
                (setq sstemp_panel_set_sorted_obj_ (vlax-ename->vla-object  sstemp_panel_set_sorted_ename_))
                (vla-move 
                  sstemp_panel_set_sorted_obj_ 
                  (vlax-3d-point (setq sstemp_panel_set_sorted_obj_ins_ (vlax-safearray->list (vlax-variant-value (vla-get-insertionpoint sstemp_panel_set_sorted_obj_)))))
                  (vlax-3d-point (list (car sstemp_panel_set_sorted_obj_ins_) (+ (cadr sstemp_panel_set_sorted_obj_ins_) y_checker) 0 ))
                )
                (setq ss_panel_set_sorted_ii (+ ss_panel_set_sorted_ii 1))
              )
              (setq level_time 1)
            ;
          )
          (setq ss        (vla-move ss_panel_set_sorted_obj_ (vlax-3d-point 0 0 0) (vlax-3d-point x_checker 0 0) )
                x_checker (+ x_checker (cadr (nth  ss_panel_set_sorted_i ss_panel_set_sorted_)))
                level_time 1
          )
        )
      )
      (setq ss_panel_set_sorted_i (+ ss_panel_set_sorted_i 1))
      ; (command "pselect"   ss_pre_filter_set_xx_ "" )
    )
  ;
)

(defun c:match_length_MMAL ()
  

    (initget "Yes No")
      (setq ss_ ;Detect the variable's result in case of a function error
        (vl-catch-all-apply 
          (function 
            (lambda () 
              (setq measurement_ (not (eq "No" (getkword "\nKeep measure with object? [Yes/No] <Y>: "))))
            )
          )
        )
      )
    ;selection_set_for_fillter_blk_name
    (if (/= ss_ T)
      (progn
        (if  ;pre_select_ssget_or_post_select_ssget
          (=
            (setq ss_pre_filter_set_xx_ (ssget "i"
                                              (list
                                                (cons 0 "dimension") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "dimension") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
        ;preloop_and_while
          (setq ss_pre_filter_set_xx_i 0)
          (setq overall_length_ 0)
          (while (< ss_pre_filter_set_xx_i (sslength ss_pre_filter_set_xx_))
            (setq ss_pre_filter_set_xx_ename_ (ssname ss_pre_filter_set_xx_ ss_pre_filter_set_xx_i))
            (setq ss_pre_filter_set_xx_obj_ (vlax-ename->vla-object ss_pre_filter_set_xx_ename_))
            (setq overall_length_ (+ overall_length_ (vla-get-measurement ss_pre_filter_set_xx_obj_)))
            (setq ss_pre_filter_set_xx_i (+ ss_pre_filter_set_xx_i 1))
          )
        ;
      )
    )
    (setq kkk ;Detect the variable's result in case of a function error
        (vl-catch-all-apply 
          (function 
            (lambda () 
              (setq pl_ename_ (car (entsel "specify Object")))
            )
          )
        )
      )
    (if (= (wcmatch (vl-princ-to-string kkk) "*error*") nil)
      (progn
           (setq pl_obj_ (vlax-ename->vla-object pl_ename_))
          (LM:setdynpropvalue pl_obj_ "H" (/ overall_length_ 1000))
      )
    )
 
    
    ;

)



(defun c:array_sheet_arsheet ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_ ))
      (setq qtypc (atoi (LM:StringSubst "" "pc." (LM:vl-getattributevalue ss_pre_filter_set_xx_obj_ "qty"))))
      (setq ss_pre_filter_set_xx_obj_ins_ (vlax-safearray->list (vlax-variant-value (vla-get-insertionpoint ss_pre_filter_set_xx_obj_))))
      (setq ss_pre_filter_set_xx_obj_getboundingbox (vla-getboundingbox ss_pre_filter_set_xx_obj_ 'min_ 'max_)) 
      (setq ss_pre_filter_set_xx_min_ (vlax-safearray->list min_)) 
      (setq ss_pre_filter_set_xx_max_ (vlax-safearray->list max_)) 
      (setq ss_pre_filter_set_xx_maxbot (list (car ss_pre_filter_set_xx_max_) (cadr ss_pre_filter_set_xx_min_) 0 ))
      (if (>= qtypc 2)
        (progn
          (command "copy" ss_pre_filter_set_xx_ename_  "" ss_pre_filter_set_xx_min_  "A" qtypc  ss_pre_filter_set_xx_maxbot )
        )
      )
      
      (setq ss_pre_filter_set_xx_i (+ ss_pre_filter_set_xx_i 1))
    )
  ;
)
(defun c:sc11 ()
  (setq sc_ename_ (car (entsel "specify Object")))
  (setq sc_obj_ (vlax-ename->vla-object sc_ename_))
  (vlax-dump-object sc_obj_)
  (setq sc_obj_ins_ (vlax-safearray->list (vlax-variant-value (vla-get-insertionpoint sc_obj_))))
  (command "scale" sc_ename_ "" sc_obj_ins_ 10000)
)
(defun c:d+ ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq get_l (LM:getdynpropvalue sss_obj_ "distance1" ) )
                  (LM:setdynpropvalue sss_obj_ "distance1" (+ get_l 20) )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
            (setq ss_pre_filter_set_xx_ename_ (ssname ss_pre_filter_set_xx_ ss_pre_filter_set_xx_i ) )
            (setq sss_obj_ (vlax-ename->vla-object ss_pre_filter_set_xx_ename_))
            (setq get_l (LM:getdynpropvalue sss_obj_ "distance1"))
            (LM:setdynpropvalue sss_obj_ "distance1" (+ get_l 20))
            (setq ss_pre_filter_set_xx_i (+ ss_pre_filter_set_xx_i 1))
          )
        )
        
      )
    ;

  )
  (defun c:d- ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                  (setq sss_obj_ (vlax-ename->vla-object ss_pre_filter_set_xx_ename_))
                  (setq get_l (LM:getdynpropvalue sss_obj_ "distance1" ) )
                  (LM:setdynpropvalue sss_obj_ "distance1" (- get_l 20) )
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
            (setq ss_pre_filter_set_xx_ename_ (ssname ss_pre_filter_set_xx_ ss_pre_filter_set_xx_i ) )
            (setq sss_obj_ (vlax-ename->vla-object ss_pre_filter_set_xx_ename_))
            (setq get_l (LM:getdynpropvalue sss_obj_ "distance1"))
            (LM:setdynpropvalue sss_obj_ "distance1" (- get_l 20))
            (setq ss_pre_filter_set_xx_i (+ ss_pre_filter_set_xx_i 1))
          )
        )
        
      )
    ;

  )
  (defun c:dc+ ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                (setq ss_pre_filter_set_xx_ename_ (ssname ss_pre_filter_set_xx_ ss_pre_filter_set_xx_i))
                (setq ss_pre_filter_set_xx_obj_ (vlax-ename->vla-object  ss_pre_filter_set_xx_ename_))

                (setq W (LM:getdynpropvalue ss_pre_filter_set_xx_obj_ "w" ))
                (setq H (LM:getdynpropvalue ss_pre_filter_set_xx_obj_ "h" ))
                (LM:vl-setattributevalue ss_pre_filter_set_xx_obj_ "h" (rtos H 2 2) )
                (LM:vl-setattributevalue ss_pre_filter_set_xx_obj_ "W" (rtos W 2 2) )
        

                (LM:setdynpropvalue ss_pre_filter_set_xx_obj_ "coil_direction_move_ x" (/ W 2))
                (LM:setdynpropvalue ss_pre_filter_set_xx_obj_   "coil_direction_move_ y" (/ h 2))
                (LM:setdynpropvalue ss_pre_filter_set_xx_obj_ "coil_direction_sc_" (/   w 7 ))
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
              (setq ss_pre_filter_set_xx_ename_ (ssname ss_pre_filter_set_xx_ ss_pre_filter_set_xx_i))
                (setq ss_pre_filter_set_xx_ename_ (ssname ss_pre_filter_set_xx_ ss_pre_filter_set_xx_i))
                (setq ss_pre_filter_set_xx_obj_ (vlax-ename->vla-object  ss_pre_filter_set_xx_ename_))

                (setq W (LM:getdynpropvalue ss_pre_filter_set_xx_obj_ "w" ))
                (setq H (LM:getdynpropvalue ss_pre_filter_set_xx_obj_ "h" ))
                (LM:vl-setattributevalue ss_pre_filter_set_xx_obj_ "h" (rtos H 2 2) )
                (LM:vl-setattributevalue ss_pre_filter_set_xx_obj_ "W" (rtos W 2 2) )
        

                (LM:setdynpropvalue ss_pre_filter_set_xx_obj_ "coil_direction_move_ x" (/ W 2))
                (LM:setdynpropvalue ss_pre_filter_set_xx_obj_   "coil_direction_move_ y" (/ h 2))
                (LM:setdynpropvalue ss_pre_filter_set_xx_obj_ "coil_direction_sc_" (/   w 7 ))
            (setq ss_pre_filter_set_xx_i (+ ss_pre_filter_set_xx_i 1))
          )
        )
        
      )
    ;

  )
  (defun c:dc+ ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                (setq ss_pre_filter_set_xx_ename_ (ssname ss_pre_filter_set_xx_ ss_pre_filter_set_xx_i))
                (setq ss_pre_filter_set_xx_obj_ (vlax-ename->vla-object  ss_pre_filter_set_xx_ename_))

                (setq W (LM:getdynpropvalue ss_pre_filter_set_xx_obj_ "w" ))
                (setq H (LM:getdynpropvalue ss_pre_filter_set_xx_obj_ "h" ))
                (LM:vl-setattributevalue ss_pre_filter_set_xx_obj_ "h" (rtos H 2 2) )
                (LM:vl-setattributevalue ss_pre_filter_set_xx_obj_ "W" (rtos W 2 2) )
        

                (LM:setdynpropvalue ss_pre_filter_set_xx_obj_ "coil_direction_move_ x" (/ W 2))
                (LM:setdynpropvalue ss_pre_filter_set_xx_obj_   "coil_direction_move_ y" (/ h 2))

                (LM:setdynpropvalue ss_pre_filter_set_xx_obj_ "coil_direction_sc_" (+ (LM:getdynpropvalue ss_pre_filter_set_xx_obj_ "coil_direction_sc_" ) 20))
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
              (setq ss_pre_filter_set_xx_ename_ (ssname ss_pre_filter_set_xx_ ss_pre_filter_set_xx_i))
                (setq ss_pre_filter_set_xx_ename_ (ssname ss_pre_filter_set_xx_ ss_pre_filter_set_xx_i))
                (setq ss_pre_filter_set_xx_obj_ (vlax-ename->vla-object  ss_pre_filter_set_xx_ename_))

                (setq W (LM:getdynpropvalue ss_pre_filter_set_xx_obj_ "w" ))
                (setq H (LM:getdynpropvalue ss_pre_filter_set_xx_obj_ "h" ))
                (LM:vl-setattributevalue ss_pre_filter_set_xx_obj_ "h" (rtos H 2 2) )
                (LM:vl-setattributevalue ss_pre_filter_set_xx_obj_ "W" (rtos W 2 2) )
        

                (LM:setdynpropvalue ss_pre_filter_set_xx_obj_ "coil_direction_move_ x" (/ W 2))
                (LM:setdynpropvalue ss_pre_filter_set_xx_obj_   "coil_direction_move_ y" (/ h 2))
                (LM:setdynpropvalue ss_pre_filter_set_xx_obj_ "coil_direction_sc_" (+ (LM:getdynpropvalue ss_pre_filter_set_xx_obj_ "coil_direction_sc_" ) 20))
            (setq ss_pre_filter_set_xx_i (+ ss_pre_filter_set_xx_i 1))
          )
        )
        
      )
    ;

  )
  (defun c:dc- ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (or (= ss_ nil) (= (vl-prin1-to-string ss_) "#<%catch-all-apply-error%>")  )
        (progn
          ;selection_set_for_fillter_blk_name
            (if  ;pre_select_ssget_or_post_select_ssget
              (=
                (setq ss_pre_filter_set_xx_ (ssget "i"
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
                nil
              )
              (progn
                (setq ss_pre_filter_set_xx_ (ssget 
                                                  (list
                                                    (cons 0 "INSERT") ;type of object
                                                    ; (cons 8 "000 - GRID")   ;kind of layer
                                                    ; (cons 2 "000-GRID_LINE_DYN")       ;kind of nameblock
                                                    ; (cons 62 1)           ;kind of color call sign with color code index
                                                  )
                                            )
                )
              )
              (sslength ss_pre_filter_set_xx_)
            )
          ;
          ;
            ; (setq ss_pre_filter_set_xx_ (TA:EF_Filter_ss_set_ ss_pre_filter_set_xx_ "000TYP-LINE_AND_ARRAY_@400mm._TYPE2_"))
          ;
          ;preloop_and_while
            (setq ss_pre_filter_set_xx_i 0)
            (while (< ss_pre_filter_set_xx_i (sslength ss_pre_filter_set_xx_))
              (setq ss_pre_filter_set_xx_ename_ (ssname ss_pre_filter_set_xx_ ss_pre_filter_set_xx_i))
                (setq ss_pre_filter_set_xx_ename_ (ssname ss_pre_filter_set_xx_ ss_pre_filter_set_xx_i))
                (setq ss_pre_filter_set_xx_obj_ (vlax-ename->vla-object  ss_pre_filter_set_xx_ename_))

                (setq W (LM:getdynpropvalue ss_pre_filter_set_xx_obj_ "w" ))
                (setq H (LM:getdynpropvalue ss_pre_filter_set_xx_obj_ "h" ))
                (LM:vl-setattributevalue ss_pre_filter_set_xx_obj_ "h" (rtos H 2 2) )
                (LM:vl-setattributevalue ss_pre_filter_set_xx_obj_ "W" (rtos W 2 2) )
        

                (LM:setdynpropvalue ss_pre_filter_set_xx_obj_ "coil_direction_move_ x" (/ W 2))
                (LM:setdynpropvalue ss_pre_filter_set_xx_obj_   "coil_direction_move_ y" (/ h 2))

                (LM:setdynpropvalue ss_pre_filter_set_xx_obj_ "coil_direction_sc_" (- (LM:getdynpropvalue ss_pre_filter_set_xx_obj_ "coil_direction_sc_" ) 20))
              (setq ss_pre_filter_set_xx_i (+ ss_pre_filter_set_xx_i 1))
            )
          ;
        
        )
      )
      (if (and (/= ss_ nil) (/= (vl-prin1-to-string ss_) "#<%catch-all-apply-error%>")  )
        (progn
          (setq ss_pre_filter_set_xx_i 0)
          (while (< ss_pre_filter_set_xx_i (sslength ss_pre_filter_set_xx_)) 
              (setq ss_pre_filter_set_xx_ename_ (ssname ss_pre_filter_set_xx_ ss_pre_filter_set_xx_i))
                (setq ss_pre_filter_set_xx_ename_ (ssname ss_pre_filter_set_xx_ ss_pre_filter_set_xx_i))
                (setq ss_pre_filter_set_xx_obj_ (vlax-ename->vla-object  ss_pre_filter_set_xx_ename_))

                (setq W (LM:getdynpropvalue ss_pre_filter_set_xx_obj_ "w" ))
                (setq H (LM:getdynpropvalue ss_pre_filter_set_xx_obj_ "h" ))
                (LM:vl-setattributevalue ss_pre_filter_set_xx_obj_ "h" (rtos H 2 2) )
                (LM:vl-setattributevalue ss_pre_filter_set_xx_obj_ "W" (rtos W 2 2) )
        

                (LM:setdynpropvalue ss_pre_filter_set_xx_obj_ "coil_direction_move_ x" (/ W 2))
                (LM:setdynpropvalue ss_pre_filter_set_xx_obj_   "coil_direction_move_ y" (/ h 2))
                (LM:setdynpropvalue ss_pre_filter_set_xx_obj_ "coil_direction_sc_" (- (LM:getdynpropvalue ss_pre_filter_set_xx_obj_ "coil_direction_sc_" ) 20))
            (setq ss_pre_filter_set_xx_i (+ ss_pre_filter_set_xx_i 1))
          )
        )
        
      )
    ;

  )


(defun c:ro+ ()
    ;user_input_
      (initget "Yes No")
      (setq ss_ ;Detect the variable's result in case of a function error
        (vl-catch-all-apply 
          (function 
            (lambda () 
              (setq DELETE_OBJ_ (not (eq "No" (getkword "\nKeep Existing point with object? [Yes/No] <Y>: "))))
            )
          )
        )
      )
      (if (and (= ss_ nil)  )
        (progn
          (if  ;pre_select_ssget_or_post_select_ssget
            (=
              (setq ss_pre_filter_set_xx_ (ssget "i"
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
              nil
            )
            (progn
              (setq ss_pre_filter_set_xx_ (ssget
                                                (list
                                                  (cons 0 "INSERT") ;type of object
                                                  ; (cons 8 "000 - GRID")   ;kind of layer
                                                  ; (cons 2 "000-GRID_LINE_DYN")       ;kind of nameblock
                                                  ; (cons 62 1)           ;kind of color call sign with color code index
                                                )
                                          )
              )
            )
            (sslength ss_pre_filter_set_xx_)
          )
        )
      )
    ;
    ;preloop_and_while_
      (setq LV_1_ans_ nil)
      (while (/= (vl-catch-all-error-p LV_1_ans_ ) T)
        ;error_detect_
          (setq LV_1_ans_ ;Detect the variable's result in case of a function error
            (vl-catch-all-apply 
              (function 
                (lambda () 
                  (setq LV_1_ans_int_ (cond ( (getint (strcat "method_1" "\n" "method_2" "\n" "method_3" "\n" "method_4" "\n" "method_5" "\n<" (rtos (setq LV_1_ans_int_ (cond (LV_1_ans_int_) (1.0) ) ) ) "> : " ) ) ) (LV_1_ans_int_) ) )
                  
                )
              )
            )
          )
          (if (= (vl-catch-all-error-p LV_1_ans_ ) T)
            (progn
              (vl-catch-all-error-message LV_1_ans_ )
            )
          )
        ;
        
        ;condition_for_folding_control
          (cond
            (;raster_case_1
              (and
                (= LV_1_ans_int_ 1)
                (/= (vl-catch-all-error-p LV_1_ans_ ) T)
              )
              (progn
                ;preloop_and_while
                  (setq ss_pre_filter_set_xx_i 0)
                  (while (< ss_pre_filter_set_xx_i (sslength ss_pre_filter_set_xx_))
                    (setq ss_pre_filter_set_xx_ename_ (ssname ss_pre_filter_set_xx_ ss_pre_filter_set_xx_i))
                    (setq ss_pre_filter_set_xx_obj_ (vlax-ename->vla-object  ss_pre_filter_set_xx_ename_))
                    (setq ss_pre_filter_set_xx_obj_ins_ (vlax-safearray->list (vlax-variant-value (vla-get-insertionpoint ss_pre_filter_set_xx_obj_))))
                    (vla-put-rotation ss_pre_filter_set_xx_obj_ (deg-to-rad (TA:ModifyRotation (rad-to-deg (vla-get-rotation ss_pre_filter_set_xx_obj_  )) +1)) )
                    (setq ss_pre_filter_set_xx_i (+ ss_pre_filter_set_xx_i 1))
                  )
                ;
                (princ "raster_case_1")
              )
            )
            (;raster_case_2
              (and
                (= LV_1_ans_int_ 2)
                (/= (vl-catch-all-error-p LV_1_ans_ ) T)
              )
              (progn
                (setq ss_pre_filter_set_xx_i 0)
                (while (< ss_pre_filter_set_xx_i (sslength ss_pre_filter_set_xx_))
                  (setq ss_pre_filter_set_xx_ename_ (ssname ss_pre_filter_set_xx_ ss_pre_filter_set_xx_i))
                  (setq ss_pre_filter_set_xx_obj_ (vlax-ename->vla-object  ss_pre_filter_set_xx_ename_))
                  (setq ss_pre_filter_set_xx_obj_ins_ (vlax-safearray->list (vlax-variant-value (vla-get-insertionpoint ss_pre_filter_set_xx_obj_))))
                  (vla-put-rotation ss_pre_filter_set_xx_obj_ (deg-to-rad (TA:ModifyRotation (rad-to-deg (vla-get-rotation ss_pre_filter_set_xx_obj_  )) -1)) )
                  (setq ss_pre_filter_set_xx_i (+ ss_pre_filter_set_xx_i 1))
                )
                (princ "raster_case_2")
              )
            )
            (;raster_case_5
              (and
                (vl-catch-all-error-p LV_1_ans_ )
                  
              )
              (progn
                
                (princ "raster_case_6")
              )
            )
          )
        ;
      )
    ; 
)










;PPLINE CKST func
  (defun PPLINE_CKST_MK-CSD-PLAN-black (blk_obj_)
    ; (setq blk_ename_ (car (entsel "specify Object")))
    ; (setq blk_obj_ (vlax-ename->vla-object blk_ename_))
    (GetBlockHatches (LM:Effectivename blk_obj_))
    (setq blk_obj_subblk_LVL1_ (TA:Assembly_vla-obj-block_ blk_obj_))
    ;preloop_and_while
      (setq blk_obj_subblk_LVL1_i 0)
      (while (< blk_obj_subblk_LVL1_i (length blk_obj_subblk_LVL1_))
        (setq blk_obj_subblk_LVL1_obj_ (car (nth  blk_obj_subblk_LVL1_i blk_obj_subblk_LVL1_)))
        (GetBlockHatches (LM:Effectivename blk_obj_subblk_LVL1_obj_))
        (if (/= (setq LV2_ (TA:Assembly_vla-obj-block_ blk_obj_subblk_LVL1_obj_)) nil)
          (progn
            ;preloop_and_while
              (setq LV2_i 0)
              (while (< LV2_i (length LV2_))
                (setq LV2_obj_ (car (nth  LV2_i LV2_)))
                (GetBlockHatches (LM:Effectivename LV2_obj_))
                (if (= (TA:Assembly_vla-obj-block_ LV2_obj_) nil)
                  (progn
                    (GetBlockHatches (LM:Effectivename LV2_obj_))
                  )
                  ; (alert "S")
                )
                (setq LV2_i (+ LV2_i 1))
              )
            ;
          )
          (GetBlockHatches (LM:Effectivename blk_obj_subblk_LVL1_obj_))
        )

        (setq blk_obj_subblk_LVL1_i (+ blk_obj_subblk_LVL1_i 1))
      )
    ;
  )
  (defun GetBlockHatches (blockname )
    (setq line_color 8)
    (setq hatch_color 9)
    (setq hatches_ '())
    (setq blkdef (tblobjname "BLOCK" blockname))
    (setq ent (entnext blkdef))
    (while ent
      (setq ed (entget ent))
      (if (= (cdr (assoc 0 ed)) "HATCH")
        (progn
          (setq hatches_ (cons ent hatches_))
          ;main idea of code keep or delete don't affect with core code
            (setq hatches_obj_ (vlax-ename->vla-object (cdr (assoc -1 ed))))
            (vla-put-color hatches_obj_  hatch_color)
            (vla-put-EntityTransparency hatches_obj_ 80 )
          ;
        )
      )
      (if (= (cdr (assoc 0 ed)) "ARC")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (if (= (cdr (assoc 0 ed)) "LINE")
        (progn
          ; (setq hatches_ (cons ent hatches_))
          ;main idea of code keep or delete don't affect with core code
            (setq hatches_obj_ (vlax-ename->vla-object (cdr (assoc -1 ed))))
            (if (/= (vla-get-layer hatches_obj_ ) "A-ANNO-SYMB")
              (progn
                (vla-put-color hatches_obj_  line_color)
              )
            )
          ;
        )
      )
      (if (= (cdr (assoc 0 ed)) "LWPOLYLINE")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (if (= (cdr (assoc 0 ed)) "SPLINE")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (if (= (cdr (assoc 0 ed)) "ELLIPSE")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (setq ent (entnext ent))
    )
    (reverse hatches)
  )
  (defun c:PPLINE_CKST_CSD-PLAN_mkblack ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (textscr)
    (getstring "\nHit [ENTER] to continue...")
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq LV00_ (TA:Assembly_vla-obj-block_ ss_pre_filter_set_xx_obj_))
          ;preloop_and_while
            (setq LV00_i 0)
            (while (< LV00_i (length LV00_))
              (setq LV00_obj_ (car (nth  LV00_i LV00_)))
              (PPLINE_CKST_MK-CSD-PLAN-black LV00_obj_ )
              
              (setq LV00_i (+ LV00_i 1))
            )
          ;
        (TA:textscr_process "update" ss_pre_filter_set_xx_i ss_pre_filter_set_xx_)
        (setq ss_pre_filter_set_xx_i (+ ss_pre_filter_set_xx_i 1))
      )
    ; 
    (command "-layer" "filter" "n" "G" "" "*CSD*" "CSD" ""  )
  )

;
(defun c:csdflayer_ ()
  (if (= 1 1)
    (progn
      
      (command "-layer" "filter" "n" "G" "" "*CSD*" "CSD" ""  )
      (command "-layer" "filter" "s" "All" "")
      
    )
  )
)













;PPLINE CKST - Layer Func
  (defun c:PPLINE_CKST_viewport_layer_CKST-VPpanel()
    ;detect_mode_
      ;เพิ่มคำสั่งที่ใช้เช็คตัวตนของเลเยอร์อีกครั้ง
    ;
    (_StartUndo doc)
    (if (= (TA:if_found_layer_ "A11_ALU.SOLID SHEET" ) T)
      (progn
        (command "vplayer" "c" 2 "A11_ALU.SOLID SHEET" "c" "")
      )
    )
    (if (= (TA:if_found_layer_ "A04_TUBE SERIES" ) T)
      (progn
        (command "vplayer" "c" 2 "A04_TUBE SERIES" "c" "")
      )
    )
    (if (= (TA:if_found_layer_ "001 - ASCESSORIES" ) T)
      (progn
        (command "vplayer" "f" "001 - ASCESSORIES" "c" "")
      )
    )
    (if (= (TA:if_found_layer_ "001 - ASCESSORIES_HANGING" ) T)
      (progn
        (command "vplayer" "f" "001 - ASCESSORIES_HANGING" "c" "")
      )
    )
    (if (= (TA:if_found_layer_ "FRAMING_HANGING_MAIN_COLOR_1" ) T)
      (progn
        (command "vplayer" "f" "FRAMING_HANGING_MAIN_COLOR_1" "c" "")
      )
    )
    (if (= (TA:if_found_layer_ "000 - GRID" ) T)
      (progn
        (command "vplayer" "f" "000 - GRID" "c" "")
      )
    )
    (if (= (TA:if_found_layer_ "000 - DEF GRID" ) T)
      (progn
        (command "vplayer" "f" "000 - DEF GRID" "c" "")
      )
    )
    (setq TA_layer_ (TA:get_name_layer_in_drawing)) 
    (if (and 
          (/= (TA:wcmatch_list (list "*000_PPLINE_CKST_SMOKE_ACESSORIES*") TA_layer_ T) nil)
          (/= (TA:wcmatch_list (list "*000_PPLINE_CKST_SMOKE_BARRIER*") TA_layer_ T) nil)
        )
      (progn
        (command "vplayer" "F" "*000_PPLINE_CKST_SMOKE_ACESSORIES*" "c" "")
        (command "vplayer" "F" "*000_PPLINE_CKST_SMOKE_BARRIER*" "c" "")
      )
    )
    (if (and 
          (/= (TA:wcmatch_list (list "*000 - CSD_*") TA_layer_ T) nil)
        )
      (progn
        (command "vplayer" "f" "000 - CSD_*" "c" "")
      )
    )
    (if (and 
          (/= (TA:wcmatch_list (list "000 - SYMBOL CON_*") TA_layer_ T) nil)
        )
      (progn
        (command "vplayer" "f" "000 - SYMBOL CON_*" "c" "")
      )
    )
    (if (and 
          (/= (TA:wcmatch_list (list "FRAMING_*") TA_layer_ T) nil)
        )
      (progn
        (command "vplayer" "f" "FRAMING_*" "c" "")
      )
    )
    (if (and 
          (/= (TA:wcmatch_list (list "008 - AIR_*") TA_layer_ T) nil)
          (/= (TA:wcmatch_list (list "008 - E&M_*") TA_layer_ T) nil)
          (/= (TA:wcmatch_list (list "008 - LIGHT_*") TA_layer_ T) nil)
        )
      (progn
        (command "vplayer" "c" 1 "008 - AIR_*" "c" "")
        (command "vplayer" "c" 1 "008 - E&M_*" "c" "")
        (command "vplayer" "c" 1 "008 - LIGHT_*" "c" "")
      )
    )
    (_endUndo doc)
    
    
    ; (command "-layer" "color" 251 "VP" "SMOKE" "")
  )
  (defun c:PPLINE_CKST_viewport_layer_CKST-VPC06()
    ;detect_mode_
      ;เพิ่มคำสั่งที่ใช้เช็คตัวตนของเลเยอร์อีกครั้ง
    ;
    (TA:interface_text_ T)
    
    (_StartUndo doc)
    (if (= (TA:if_found_layer_ "A11_ALU.SOLID SHEET" ) T)
      (progn
        (command "vplayer" "c" 251 "A11_ALU.SOLID SHEET" "c" "")
      )
    )
    (if (= (TA:if_found_layer_ "A04_TUBE SERIES" ) T)
      (progn
        (command "vplayer" "c" 251 "A04_TUBE SERIES" "c" "")
      )
    )
    (if (= (TA:if_found_layer_ "001 - ASCESSORIES" ) T)
      (progn
        (command "vplayer" "f" "001 - ASCESSORIES" "c" "")
      )
    )
    (if (= (TA:if_found_layer_ "001 - ASCESSORIES_HANGING" ) T)
      (progn
        (command "vplayer" "f" "001 - ASCESSORIES_HANGING" "c" "")
      )
    )
    (if (= (TA:if_found_layer_ "FRAMING_HANGING_MAIN_COLOR_1" ) T)
      (progn
        (command "vplayer" "f" "FRAMING_HANGING_MAIN_COLOR_1" "c" "")
      )
    )
    ; (if (= (TA:if_found_layer_ "000 - GRID" ) T)
    ;   (progn
    ;     (command "vplayer" "f" "000 - GRID" "c" "")
    ;   )
    ; )
    (if (= (TA:if_found_layer_ "000 - DEF GRID" ) T)
      (progn
        (command "vplayer" "f" "000 - DEF GRID" "c" "")
      )
    )
    (if (= (TA:if_found_layer_ "S-GRID" ) T)
      (progn
        (command "vplayer" "c" "1" "S-GRID" "c" "")
      )
    )
    (setq TA_layer_ (TA:get_name_layer_in_drawing)) 
    (if (and 
          (/= (TA:wcmatch_list (list "*000_PPLINE_CKST_SMOKE_ACESSORIES*") TA_layer_ T) nil)
          (/= (TA:wcmatch_list (list "*000_PPLINE_CKST_SMOKE_BARRIER*") TA_layer_ T) nil)
        )
      (progn
        (command "vplayer" "F" "*000_PPLINE_CKST_SMOKE_ACESSORIES*" "c" "")
        (command "vplayer" "F" "*000_PPLINE_CKST_SMOKE_BARRIER*" "c" "")
      )
    )
    (if (and 
          (/= (TA:wcmatch_list (list "*000 - CSD_*") TA_layer_ T) nil)
        )
      (progn
        (command "vplayer" "f" "000 - CSD_*" "c" "")
      )
    )
    ;ckst_layer_list_
      (setq CKST_layer_list_ (list
                                "_ G-ANNO-TTLB -1"
                                "_ G-ANNO-TTLB-3"
                                "_ G-ANNO-TTLB-6"
                                "A-ANNO-DIMS"
                                "A-ANNO-DIMS-500"
                                "A-ANNO-NOTE"
                                "A-CLNG"
                                "A-CLNG-IDEN"
                                "A-CLNG-PATT"
                                "A-COLS"
                                "A-COLS-E"
                                "A-DETL"
                                "A-DETL-GENF"
                                "A-DETL-OPENING"
                                "A-DETL-THIN"
                                "A-DOOR"
                                "A-DOOR-E"
                                "A-DOOR-FRAM"
                                "A-DOOR-HDLN"
                                "A-DOOR-OPNG"
                                "A-FLOR"
                                "A-FLOR-E"
                                "A-FLOR-PATT"
                                "A-GENM"
                                "A-GLAZ-CURT"
                                "A-ROOM-IDEN"
                                "A-ROOM-LINE"
                                "A-WALL"
                                "A-WALL-E"
                                "A-WALL-FNSH"
                                "A-WALL-PATT"
                                "CEILING"
                                "COLM"
                                "COLM"
                                "Defpoints"
                                "E-LITE-EQPM"
                                "E-LITE-EQPM-HDLN"
                                "G-ANNO-NPLT"
                                "G-ANNO-REVC"
                                "G-ANNO-REVC-IDEN"
                                "G-ANNO-SCHD"
                                "G-ANNO-TEXT"
                                "G-ANNO-TTLB"
                                "G-ANNO-VTTL"
                                "G-IMPT"
                                "HOOK"
                                "HOOK"
                                "I-WALL-E"
                                "Q-SPCQ"
                                "Q-SPCQ-HDLN"
                                "S-BEAM"
                                "S-BEAM"
                                "S-COLS"
                                "S-COLS-E"
                                "S-GRID"
                                "S-GRID-IDEN"
                                "WALL-E"
                                "ceiling"
                              )
      )
      ;preloop_and_while
        (setq CKST_layer_list_i 0)
        (while (and 
                 (> (getvar "CVPORT") 1)
                 (< CKST_layer_list_i (length CKST_layer_list_))
               )
          (if (and 
                (= (TA:if_found_layer_ (setq CKST_layer_list_layername_ (nth  CKST_layer_list_i CKST_layer_list_)) ) T)
                (/= (wcmatch (setq CKST_layer_list_layername_ (nth  CKST_layer_list_i CKST_layer_list_)) "S-GRID,S-GRID-IDEN,A-ANNO-DIMS,S-COLS-E,A-COLS,A-ANNO-MATC,G-ANNO-SYMB") T)
                
              )
            (progn
              (command "vplayer" "c" 1 CKST_layer_list_layername_ "c" ""  )
              (command "vplayer" "tr" 50 CKST_layer_list_layername_ "c" "")
            )
          )
          (TA:textscr_process_V2 "\nupdate dynamic" CKST_layer_list_i CKST_layer_list_)
          (setq CKST_layer_list_i (+ CKST_layer_list_i 1))
        )
      ;
    ;
    
    (_endUndo doc)
    
    
    ; (command "-layer" "color" 251 "VP" "SMOKE" "")
  )
  (defun c:PPLINE_CKST_viewport_layer_CKST-VPfaming()
    (_StartUndo doc)
    (command "vplayer" "c" 251 "A11_ALU.SOLID SHEET" "c" "") 
    (command "vplayer" "c" 251 "A04_TUBE SERIES" "c" "") 
    (command "vplayer" "c" 251 "A-WALL-PATT" "c" "") 
    (command "vplayer" "c" 251 "A-CLNG" "c" "") 
    (command "vplayer" "c" 251 "A-CLNG-PATT" "c" "") 
    (command "vplayer" "f" "A-ROOM-IDEN" "c" "") 
    ; (command "vplayer" "f" "A-ANNO-KEYN" "c" "") 
    (command "vplayer" "f" "G-ANNO-TEXT" "c" "") 
    (command "vplayer" "f" "A-ANNO-DIMS-100" "c" "") 
    (command "vplayer" "f" "A-ANNO-NOTE" "c" "")
    (command "vplayer" "f" "A-ANNO-NOTE" "c" "")
    (command "vplayer" "f" "A-DETL-GENF" "c" "")
    (command "vplayer" "f" "000 - DEF GRID" "c" "")
    ; (command "vplayer" "f" "PPLS Master ROW C1 C2_dwg _2_" "c" "")
    (command "vplayer" "F" "000 - CSD_*" "c" "")
    (command "vplayer" "F" "*000_PPLINE_CKST_SMOKE_ACESSORIES*" "c" "")
    (command "vplayer" "F" "*000_PPLINE_CKST_SMOKE_BARRIER*" "c" "")
    
    
    (command "vplayer" "t" "*duct*" "c" "")
    (_endUndo doc)
  )
  (defun c:PPLINE_CKST_viewport_layer_CKST-VPthawall()
    (command "_.VPLAYER" "_T" "*" "") 
  )
  (defun c:vpaspgelevation ()
    (command "vplayer" "LT" "TA_HL_050.00000" "010 - ASPG_FRAMING_SUB_COLOR_2" "C" "" )
    (command "vplayer" "FR" "010 - ASPG_FRAMING_WIPEOUT_" "C" "" )
  )
  (defun c:PPLINE_CKST_CSDprefixLayer_ ()
    (setq Ex_layer_List_ (TA:get_name_layer_in_drawing ))
    (setq doc (vla-get-ActiveDocument (vlax-get-acad-object)))
    (setq layers (vla-get-Layers doc))

    ;preloop_and_while
      (setq Ex_layer_list_i 0)
      (while (< Ex_layer_list_i (length Ex_layer_list_))
        (setq Ex_layer_list_name_ (nth  Ex_layer_list_i Ex_layer_list_))
        (if 
          (and
            (/= Ex_layer_list_name_ "0")
            (/= Ex_layer_list_name_ "DEF")
          )
          (progn
            (setq Layer-obj_ (vla-Item layers Ex_layer_list_name_))
            (setq newl (strcat "000 - CSD_PL_" Ex_layer_list_name_))
            (vla-put-name Layer-obj_  newl )
            
          )
        )
        (setq Ex_layer_list_i (+ Ex_layer_list_i 1))

      )
    ;
  )
  (defun c:PPLINE-Filter_FAMELINElayer ()
    ;preloop_and_while
      (setq TA-FL_Layer_ (list "000 - SYMBOL CLOUD TYPE 1" "000 - SYMBOL CLOUD TYPE 2" "0" "Defpoints" "000 - DEF GRID" "000 - T E X T" "000 - TITLEBLOCK" 
                            "000 - H A T C H" "000 - L I N E 0.1" "000 - D I M 0.25" 
                            "000 - WIPEOUT" "000 - GRID" "A11_ALU.SOLID SHEET" 
                            "A12_PERFORATED" "A04_TUBE SERIES" "002 - STRUCTURAL STEEL" 
                            "000 - H I D D E N" "000 - D I M" "001 - ASCESSORIES" "001 - ASCESSORIES_HANGING" 
                            "A02_LITEWOOD" "000 - BUBBLE" "000 - SYMBOL CON" "000 - A_XREF" 
                            "000 - GROUND" "000 - L I N E" "000 - TEMP LAYER" "001 - DOOR" 
                            "001 - WINDOWS" "002 - STEEL LRIP" "002 - STEEL TUBE" 
                            "004 - CONCRETE" "004 - DOOR WINDOW" "004 - FLOOR" 
                            "004 - VIVA BOARD" "004 - WALL" "005 - WATER CLOSET EQUIP" 
                            "006 - ROOF" "008 - LIGHTING" "A01_ACP" "A03_SUN LOUVER" 
                            "A05_AHP." "A06_PERFORMANCE LOUVERS" "A07_PRANKCAD" "A08_AEROLITE" 
                            "A09_BIFOLDING" "A10_ENTRANCE MATT" "A13_EXPANDED"
                      )
      )
      (setq ii 0)
      (command "-layer" "filter" "n" "G" "" "0" "PPLINE-FAMELINE" ""  )
      (command "-LAYER" "filter" "new" "group"  
            "PPLINE-FAMELINE"
            "" ;(add layer name to filter, Can use wildcard for adding)
            "NOM_LAYER" 
            "" 
      )
      (while (< ii (length TA-FL_Layer_))
        (setq TA-FL_Layer_list_ (nth ii TA-FL_Layer_))
        
        (command "-layer" "filter"  "e" "0" "NOM_LAYER" "a" TA-FL_Layer_list_ "L" "") 
        
        
        (setq ii (+ ii 1))
      ) 
    ;
  )
  (defun c:PPLINE-Filter_CKSTEXlayer_ ()
    ;preloop_and_while
      (setq example_List_ (list "ssddd" "0" "Defpoints" "000 - T E X T" "000 - TITLEBLOCK" 
                            "000 - H A T C H" "000 - L I N E 0.1" "000 - D I M 0.25" 
                            "000 - WIPEOUT" "000 - GRID" "A11_ALU.SOLID SHEET" 
                            "A12_PERFORATED" "A04_TUBE SERIES" "002 - STRUCTURAL STEEL" 
                            "000 - H I D D E N" "000 - D I M" "001 - ASCESSORIES" 
                            "A02_LITEWOOD" "000 - BUBBLE" "000 - SYMBOL CON" "000 - A_XREF" 
                            "000 - GROUND" "000 - L I N E" "000 - TEMP LAYER" "001 - DOOR" 
                            "001 - WINDOWS" "002 - STEEL LRIP" "002 - STEEL TUBE" 
                            "004 - CONCRETE" "004 - DOOR WINDOW" "004 - FLOOR" 
                            "004 - VIVA BOARD" "004 - WALL" "005 - WATER CLOSET EQUIP" 
                            "006 - ROOF" "008 - LIGHTING" "A01_ACP" "A03_SUN LOUVER" 
                            "A05_AHP." "A06_PERFORMANCE LOUVERS" "A07_PRANKCAD" "A08_AEROLITE" 
                            "A09_BIFOLDING" "A10_ENTRANCE MATT" "A13_EXPANDED"
                      )
      )
      (setq all-layer_ (TA:get_name_layer_in_drawing))
      (setq ii 0)
      (command "-layer" "filter" "n" "G" "" "0" "PPLINE-CKST-EX-LAYER" ""  )
      (while (< ii (length all-layer_))
        (setq all-layer__list_ (nth ii all-layer_))
        ; (setq all-layer__list_ (nth 90 all-layer_))
        (if 
          (or 
            (= (wcmatch (strcase all-layer__lisT_) (strcase "DefpoinTs")) T)
            (= (wcmatch (strcase all-layer__lisT_) (strcase "000 - T E X T")) T)
            (= (wcmatch (strcase all-layer__lisT_) (strcase "000 - TITLEBLOCK")) T)
            (= (wcmatch (strcase all-layer__lisT_) (strcase "000 - H A T C H")) T )
            (= (wcmatch (strcase all-layer__lisT_) (strcase "000 - L I N E 0.1")) T )
            (= (wcmatch (strcase all-layer__lisT_) (strcase "000 - D I M 0.25")) T )
            (= (wcmatch (strcase all-layer__lisT_) (strcase "000 - WIPEOUT")) T)
            (= (wcmatch (strcase all-layer__lisT_) (strcase "000 - GRID")) T)
            (= (wcmatch (strcase all-layer__lisT_) (strcase "A11_ALU.SOLID SHEET")) T )
            (= (wcmatch (strcase all-layer__lisT_) (strcase "A12_PERFORATED")) T)
            (= (wcmatch (strcase all-layer__lisT_) (strcase "A04_TUBE SERIES")) T )
            (= (wcmatch (strcase all-layer__lisT_) (strcase "002 - STRUCTURAL STEEL") ) T )
            (= (wcmatch (strcase all-layer__lisT_) (strcase "000 - H I D D E N")) T )
            (= (wcmatch (strcase all-layer__lisT_) (strcase "000 - D I M")) T)
            (= (wcmatch (strcase all-layer__lisT_) (strcase "001 - ASCESSORIES")) T )
            (= (wcmatch (strcase all-layer__lisT_) (strcase "A02_LITEWOOD")) T)
            (= (wcmatch (strcase all-layer__lisT_) (strcase "000 - BUBBLE")) T)
            (= (wcmatch (strcase all-layer__lisT_) (strcase "000 - SYMBOL CON")) T )
            (= (wcmatch (strcase all-layer__lisT_) (strcase "000 - A_XREF")) T)
            (= (wcmatch (strcase all-layer__lisT_) (strcase "000 - GROUND")) T)
            (= (wcmatch (strcase all-layer__lisT_) (strcase "000 - L I N E")) T)
            (= (wcmatch (strcase all-layer__lisT_) (strcase "000 - TEMP LAYER")) T )
            (= (wcmatch (strcase all-layer__lisT_) (strcase "001 - DOOR")) T)
            (= (wcmatch (strcase all-layer__lisT_) (strcase "001 - WINDOWS")) T)
            (= (wcmatch (strcase all-layer__lisT_) (strcase "002 - STEEL LRIP")) T )
            (= (wcmatch (strcase all-layer__lisT_) (strcase "002 - STEEL TUBE")) T )
            (= (wcmatch (strcase all-layer__lisT_) (strcase "004 - CONCRETE")) T)
            (= (wcmatch (strcase all-layer__lisT_) (strcase "004 - DOOR WINDOW")) T )
            (= (wcmatch (strcase all-layer__lisT_) (strcase "004 - FLOOR")) T)
            (= (wcmatch (strcase all-layer__lisT_) (strcase "004 - VIVA BOARD")) T )
            (= (wcmatch (strcase all-layer__lisT_) (strcase "004 - WALL")) T)
            (= (wcmatch (strcase all-layer__lisT_) (strcase "005 - WATER CLOSET EQUIP") ) T )
            (= (wcmatch (strcase all-layer__lisT_) (strcase "006 - ROOF")) T)
            (= (wcmatch (strcase all-layer__lisT_) (strcase "008 - LIGHTING")) T)
            (= (wcmatch (strcase all-layer__lisT_) (strcase "A01_ACP")) T)
            (= (wcmatch (strcase all-layer__lisT_) (strcase "A03_SUN LOUVER")) T)
            (= (wcmatch (strcase all-layer__lisT_) (strcase "A05_AHP.")) T)
            (= (wcmatch (strcase all-layer__lisT_) (strcase "A06_PERFORMANCE LOUVERS") ) T )
            (= (wcmatch (strcase all-layer__lisT_) (strcase "A07_PRANKCAD")) T)
            (= (wcmatch (strcase all-layer__lisT_) (strcase "A08_AEROLITE")) T)
            (= (wcmatch (strcase all-layer__lisT_) (strcase "A09_BIFOLDING")) T)
            (= (wcmatch (strcase all-layer__lisT_) (strcase "A10_ENTRANCE MATT")) T )
            (= (wcmatch (strcase all-layer__lisT_) (strcase "A13_EXPANDED")) T)
            (= (wcmatch (strcase all-layer__lisT_) (strcat "*" (strcase "CSD_" ) "*" )) T)
            (= (wcmatch (strcase all-layer__lisT_) (strcat "*" (strcase "000" ) "*" )) T)
            (= (wcmatch (strcase all-layer__lisT_) (strcat "*" (strcase "FRAMING_" ) "*" )) T)
          )
          (progn
            (princ all-layer__lisT_)
          )
          (command "-layer" "filter"  "e" "0" "PPLINE-CKST-EX-LAYER" "a" all-layer__lisT_ "L" "")
        )
        (setq ii (+ ii 1))
      ) 
    ;
    (command "-layer" "filter" "s" "All" "")
  )
  (defun c:PPLINE-Filter_CKSTCSDlayer_ ()
    (if (= 1 1)
      (progn
        
        (command "-layer" "filter" "n" "G" "" "*000 - CSD_PL_*" "CSD" ""  )
        (command "-layer" "filter" "s" "All" "")
        (command "-LAYER" "filter" "new" "group"  
                         "CSD"
                         "*Duct*" ;(add layer name to filter, Can use wildcard for adding)
                         "DUCT" 
                         "" 
        )
          (command "-LAYER" "filter" "new" "group"  
                          "CSD"
                          "~*Duct*" ;(add layer name to filter, Can use wildcard for adding)
                          "NO-DUCT" 
                          "" 
          )
        
      )
    )
  )
  (defun c:PPLINE-Filter_CKST_EX_CL_ ()
    (if (= 1 1)
      (progn
        (command "-layer" "n" "CKST - Ex CL" "")
        (command "-layer" "filter" "n" "G" "" "CKST - Ex CL" "CKST - Ex CL" ""  )
      )
    )
  )
  (defun c:PPLINE-CKST-Filterset_ ()
    (c:PPLINE-Filter_CKSTEXlayer_)
    (c:PPLINE-Filter_FAMELINElayer)
    (c:PPLINE-Filter_CKSTCSDlayer_)
    (c:PPLINE-Filter_CKST_EX_CL_)
    
    (command "-LAYER" "filter" "new" "group"  
                         "PPLINE-FAMELINE"
                         "*001 - ASCESSORIES*" ;(add layer name to filter, Can use wildcard for adding)
                         "PPLINE-FAMELINE_ASCESSORIES_" 
                         "" 
    )
    (command "-LAYER" "filter" "new" "group"  
                         "PPLINE-FAMELINE"
                         "" ;(add layer name to filter, Can use wildcard for adding)
                         "PPLINE-FAMELINE_PANEL" 
                         "" 
    )
    (command "-layer"
            "filter"
            "edit"
            "PPLINE-FAMELINE_PANEL" ; (Filter name must be sensitibe case)
            "add"
            "A04_TUBE SERIES" ;(add layer name to filter, Can use wildcard for adding)
             "add"
            "A11_ALU.SOLID SHEET"  ;(add layer name to filter, Can use wildcard for adding)
            "x" ""
    )
  )
  (defun c:PPLINE-CKST-DropVPcolor_ ()
    (_StartUndo doc)
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ;preloop_and_while
        (setq ss_pre_filter_set_xx_i 0)
        (setq ss_pre_filter_set_xx_layet_list_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_layet_list_ (cons (vla-get-layer ss_pre_filter_set_xx_obj_) ss_pre_filter_set_xx_layet_list_))
          
          
          (setq ss_pre_filter_set_xx_i (+ ss_pre_filter_set_xx_i 1))
        )
        (setq target_layer_list_ (TA:Count_item_in_list_ ss_pre_filter_set_xx_layet_list_))
        ;preloop_and_while
          (setq target_layer_list_i 0)
          (while (< target_layer_list_i (length target_layer_list_))
            (setq target_layer_list_ename_ (car (nth  target_layer_list_i target_layer_list_)))
            (if (and 
                  (/= target_layer_list_ename_ "0")
                )
              (progn
                (command "vplayer" "c" 251 target_layer_list_ename_ "c" "")
              )
            )
            
        
            (setq target_layer_list_i (+ target_layer_list_i 1))
          )
        ;
      ;
    ;
    (_endUndo doc)
  )
  
;
;PPLINE CKST - SMOKE BARRIER Layer Func
  (defun c:PPLINE_CKST_SMOKE_create ()
    (command "-layer" "n" "000_PPLINE_CKST_SMOKE_GLASS_FIN_MAIN_COLOR" "")
    (command "-layer" "n" "000_PPLINE_CKST_SMOKE_GLASS_FIN_SUB_COLOR_1" "")
    (command "-layer" "n" "000_PPLINE_CKST_SMOKE_GLASS_FIN_SUB_COLOR_2" "")
    (command "-layer" "n" "000_PPLINE_CKST_SMOKE_GLASS_FIN_HATCH" "")
    (command "-layer" "n" "000_PPLINE_CKST_SMOKE_GLASS_FIN_WIPEOUT" "")
    
    (command "-layer" "n" "000_PPLINE_CKST_SMOKE_BARRIER_MAIN_COLOR" "")
    (command "-layer" "n" "000_PPLINE_CKST_SMOKE_BARRIER_SUB_COLOR_1" "")
    (command "-layer" "n" "000_PPLINE_CKST_SMOKE_BARRIER_SUB_COLOR_2" "")
    (command "-layer" "n" "000_PPLINE_CKST_SMOKE_BARRIER_HATCH" "")
    (command "-layer" "n" "000_PPLINE_CKST_SMOKE_BARRIER_WIPEOUT" "")

    (command "-layer" "n" "000_PPLINE_CKST_SMOKE_ACESSORIES_MAIN_COLOR" "")
    (command "-layer" "n" "000_PPLINE_CKST_SMOKE_ACESSORIES_SUB_COLOR_1" "")
    (command "-layer" "n" "000_PPLINE_CKST_SMOKE_ACESSORIES_SUB_COLOR_2" "")
    (command "-layer" "n" "000_PPLINE_CKST_SMOKE_ACESSORIES_HATCH" "")
    (command "-layer" "n" "000_PPLINE_CKST_SMOKE_ACESSORIES_WIPEOUT" "")

    (command "-layer" "c" 3 "000_PPLINE_CKST_SMOKE_GLASS_FIN_MAIN_COLOR" "" ) 
    (command "-layer" "c" 1 "000_PPLINE_CKST_SMOKE_GLASS_FIN_SUB_COLOR_1" "" ) 
    (command "-layer" "c" 1 "000_PPLINE_CKST_SMOKE_GLASS_FIN_SUB_COLOR_2" "" ) 
    (command "-layer" "c" 251 "000_PPLINE_CKST_SMOKE_GLASS_FIN_HATCH" "" ) 
    (command "-layer" "c" 250 "000_PPLINE_CKST_SMOKE_GLASS_FIN_WIPEOUT" "" ) 
    
    (command "-layer" "c" 2 "000_PPLINE_CKST_SMOKE_BARRIER_MAIN_COLOR" "" ) 
    (command "-layer" "c" 1 "000_PPLINE_CKST_SMOKE_BARRIER_SUB_COLOR_1" "" ) 
    (command "-layer" "c" 1 "000_PPLINE_CKST_SMOKE_BARRIER_SUB_COLOR_2" "" ) 
    (command "-layer" "c" 251 "000_PPLINE_CKST_SMOKE_BARRIER_HATCH" "" ) 
    (command "-layer" "c" 250 "000_PPLINE_CKST_SMOKE_BARRIER_WIPEOUT" "" ) 
    
    (command "-layer" "c" 1 "000_PPLINE_CKST_SMOKE_ACESSORIES_MAIN_COLOR" "" ) 
    (command "-layer" "c" 1 "000_PPLINE_CKST_SMOKE_ACESSORIES_SUB_COLOR_1" "" ) 
    (command "-layer" "c" 1 "000_PPLINE_CKST_SMOKE_ACESSORIES_SUB_COLOR_2" "" ) 
    (command "-layer" "c" 251 "000_PPLINE_CKST_SMOKE_ACESSORIES_HATCH" "" ) 
    (command "-layer" "c" 250 "000_PPLINE_CKST_SMOKE_GLASS_FIN_WIPEOUT" "" ) 

    ;(command "-layer" "filter" "n" "G" "" "*000 - CSD_PL_*" "CSD" ""  )
    (setq MAIN-filter_1 "SMOKE")
    (setq MAIN-filter_1-1 "PPLINE_CKST_SMOKE_GLASS_FIN")
    (setq MAIN-filter_1-2 "PPLINE_CKST_SMOKE_BARRIER")
    (setq MAIN-filter_1-3 "PPLINE_CKST_SMOKE_ACESSORIES")
  
    (command "-layer" "filter" "new" "group" "" "*000_PPLINE_CKST_SMOKE_*" MAIN-filter_1 ""  )
    (command "-LAYER" "filter" "new" "group"  MAIN-filter_1 "*000_PPLINE_CKST_SMOKE_G*" MAIN-filter_1-1 "" ) 
    (command "-LAYER" "filter" "new" "group"  MAIN-filter_1 "*000_PPLINE_CKST_SMOKE_BARRIER*" MAIN-filter_1-2 "" ) 
    (command "-LAYER" "filter" "new" "group"  MAIN-filter_1 "*000_PPLINE_CKST_SMOKE_ACESSORIES*" MAIN-filter_1-3 "" ) 
  )
  (defun c:PPLINE_CKST_SMOKE_smk1_temp ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "A$C49D3615B" "A$C34021FDE" )))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (vla-put-layer ss_pre_filter_set_xx_obj_ "000_PPLINE_CKST_SMOKE_ACESSORIES_MAIN_COLOR")
        (setq ss_pre_filter_set_xx_i (+ ss_pre_filter_set_xx_i 1))
      )
    ;
  )
  (defun c:TEMP_2sk_ ()
    (if  ;pre_select_ssget_or_post_select_ssget
      (=
        (setq ss_pre_filter_set_xx_ (ssget "i"
                                          (list
                                            (cons 0 "hatch") ;type of object
                                            (cons 8 "A-DETL-GENF")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "hatch") ;type of object
                                            (cons 8 "A-DETL-GENF")   ;kind of layer
                                            ; (cons 2 "000-GRID_LINE_DYN")       ;kind of nameblock
                                            ; (cons 62 1)           ;kind of color call sign with color code index
                                          )
                                    )
        )
      )
      (sslength ss_pre_filter_set_xx_)
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (vla-put-layer ss_pre_filter_set_xx_obj_ "000_PPLINE_CKST_SMOKE_GLASS_FIN_MAIN_COLOR")
        (setq ss_pre_filter_set_xx_i (+ ss_pre_filter_set_xx_i 1))
      )
    ;
  )
;

;prototype for filter layer
  (defun c:create_main_and_sub_filter_creF1 ()
    ;presettting
      (setq main_filter_name_ (list 
                                (list "A" "A1" "A2")
                                (list "B" "B1" "B2")
                                (list "C" "C1" "C2")
                                (list "D" "D1" "D2")
                                (list "A2" "A22" "A23")
                              )
      )
      (setq wildcard_layer_name_ "*0*")
    ;
    ;preloop_and_while_main_filter
      (setq main_filter_name_i 0)
      (while (< main_filter_name_i (length main_filter_name_))
        (setq main_filter_name_val_ (nth  main_filter_name_i main_filter_name_))
        (if (= (type main_filter_name_val_) 'list)
          (progn
            ;preloop_and_while
              (command "-layer" "filter" "new" "group" "" wildcard_layer_name_ (car main_filter_name_val_) ""  )
              (setq main_filter_name_val_i 1)
              (while (< main_filter_name_val_i (length main_filter_name_val_))
                (setq main_filter_name_val_sval_ (nth  main_filter_name_val_i main_filter_name_val_))
                ; (command "-layer" "filter" "new" "group" "" wildcard_layer_name_ main_filter_name_val_sval_ ""  )    
                (command "-LAYER" "filter" "new" "group"  
                         (car main_filter_name_val_)
                         "" ;(add layer name to filter, Can use wildcard for adding)
                         main_filter_name_val_sval_ 
                         "" )
                (setq main_filter_name_val_i (+ main_filter_name_val_i 1))
              )
            ;
          )
          (command "-layer" "filter" "new" "group" "" wildcard_layer_name_ main_filter_name_val_ ""  )
        )
        (setq main_filter_name_i (+ main_filter_name_i 1))
      )
    ;
  )
  (defun c:add_layer_main_and_sub_filter_addLFilter ()
    ;presettting
      ;Note By Code_Developer
        ;fist val in list   = filter name
        ;second val in list = wildcard_layer name
        ;sub array list in filter name must be 2 val only 
      ;
        (setq main_filter_name_ (list 
                                  (list "A1" "*FIN*")
                                  (list "B2" "*HATCH*")
                                  (list "C2" "*MAIN*")
                                  (list "D1" "*SUB*")
                                  (list "A2" "")
                                  (list "A1" "HATCH")
                                )
        )
      ;
      ;
    ;
    ;preloop_and_while_main_filter
      (setq main_filter_name_i 0)
      (while (< main_filter_name_i (length main_filter_name_))
        (setq main_filter_name_val_ (nth  main_filter_name_i main_filter_name_))
        (if (and 
              (= (type main_filter_name_val_) 'list)
              (= (length main_filter_name_val_) 2)
            )
          (progn
            ;preloop_and_while
              (setq main_filter_name_val_i 0)
                (setq main_filter_name_val_sval1_ (car main_filter_name_val_))
                (setq main_filter_name_val_sval2_ (cadr main_filter_name_val_))
                ; (command "-layer" "filter" "new" "group" "" wildcard_layer_name_ main_filter_name_val_sval_ ""  )    
                (command "-layer"
                         "filter"
                         "edit"
                         main_filter_name_val_sval1_ ; (Filter name must be sensitibe case)
                         "add"
                         main_filter_name_val_sval2_ ;(add layer name to filter, Can use wildcard for adding)
                         "x" ""
                )
            ;
          )
        )
        (setq main_filter_name_i (+ main_filter_name_i 1))
      )
    ;
  )
;
;PPLINE CKST - Visibility Func
  (defun c:PPLINE-CKST-reset300layer () ;ใช้สำหรับ set layer ในบล็อก เพื่อให้เรียบร้อย
    ;selection_set_for_fillter_blk_name
      (if  ;pre_select_ssget_or_post_select_ssget
        (=
          (setq ss_pre_filter_set_xx_ (ssget "x"
                                            (list
                                              (cons 0 "INSERT,lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget "X"
                                            (list
                                              (cons 0 "INSERT,lwpolyline") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ssvis_1 (ssadd))
      (setq ssvis_1-1 (ssadd))
      (setq ssvis_2 (ssadd))
      (setq ssvis_2-1 (ssadd))
      (setq ssvis_3 (ssadd))
      (setq ssvis_4 (ssadd))
      (setq ssvis_5 (ssadd))
    ;
    ;preloop_and_while
      (setq ss_pre_filter_set_xx_i 0)
      (while (and 
              (< ss_pre_filter_set_xx_i (sslength ss_pre_filter_set_xx_))
              (= (getvar "blockeditor") 1)
            )
        (setq ss_pre_filter_set_xx_ename_ (ssname ss_pre_filter_set_xx_ ss_pre_filter_set_xx_i))
        (setq ss_pre_filter_set_xx_obj_ (vlax-ename->vla-object  ss_pre_filter_set_xx_ename_))
        (if (= (vla-get-objectname ss_pre_filter_set_xx_obj_ ) "AcDbBlockReference")
          (progn
            (cond
              (;EFname_case_1
                (or
                    (= (LM:effectivename ss_pre_filter_set_xx_obj_ ) "000 - DYNAMIC_ARRAY+COMBINE+VIEW_ASSCESSORIES_FAMELINE_AL.CELL_CELING_PANEL_300HK_@400mm_COMBINE_SET" )
                    (= (LM:effectivename ss_pre_filter_set_xx_obj_ ) "000 - DYNAMIC_ARRAY+COMBINE+VIEW_ASSCESSORIES_FAMELINE_AL.CELL_CELING_PANEL_360HK_@372mm_COMBINE_SET" )
                    (= (LM:effectivename ss_pre_filter_set_xx_obj_ ) "000 - DYNAMIC_ARRAY_ASSCESSORIES_FAMELINE_AL.CELL_CELING_PANEL_300HK-VA_@400mm_BOTTOM_VIEW" )
                )
                (progn
                  (vla-put-layer ss_pre_filter_set_xx_obj_ "A11_ALU.SOLID SHEET" )
                  (vla-put-color ss_pre_filter_set_xx_obj_ 0 )
                  (vla-put-linetype ss_pre_filter_set_xx_obj_ "byblock" )
                  (setq ssvis_1 (ssadd ss_pre_filter_set_xx_ename_ ssvis_1 ))
                  (princ "EFname_case_1")
                )
              )
              (;EFname_case_2
                (or
                    (= (LM:effectivename ss_pre_filter_set_xx_obj_ ) "000 - DYNAMIC_COMBINE+VIEW_ASSCESSORIES_FAMELINE_GALV.BRACKET_FITTING_Z-PROFILE_HR-02B_COMBINE_VIEW" )
                    (= (LM:effectivename ss_pre_filter_set_xx_obj_ ) "000 - DYNAMIC_COMBINE+VIEW_ASSCESSORIES_FAMELINE_GALV.BRACKET_FITTING_Z-PROFILE_HR-02AA_COMBINE_VIEW" )
                    (= (LM:effectivename ss_pre_filter_set_xx_obj_ ) "000 - DYNAMIC_COMBINE+VIEW_ASSCESSORIES_FAMELINE_GALV.BRACKET_FITTING_U-PROFILE_CC-01_COMBINE_VIEW" )
                    (= (LM:effectivename ss_pre_filter_set_xx_obj_ ) "000 - ASSCESSORIES_FAMELINE_GALV.BRACKET_FITTING_Z-PROFILE_HR-09B_TOP_VIEW" )
                    (= (LM:effectivename ss_pre_filter_set_xx_obj_ ) "000 - DYNAMIC_COMBINE+VIEW_ASSCESSORIES_FAMELINE_BRACKET-L-PROFILE_50x68mm.+HEX_BOLT-M5-SET_non-code_COMBINE_SET" )
                    (= (LM:effectivename ss_pre_filter_set_xx_obj_ ) "000 - DYNAMIC_COMBINE+VIEW_ASSCESSORIES_FAMELINE_BRACKET-L-PROFILE_50x45mm.+HEX_BOLT-M5-SET_non-code_COMBINE_SET" )
                )
                (progn
                  (vla-put-layer ss_pre_filter_set_xx_obj_ "001 - ASCESSORIES" )
                  (vla-put-color ss_pre_filter_set_xx_obj_ 256 )
                  (vla-put-linetype ss_pre_filter_set_xx_obj_ "byblock" )
                  (setq ssvis_2 (ssadd ss_pre_filter_set_xx_ename_ ssvis_2 ))
                  (princ "EFname_case_2")
                )
              )
              
              (;EFname_case_3
                (or
                    (= (LM:effectivename ss_pre_filter_set_xx_obj_ ) "001 - DYNAMIC REC&SSQ SHAPE SOLID_centerpoint" )
                    (= (LM:effectivename ss_pre_filter_set_xx_obj_ ) "000 - DYNAMIC_COMBINE+VIEW_ASSCESSORIES_FAMELINE_AL.EXTR._C-PROFILE_50x100mm._non-code_COMBINE_VIEW" )
                    (= (LM:effectivename ss_pre_filter_set_xx_obj_ ) "000 - DYNAMIC_COMBINE+VIEW_ASSCESSORIES_FAMELINE_AL.EXTR._REC-PROFILE_50x100mm._non-code_COMBINE_VIEW" )
                )
                (progn
                  (vla-put-layer ss_pre_filter_set_xx_obj_ "A04_TUBE SERIES" )
                  (vla-put-color ss_pre_filter_set_xx_obj_ 0 )
                  (vla-put-linetype ss_pre_filter_set_xx_obj_ "byblock" )
                  (setq ssvis_3 (ssadd ss_pre_filter_set_xx_ename_ ssvis_3 ))
                  (princ "EFname_case_3")
                )
              )
              (;EFname_case_4
                (or
                    (= (LM:effectivename ss_pre_filter_set_xx_obj_ ) "000 - DYNAMIC_LENGTH+COMBINE+VIEW_ASSCESSORIES_FAMELINE_BK-08_HANGING_SYSTEM_300HK_COMBINE_SET" )
                )
                (progn
                  (vla-put-layer ss_pre_filter_set_xx_obj_ "001 - ASCESSORIES" )
                  (vla-put-color ss_pre_filter_set_xx_obj_ 256 )
                  (vla-put-linetype ss_pre_filter_set_xx_obj_ "byblock" )
                  (setq ssvis_4 (ssadd ss_pre_filter_set_xx_ename_ ssvis_4 ))
                  (princ "EFname_case_4")
                )
              )
            )
          )
          (cond
            (;EFname_case_1-300-PLINE
              (and
                  (= (vla-get-objectname ss_pre_filter_set_xx_obj_ ) "AcDbPolyline" )
                  (= (vla-get-layer ss_pre_filter_set_xx_obj_ ) "A11_ALU.SOLID SHEET" )
                  (= (vla-get-color ss_pre_filter_set_xx_obj_ ) 256 )
              )
              (progn
                (vla-put-color ss_pre_filter_set_xx_obj_ 256 )
                (vla-put-linetype ss_pre_filter_set_xx_obj_ "byblock" )
                (setq ssvis_1-1 (ssadd ss_pre_filter_set_xx_ename_ ssvis_1-1 ))
                (princ "EFname_case_1")
              )
            )
          )
        )


        
        (setq ss_pre_filter_set_xx_i (+ ss_pre_filter_set_xx_i 1))
      )
    ;
    ;visibility process
      (if (/= (sslength ssvis_1-1) 0) 
        (progn 
          (vl-catch-all-apply 
            (function 
              (lambda () 
                (command "bvstate" "S" "1_"  )
              )
            )
          )
          (vl-catch-all-apply 
            (function 
              (lambda () 
                (command "bvshow" ssvis_1-1 "" "c"  )
              )
            )
          )
          
          
        )
      )
      (if (/= (sslength ssvis_1) 0) 
        (progn 
          (vl-catch-all-apply 
            (function 
              (lambda () 
                (command "bvstate" "S" "1_"  )
              )
            )
          )
          (vl-catch-all-apply 
            (function 
              (lambda () 
                (command "bvshow" ssvis_1 "" "c"  )
              )
            )
          )
          
          
        )
      )
      (if (/= (sslength ssvis_2) 0) 
        (progn 
          (vl-catch-all-apply (function (lambda () (command "bvstate" "S" "2_"  ) ) ) )
          (vl-catch-all-apply (function (lambda () (command "bvshow" ssvis_2 "" "c"  ) ) ) )
          (vl-catch-all-apply (function (lambda () (command "bvshow" ssvis_4 "" "c") ) ) )
          
          
          
        )
      )
      (if (/= (sslength ssvis_3) 0) 
        (progn
          (vl-catch-all-apply (function (lambda () (command "bvstate" "S" "3_"  ) ) ) )
          (vl-catch-all-apply (function (lambda () (command "bvshow" ssvis_3 "" "c"  ) ) ) )
          
          
        )
      )
      (if (/= (sslength ssvis_4) 0) 
        (progn 
          (vl-catch-all-apply (function (lambda () (command "bvstate" "S" "4_") ) ) )
          (vl-catch-all-apply (function (lambda () (command "bvshow" ssvis_4 "" "c") ) ) )
          
          
        )
      )
      (if (or (/= (sslength ssvis_1) 0) (/= (sslength ssvis_3) 0) (/= (sslength ssvis_1-1) 0) ) 
        (progn 
          (vl-catch-all-apply (function (lambda () (command "bvstate" "S" "5_"  ) ) ) )
          (vl-catch-all-apply (function (lambda () (command "bvshow" ssvis_1 "" "c"  ) ) ) )
          (vl-catch-all-apply (function (lambda () (command "bvshow" ssvis_3 "" "c"  ) ) ) )
          (if (/= (sslength ssvis_1-1) 0)
            (progn
              (vl-catch-all-apply (function (lambda () (command "bvshow" ssvis_1-1 "" "c"  ) ) ) )
            )
          )
          
        )
      )
    ;

    ;
    
    
    (command "bvstate" "S" "VisibilityState0"  )
    (command "bvshow" ss_pre_filter_set_xx_ "" "C")
  )
  (defun C:sfbz ()
    ;selection_set_for_fillter_blk_name
      (if  ;pre_select_ssget_or_post_select_ssget
        (=
          (setq ss_pre_filter_set_xx_ (ssget "i"
                                            (list
                                              (cons 0 "insert") ;type of object
                                              ; (cons 70 1) ;close assoc for lwpolyline
                                              ; (cons 8 "000 - GRID")   ;kind of layer
                                              ; (cons 2 "000-GRID_LINE_DYN")       ;kind of nameblock
                                              ; (cons 62 1)           ;kind of color call sign with color code index
                                            )
                                      )
          )
          nil
        ) 
        (progn
          (setq ss_pre_filter_set_xx_ (ssget
                                            (list
                                              (cons 0 "insert") ;type of object
                                              ; (cons 70 1) ;close assoc for lwpolyline   ;kind of layer
                                              ; (cons 2 "000-GRID_LINE_DYN")       ;kind of nameblock
                                              ; (cons 62 1)           ;kind of color call sign with color code index
                                            )
                                      )
          )
        )
        (sslength ss_pre_filter_set_xx_)
      )
    ;
    ;user_input_
      (setq namelist (list 
                      (setq block_0 (strcase (strcat "*" "" "*")) )
                      (setq block_1 (strcase (strcat "*" "Vertical Panel with Gap" "*")) )
                      (setq block_2 (strcase (strcat "*" "000 - CKST_HEADING_VAL" "*")) )
                      (setq block_3 (strcase (strcat "*" "heat,smoke" "*")) )
                      (setq block_4 (strcase (strcat "*" "Luminaire" "*")) )
                      (setq block_5 (strcase (strcat "*" "Square" "*")) )
                      (setq block_6 (strcase (strcat "*" "tray" "*")) )
                      (setq block_7 (strcase (strcat "*" "ACM" "*")) )
                      (setq block_8 (strcase (strcat "*" "extr" "*")) )
                      (setq block_9 (strcase (strcat "*" "DPA_CP_Entrance" "*")) )
                      (setq block_10 (strcase (strcat "*" "GM_Louver" "*")) )
                      (setq block_11 (strcase (strcat "*" "Louver Grill Vertical Z" "*")) )
                      (setq block_12 (strcase (strcat "*" "DPA_Curved" "*")) )
                     )
      )
      (setq choose_block_di (cond 
                              ((getint 
                                 (strcat "\nSpecify block" 
                                         "\n1 = " block_1
                                         "\n2 = " block_2
                                         "\n3 = " block_3
                                         "\n4 = " block_4
                                         "\n5 = " block_5
                                         "\n6 = " block_6
                                         "\n7 = " block_7
                                         "\n8 = "  block_8
                                         "\n9 = "  block_9
                                         "\n10 = " block_10
                                         "\n11 = " block_11
                                         "\n12 = " block_12
                                         "\n<"
                                         (rtos 
                                           (setq choose_block_di (cond 
                                                                   (choose_block_di)
                                                                   (1.0)
                                                                 )
                                           )
                                         )
                                         "> : "
                                 )
                               )
                              )
                              (choose_block_di)
                            )
      )
    ;
    
    ;preloop_and_while
      (setq ss_pre_filter_set_xx_i 0)
      (setq ss_new_sec (ssadd))
      (while (< ss_pre_filter_set_xx_i (sslength ss_pre_filter_set_xx_))  
        (setq ss_pre_filter_set_xx_ename_ (ssname  ss_pre_filter_set_xx_ ss_pre_filter_set_xx_i))
        (setq ss_pre_filter_set_xx_obj_ (vlax-ename->vla-object  ss_pre_filter_set_xx_ename_))
        (if (wcmatch (strcase (LM:effectivename ss_pre_filter_set_xx_obj_)) (nth choose_block_di namelist))
          (progn
            (setq ss_new_sec (ssadd ss_pre_filter_set_xx_ename_ ss_new_sec))
          )
        )
        (setq ss_pre_filter_set_xx_i (+ ss_pre_filter_set_xx_i 1))
      )
    ;
    (command "pselect"  ss_new_sec "" )
  )
  
  (defun C:sfbvis () ;s
    ;presetting_
      (setq wildcard_string_slot_1 (strcase (strcat "*" "Vertical Panel with Gap" "*")) )
      (setq wildcard_string_slot_2 (strcase (strcat "*" "Air Supply" "*")) )
      (setq wildcard_string_slot_3 (strcase (strcat "*" "Luminaire" "*")) )
      (setq wildcard_string_slot_4 (strcase (strcat "*" "Horizontal with Gap" "*")) )
      (setq wildcard_string_slot_5 (strcase (strcat "*" "Square" "*")) )
      (setq wildcard_string_slot_6 (strcase (strcat "*" "low" "*")) )
      (setq wildcard_string_slot_7 (strcase (strcat "*" "rec" "*")) )
      (setq wildcard_string_slot_num_ (cond 
                                        ((getint 
                                          (strcat "\nspecify get wildcard_string_slot_ \n" 
                                                    "1 = " wildcard_string_slot_1 "\n"
                                                    "2 = "wildcard_string_slot_2 "\n"
                                                    "3 = "wildcard_string_slot_3 "\n"
                                                    "4 = "wildcard_string_slot_4 "\n"
                                                    "5 = "wildcard_string_slot_5 "\n"
                                                    "6 = "wildcard_string_slot_6 "\n"
                                                    "7 = "wildcard_string_slot_7 "\n"
                                                  "<"
                                                  (rtos 
                                                    (setq wildcard_string_slot_num_ (cond 
                                                                                      (wildcard_string_slot_num_)
                                                                                      (1.0)
                                                                                    )
                                                    )
                                                  )
                                                  "> : "
                                          )
                                        )
                                        )
                                        (wildcard_string_slot_num_)
                                      )
      )
      (cond
        (;wildcard_string_slot_num__case_1
          (and
              (= wildcard_string_slot_num_ 1)
          )
          (progn
            (setq wildcard_string_ wildcard_string_slot_1)
            (princ "wildcard_string_slot_num__case_1")
          )
        )
        (;wildcard_string_slot_num__case_2
          (and
              (= wildcard_string_slot_num_ 2)
              
          )
          (progn
            (setq wildcard_string_ wildcard_string_slot_2)
            (princ "wildcard_string_slot_num__case_2")
          )
        )
        (;wildcard_string_slot_num__case_3
          (and
              (= wildcard_string_slot_num_ 3)
              
          )
          (progn
            (setq wildcard_string_ wildcard_string_slot_3)
            (princ "wildcard_string_slot_num__case_3")
          )
        )
        (;wildcard_string_slot_num__case_4
          (and
              (= wildcard_string_slot_num_ 4)
              
          )
          (progn
            (setq wildcard_string_ wildcard_string_slot_4)
            (princ "wildcard_string_slot_num__case_3")
          )
        )
        (;wildcard_string_slot_num__case_5
          (and
              (= wildcard_string_slot_num_ 5)
              
          )
          (progn
            (setq wildcard_string_ wildcard_string_slot_5)
            (princ "wildcard_string_slot_num__case_3")
          )
        )
        (;wildcard_string_slot_num__case_6
          (and
              (= wildcard_string_slot_num_ 6)
              
          )
          (progn
            (setq wildcard_string_ wildcard_string_slot_6)
            (princ "wildcard_string_slot_num__case_6")
          )
        )
        (;wildcard_string_slot_num__case_7
          (and
              (= wildcard_string_slot_num_ 7)
              
          )
          (progn
            (setq wildcard_string_ wildcard_string_slot_7)
            (princ "wildcard_string_slot_num__case_7")
          )
        )

      )
    ;
    
    ;selection_set_for_fillter_blk_name
      (if  ;pre_select_ssget_or_post_select_ssget
        (=
          (setq ss_pre_filter_set_xx_ (ssget "x"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ; (setq wildcard_string_ ;Get-string by keep previous value ; old method
      ;     (if
      ;       (or
      ;         (/= (setq wildcard_string_val (getstring (strcat "\nSpecify Pattern name <" (if wildcard_string_ wildcard_string_ "") ">: ") ) ) "" )
      ;       )
      ;         (progn
      ;           (setq wildcard_string_ wildcard_string_val)
      ;           (setq wildcard_string_keep_val_ wildcard_string_val)
      ;         )
      ;       (setq wildcard_string_val wildcard_string_keep_val_)
      ;     )
    ; )
    
    
    ;preloop_and_while
      (setq ss_pre_filter_set_xx_i 0)
      (setq new_pre_filter_set_xx_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))

        (if (wcmatch (strcase (LM:effectivename ss_pre_filter_set_xx_obj_)) wildcard_string_)
          (progn
            (setq new_pre_filter_set_xx_  (ssadd ss_pre_filter_set_xx_ename_ new_pre_filter_set_xx_))
          )
        )
        (setq ss_pre_filter_set_xx_i (+ ss_pre_filter_set_xx_i 1))
      )
    ;
    (command "bvhide"  new_pre_filter_set_xx_ "" "C" )

  )
;


(defun c:PPLINE-CKST_SELDIM ()
  ;selection_set_for_fillter_blk_name
    (if  ;pre_select_ssget_or_post_select_ssget
      (=
        (setq ss_pre_filter_set_xx_ (ssget "i"
                                          (list
                                            (cons 0 "INSERT,DIMENSION,LINE,MTEXT") ;type of object
                                            (cons 8 "S-GRID,S-GRID-IDEN,_ _ A-DETL-OPENING,A-ANNO-DIMS,A-DETL")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,DIMENSION,LINE,MTEXT") ;type of object
                                            (cons 8 "S-GRID,S-GRID-IDEN,_ _ A-DETL-OPENING,A-ANNO-DIMS,A-DETL")   ;kind of layer
                                            ; (cons 2 "000-GRID_LINE_DYN")       ;kind of nameblock
                                            ; (cons 62 1)           ;kind of color call sign with color code index
                                          )
                                    )
        )
      )
      (sslength ss_pre_filter_set_xx_)
    )
  ;
  (command "pselect"  ss_pre_filter_set_xx_ "" )
  
)
(defun c:PPLINE-CKST_SELDIM2 ()
  ;selection_set_for_fillter_blk_name
    (if  ;pre_select_ssget_or_post_select_ssget
      (=
        (setq ss_pre_filter_set_xx_ (ssget "i"
                                          (list
                                            (cons 0 "DIMENSION") ;type of object
                                            ; (cons 8 "S-GRID,S-GRID-IDEN,_ _ A-DETL-OPENING,A-ANNO-DIMS")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "DIMENSION") ;type of object
                                            ; (cons 8 "S-GRID,S-GRID-IDEN,_ _ A-DETL-OPENING,A-ANNO-DIMS")   ;kind of layer
                                            ; (cons 2 "000-GRID_LINE_DYN")       ;kind of nameblock
                                            ; (cons 62 1)           ;kind of color call sign with color code index
                                          )
                                    )
        )
      )
      (sslength ss_pre_filter_set_xx_)
    )
  ;
  (command "pselect"  ss_pre_filter_set_xx_ "" )
  
)




(defun c:select_dynamic_block_seldyn ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq sss_sss_ (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (if (= (vla-get-isdynamicblock ss_pre_filter_set_xx_obj_) :vlax-true)
        (progn
          (setq sss_sss_ (ssadd ss_pre_filter_set_xx_ename_ sss_sss_))
        )
      )
      (setq ss_pre_filter_set_xx_i (+ ss_pre_filter_set_xx_i 1))
    )
  ;
    (command "pselect"   sss_sss_ "" )
  ;
)
(defun c:select_not_dynamic_block_ ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq sss_sss_ (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (if (/= (vla-get-isdynamicblock ss_pre_filter_set_xx_obj_) :vlax-true)
        (progn
          (setq sss_sss_ (ssadd ss_pre_filter_set_xx_ename_ sss_sss_))
        )
      )
      (setq ss_pre_filter_set_xx_i (+ ss_pre_filter_set_xx_i 1))
    )
  ;
    (command "pselect"   sss_sss_ "" )
  ;
)



(defun c:FLdim ()
  ;presetting
    ; (command "-layer" "n" "000 - D I M" "")
    ; (command "-layer" "c" 1 "000 - D I M" "" ) 
    ; (command "-layer" "c" 251 "000 - GRID" "" ) 
    ; (command "-layer" "c" 3 "001 - ASCESSORIES" "" ) 
    ; (command "-layer" "c" 251 "008 - LIGHTING" "" ) 
    ; (command "-layer" "c" 251 "A04_TUBE SERIES" "" ) 
    ; (command "-layer" "c" 251 "A11_ALU.SOLID SHEET" "" ) 
  ;
  ;selection_set_for_fillter_blk_name
    (if  ;pre_select_ssget_or_post_select_ssget
      (=
        (setq ss_pre_filter_set_xx_ (ssget "i"
                                          (list
                                            (cons 0 "DIMENSION") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "DIMENSION") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_put_color (vla-put-color ss_pre_filter_set_xx_obj_ 256)) ;0 = bylock, 256 = bylayer
      
      (if (= (TA:if_found_layer_ "000 - 0_SYM_DWG_DIMS_MAIN_COLOR_251" ) T)
        (progn
          (setq ss_pre_filter_set_xx_obj_put_layer (vla-put-layer ss_pre_filter_set_xx_obj_ "000 - 0_SYM_DWG_DIMS_MAIN_COLOR_251"))
        )
        (alert "Layer 000 - 0_SYM_DWG_DIMS_MAIN_COLOR_251 not found. Please create the layer first."  )
      )
       ;by_string_name_layer
       
      
      

      
      (setq ss_pre_filter_set_xx_i (+ ss_pre_filter_set_xx_i 1))
    )
  ;
  ;selection_set_for_fillter_blk_name
    (if  ;pre_select_ssget_or_post_select_ssget
      (=
        (setq ss_pre_filter_set_xx_ (ssget "x"
                                          (list
                                            (cons 0 "insert") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget "X"
                                          (list
                                            (cons 0 "insert") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_ ss_pre_filter_set_xx_ "000-GRID_LINE_DYN_V2"))
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_put_color (vla-put-color ss_pre_filter_set_xx_obj_ 256)) ;0 = bylock, 256 = bylayer
      (setq ss_pre_filter_set_xx_obj_put_color (vla-put-linetype ss_pre_filter_set_xx_obj_ "TA_GL_000.90000")) ;0 = bylock, 256 = bylayer
      
      
       ;by_string_name_layer
       
      
      

      
      (setq ss_pre_filter_set_xx_i (+ ss_pre_filter_set_xx_i 1))
    )
  ;
)
(defun c:CKdim ()
  ;presetting
    (command "-layer" "n" "000 - D I M" "")
    (command "-layer" "c" 1 "000 - D I M" "" ) 
    (command "-layer" "c" 251 "000 - GRID" "" ) 
    ; (command "-layer" "c" 3 "001 - ASCESSORIES" "" ) 
    ; (command "-layer" "c" 251 "008 - LIGHTING" "" ) 
    ; (command "-layer" "c" 251 "A04_TUBE SERIES" "" ) 
    ; (command "-layer" "c" 251 "A11_ALU.SOLID SHEET" "" ) 
  ;
  ;selection_set_for_fillter_blk_name
    (if  ;pre_select_ssget_or_post_select_ssget
      (=
        (setq ss_pre_filter_set_xx_ (ssget "i"
                                          (list
                                            (cons 0 "DIMENSION") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "DIMENSION") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_put_color (vla-put-color ss_pre_filter_set_xx_obj_ 256)) ;0 = bylock, 256 = bylayer
      
      
      (setq ss_pre_filter_set_xx_obj_put_layer (vla-put-layer ss_pre_filter_set_xx_obj_ "000 - D I M")) ;by_string_name_layer
       
      
      

      
      (setq ss_pre_filter_set_xx_i (+ ss_pre_filter_set_xx_i 1))
    )
  ;
  ;selection_set_for_fillter_blk_name
    (if  ;pre_select_ssget_or_post_select_ssget
      (=
        (setq ss_pre_filter_set_xx_ (ssget "x"
                                          (list
                                            (cons 0 "insert") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget "X"
                                          (list
                                            (cons 0 "insert") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_v2_ ss_pre_filter_set_xx_ (list "000-GRID_LINE_DYN_V2" "000-GRID_LINE_DYN_V3")))
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_put_color (vla-put-color ss_pre_filter_set_xx_obj_ 256)) ;0 = bylock, 256 = bylayer
      (setq ss_pre_filter_set_xx_obj_put_color (vla-put-linetype ss_pre_filter_set_xx_obj_ "TA_GL_000.90000")) ;0 = bylock, 256 = bylayer
      
      
       ;by_string_name_layer
       
      
      

      
      (setq ss_pre_filter_set_xx_i (+ ss_pre_filter_set_xx_i 1))
    )
  ;
)
(defun c:CKgen ()
  ;presetting
    (command "-layer" "n" "000 - D I M" "")
    (command "-layer" "c" 251 "000 - D I M" "" ) 
    (command "-layer" "c" 251 "000 - GRID" "" ) 
    ; (command "-layer" "c" 3 "001 - ASCESSORIES" "" ) 
    ; (command "-layer" "c" 251 "008 - LIGHTING" "" ) 
    ; (command "-layer" "c" 251 "A04_TUBE SERIES" "" ) 
    ; (command "-layer" "c" 251 "A11_ALU.SOLID SHEET" "" ) 
  ;
  ;selection_set_for_fillter_blk_name
    (if  ;pre_select_ssget_or_post_select_ssget
      (=
        (setq ss_pre_filter_set_xx_ (ssget "x"
                                          (list
                                            (cons 0 "DIMENSION") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget 
                                          (list
                                            (cons 0 "DIMENSION") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_put_color (vla-put-color ss_pre_filter_set_xx_obj_ 1)) ;0 = bylock, 256 = bylayer
      
      (if (= (vla-get-arrowhead1block ss_pre_filter_set_xx_obj_  ) "Oblique")
        (progn
          (vla-put-arrowhead1block ss_pre_filter_set_xx_obj_ "ArchTick" )
        )
      )
      (if (= (vla-get-arrowhead2block ss_pre_filter_set_xx_obj_ ) "Oblique")
        (progn
          (vla-put-arrowhead2block ss_pre_filter_set_xx_obj_ "ArchTick" )
        )
      )
      (vla-put-ArrowheadSize  ss_pre_filter_set_xx_obj_ 0.2 )
      (vla-put-textcolor  ss_pre_filter_set_xx_obj_ 3 )
      ; (vla-put-linearscalefactor  ss_pre_filter_set_xx_obj_ -10 )
      
      (setq ss_pre_filter_set_xx_obj_put_layer (vla-put-layer ss_pre_filter_set_xx_obj_ "000 - D I M")) ;by_string_name_layer
       
      
      

      
      (setq ss_pre_filter_set_xx_i (+ ss_pre_filter_set_xx_i 1))
    )
  ;
  ;selection_set_for_fillter_blk_name
    (if  ;pre_select_ssget_or_post_select_ssget
      (=
        (setq ss_pre_filter_set_xx_ (ssget "x"
                                          (list
                                            (cons 0 "insert") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget "X"
                                          (list
                                            (cons 0 "insert") ;type of object
                                            (cons 410 (getvar "CTAB"))
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_ ss_pre_filter_set_xx_ "000-GRID_LINE_DYN_V2"))
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_put_color (vla-put-color ss_pre_filter_set_xx_obj_ 256)) ;0 = bylock, 256 = bylayer
      (setq ss_pre_filter_set_xx_obj_put_color (vla-put-linetype ss_pre_filter_set_xx_obj_ "TA_GL_000.90000")) ;0 = bylock, 256 = bylayer
      
      
       ;by_string_name_layer
       
      
      

      
      (setq ss_pre_filter_set_xx_i (+ ss_pre_filter_set_xx_i 1))
    )
  ;
)




(defun c:loadlisp () 
  (cond
    ((and 
       (= (getenv "COMPUTERNAME") "NONGSAISUEARAIH")
       (= (getenv "USERNAME") "popul")
     )
      (progn
        (setq Er-msg_ (vl-catch-all-apply (function (lambda () (load "C:/TA/TA_COMPELETE/COMPELETE NEXT 2025/Z73-Tranference_Autocad-Excel_data.lsp") ) ) ) )
        (setq Er-msg_1 (vl-catch-all-apply (function (lambda () (load "C:/TA/TA_COMPELETE/COMPELETE NEXT 2025/REWORK DIM/z62x_REWORK_DIMENSION_REV02.lsp") ) ) ) )
        (setq Er-msg_1 (vl-catch-all-apply (function (lambda () (load "C:/TA/TA_COMPELETE/COMPELETE IN COMPELETE/SFB_FINDING_SPECFILY_NAME_BLOCK.lsp") ) ) ) )
        (setq Er-msg_1 (vl-catch-all-apply (function (lambda () (load "C:/TA/TA_COMPELETE/000 - automation_cad.lsp") ) ) ) )
        (setq Er-msg_1 (vl-catch-all-apply (function (lambda () (load "C:/TA/TA_COMPELETE/000 - FOR_CREATE_LAYER_.lsp") ) ) ) )
        (setq Er-msg_1 (vl-catch-all-apply (function (lambda () (load "C:/TA/TA_COMPELETE/GPT CODE/TA_LAYER_TRANSFER/Maviewport.lsp") ) ) ) )
        (setq Er-msg_1 (vl-catch-all-apply (function (lambda () (load "C:/TA/TA_COMPELETE/GPT CODE/TA_LAYER_TRANSFER/Maviewport.lsp") ) ) ) )
      )
    )
    ((and 
       (= (getenv "COMPUTERNAME") "DESKTOP-FSRT7SI")
       (= (getenv "USERNAME") "Admin")
     )
      (progn
        (setq Er-msg_ (vl-catch-all-apply (function (lambda () (load "C:/Users/Admin/Documents/GitHub/TA_COMPELETE/COMPELETE NEXT 2025/Z73-Tranference_Autocad-Excel_data.lsp") ) ) ) )
        (setq Er-msg_1 (vl-catch-all-apply (function (lambda () (load "C:/Users/Admin/Documents/GitHub/TA_COMPELETE/COMPELETE NEXT 2025/REWORK DIM/z62x_REWORK_DIMENSION_REV02.lsp") ) ) ) )
        (setq Er-msg_1 (vl-catch-all-apply (function (lambda () (load "C:/Users/Admin/Documents/GitHub/TA_COMPELETE/COMPELETE IN COMPELETE/SFB_FINDING_SPECFILY_NAME_BLOCK.lsp") ) ) ) )
        (setq Er-msg_1 (vl-catch-all-apply (function (lambda () (load "C:/Users/Admin/Documents/GitHub/TA_COMPELETE/000 - FOR_CREATE_LAYER_.lsp") ) ) ) )
      )
    )
    ((and 
       (= (getenv "COMPUTERNAME") "DESKTOP-VNKD8FJ")
       (= (getenv "USERNAME") "tawan.t")
     )
      (progn 
        (setq Er-msg_ (vl-catch-all-apply (function (lambda () (load "C:/Users/tawan.t/Documents/GitHub/TA_COMPELETE/COMPELETE NEXT 2025/Z73-Tranference_Autocad-Excel_data.lsp") ) ) ) )
        (setq Er-msg_1 (vl-catch-all-apply (function (lambda () (load "C:/Users/tawan.t/Documents/GitHub/TA_COMPELETE/COMPELETE NEXT 2025/REWORK DIM/z62x_REWORK_DIMENSION_REV02.lsp") ) ) ) )
        (setq Er-msg_1 (vl-catch-all-apply (function (lambda () (load "C:/Users/tawan.t/Documents/GitHub/TA_COMPELETE/COMPELETE IN COMPELETE/SFB_FINDING_SPECFILY_NAME_BLOCK.lsp") ) ) ) )
        (setq Er-msg_1 (vl-catch-all-apply (function (lambda () (load "C:/Users/tawan.t/Documents/GitHub/TA_COMPELETE/000 - FOR_CREATE_LAYER_.lsp") ) ) ) )
        (setq Er-msg_1 (vl-catch-all-apply (function (lambda () (load "C:/Users/tawan.t/Documents/GitHub/TA_COMPELETE/000 - automation_cad.lsp") ) ) ) )
        (setq Er-msg_1 (vl-catch-all-apply (function (lambda () (load "C:/Users/tawan.t/Documents/GitHub/TA_COMPELETE/COMPELETE IN COMPELETE/PPLINE TEST AUTOPLOT.lsp") ) ) ) )
        (setq Er-msg_1 (vl-catch-all-apply (function (lambda () (load "C:/Users/tawan.t/Documents/GitHub/TA_COMPELETE/z00x_TA_standard_sun_func_and_MAIN.lsp") ) ) ) )
      )
    )
    ((and 
       (= (getenv "COMPUTERNAME") "NONGSAISUEARAI")
       (= (getenv "USERNAME") "popul")
     )
      (progn 
        (setq Er-msg_1 (vl-catch-all-apply (function (lambda () (load "C:/TA compelete github/TA_COMPELETE/z00x_TA_standard_sun_func_and_MAIN.lsp") ) ) ) )
        (setq Er-msg_1 (vl-catch-all-apply (function (lambda () (load "C:/TA compelete github/TA_COMPELETE/COMPELETE NEXT 2025/Z73-Tranference_Autocad-Excel_data.lsp") ) ) ) )
        (setq Er-msg_1 (vl-catch-all-apply (function (lambda () (load "C:/TA compelete github/TA_COMPELETE/COMPELETE NEXT 2025/REWORK DIM/z62x_REWORK_DIMENSION_REV02.lsp") ) ) ) )
        (setq Er-msg_1 (vl-catch-all-apply (function (lambda () (load "C:/TA compelete github/TA_COMPELETE/COMPELETE IN COMPELETE/SFB_FINDING_SPECFILY_NAME_BLOCK.lsp") ) ) ) )
        (setq Er-msg_1 (vl-catch-all-apply (function (lambda () (load "C:/TA compelete github/TA_COMPELETE/000 - FOR_CREATE_LAYER_.lsp") ) ) ) )
        (setq Er-msg_1 (vl-catch-all-apply (function (lambda () (load "C:/TA compelete github/TA_COMPELETE/000 - automation_cad.lsp") ) ) ) )
        (setq Er-msg_1 (vl-catch-all-apply (function (lambda () (load "C:/TA compelete github/TA_COMPELETE/COMPELETE IN COMPELETE/PPLINE TEST AUTOPLOT.lsp") ) ) ) )
        (setq Er-msg_1 (vl-catch-all-apply (function (lambda () (load "C:/TA compelete github/TA_COMPELETE/GPT CODE/TA_LAYER_TRANSFER/Maviewport.lsp") ) ) ) )
        (setq Er-msg_1 (vl-catch-all-apply (function (lambda () (load "C:/TA compelete github/TA_COMPELETE/GPT CODE/TA_LAYER_TRANSFER/Maviewport.lsp") ) ) ) )
        
        
        
      )
    )
  )
)
(defun c:loadline ()
  (cond
    ((and 
          (= (getenv "COMPUTERNAME") "NONGSAISUEARAIH")
          (= (getenv "USERNAME") "popul")
        )
      (progn
        ; (setq Er-msg_1 (vl-catch-all-apply (function (lambda () (load "C:/TA compelete github/TA_COMPELETE/CC11x_ADD_LINETYPE.lsp") ) ) ) )
        (setq Er-msg_1 (vl-catch-all-apply (function (lambda () (load "C:/TA/TA_COMPELETE/CC11x_ADD_LINETYPE.lsp") ) ) ) )
        
      )
    )
    ((and 
       (= (getenv "COMPUTERNAME") "DESKTOP-FSRT7SI")
       (= (getenv "USERNAME") "Admin")
     )
      (progn
        (setq Er-msg_1 (vl-catch-all-apply (function (lambda () (load "C:/Users/Admin/Documents/GitHub/TA_COMPELETE/CC11x_ADD_LINETYPE.lsp") ) ) ) )
      )
    )
    ((and 
       (= (getenv "COMPUTERNAME") "DESKTOP-VNKD8FJ")
       (= (getenv "USERNAME") "tawan.t")
     )
      (progn 
        (setq Er-msg_ (vl-catch-all-apply (function (lambda () (load "C:/Users/tawan.t/Documents/GitHub/TA_COMPELETE/CC11x_ADD_LINETYPE.lsp") ) ) ) )

      )
    )
  )
)

  
  




;PP LINE Replace EXTR
  ; (defun c:mvxextr ()
    
  ;   (setq polar_move_val 12.5)
  ;   (setvar "osmode" 0)
  ;   (setq ss_ename_ (car (entsel "specify Object")))
  ;   (setq ss_obj_ (vlax-ename->vla-object ss_ename_))
  ;   (setq ss_obj_extr_boundingbox_ (TA:get-visible-boundingbox ss_obj_ ))
  ;   (command "erase" "l" "")
  ;   (command "zoom" "ob" ss_ename_ "")

  ;   ;selection_set_for_fillter_blk_name
  ;       (if  ;pre_select_ssget_or_post_select_ssget
  ;         (=
  ;           (setq ss_pre_filter_set_xx_ (ssget "i"
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;           nil
  ;         )
  ;         (progn
  ;           (setq ss_pre_filter_set_xx_ (ssget "c" (car (car ss_obj_extr_boundingbox_)) (caddr (car ss_obj_extr_boundingbox_))
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;         )
  ;         (sslength ss_pre_filter_set_xx_)
  ;       )
  ;   ;
  ;   (command "zoom" "p" )
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object  ss_pre_filter_set_xx_ename_))
  ;       (if (or
  ;             (= (LM:effectivename ss_pre_filter_set_xx_obj_ ) "000 - DYNAMIC_COMBINE+VIEW_ASSCESSORIES_FAMELINE_BRACKET-L-PROFILE_50x68mm.+HEX_BOLT-M5-SET_non-code_COMBINE_SET")
  ;             (= (LM:effectivename ss_pre_filter_set_xx_obj_ ) "000 - DYNAMIC_COMBINE+VIEW_ASSCESSORIES_FAMELINE_BRACKET-L-PROFILE_50x45mm.+HEX_BOLT-M5-SET_non-code_COMBINE_SET")
  ;             (= (LM:effectivename ss_pre_filter_set_xx_obj_ ) "000 - DYNAMIC_COMBINE+VIEW_ASSCESSORIES_FAMELINE_AL.EXTR._REC-PROFILE_50x100mm._non-code_COMBINE_VIEW")
  ;             (= (LM:effectivename ss_pre_filter_set_xx_obj_ ) "000 - DYNAMIC_COMBINE+VIEW_ASSCESSORIES_FAMELINE_AL.EXTR._C-PROFILE_50x100mm._non-code_COMBINE_VIEW")
  ;           )
  ;         (progn
  ;           (TA:move_axis_insertionpoint ss_pre_filter_set_xx_obj_ "x" polar_move_val )
  ;         )
  ;       )
        
  ;       (setq ss_pre_filter_set_xx_i (+ ss_pre_filter_set_xx_i 1))
  ;     )
  ;   ;
  ;   (setq polar_move_val 12.5)
  ;   (setq ss_ename_ (car (entsel "specify Object")))
  ;   (setq ss_obj_ (vlax-ename->vla-object ss_ename_))
  ;   (setq ss_obj_extr_boundingbox_ (TA:get-visible-boundingbox ss_obj_ ))
  ;   (command "erase" "l" "")
  ;   (command "zoom" "ob" ss_ename_ "")
  ;   ;selection_set_for_fillter_blk_name
  ;       (if  ;pre_select_ssget_or_post_select_ssget
  ;         (=
  ;           (setq ss_pre_filter_set_xx_ (ssget "i"
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;           nil
  ;         )
  ;         (progn
  ;           (setq ss_pre_filter_set_xx_ (ssget "c" (car (car ss_obj_extr_boundingbox_)) (caddr (car ss_obj_extr_boundingbox_))
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;         )
  ;         (sslength ss_pre_filter_set_xx_)
  ;       )
  ;   ;
  ;   (command "zoom" "p" )
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object  ss_pre_filter_set_xx_ename_))
  ;       (if (or
  ;             (= (LM:effectivename ss_pre_filter_set_xx_obj_ ) "000 - DYNAMIC_COMBINE+VIEW_ASSCESSORIES_FAMELINE_BRACKET-L-PROFILE_50x68mm.+HEX_BOLT-M5-SET_non-code_COMBINE_SET")
  ;             (= (LM:effectivename ss_pre_filter_set_xx_obj_ ) "000 - DYNAMIC_COMBINE+VIEW_ASSCESSORIES_FAMELINE_BRACKET-L-PROFILE_50x45mm.+HEX_BOLT-M5-SET_non-code_COMBINE_SET")
  ;             (= (LM:effectivename ss_pre_filter_set_xx_obj_ ) "000 - DYNAMIC_COMBINE+VIEW_ASSCESSORIES_FAMELINE_AL.EXTR._REC-PROFILE_50x100mm._non-code_COMBINE_VIEW")
  ;             (= (LM:effectivename ss_pre_filter_set_xx_obj_ ) "000 - DYNAMIC_COMBINE+VIEW_ASSCESSORIES_FAMELINE_AL.EXTR._C-PROFILE_50x100mm._non-code_COMBINE_VIEW")
  ;           )
  ;         (progn
  ;           (TA:move_axis_insertionpoint ss_pre_filter_set_xx_obj_ "x" (- polar_move_val) )
  ;         )
  ;       )
        
  ;       (setq ss_pre_filter_set_xx_i (+ ss_pre_filter_set_xx_i 1))
  ;     )
  ;   ;
  ;   (setvar "osmode" 1215)


  ; )
  ; (defun c:mvyextr ()
    
  ;   (setq polar_move_val 12.5)
  ;   (setvar "osmode" 0)
  ;   (setq ss_ename_ (car (entsel "specify Object")))
  ;   (setq ss_obj_ (vlax-ename->vla-object ss_ename_))
  ;   (setq ss_obj_extr_boundingbox_ (TA:get-visible-boundingbox ss_obj_ ))
  ;   (command "erase" "l" "")
  ;   (command "zoom" "ob" ss_ename_ "")

  ;   ;selection_set_for_fillter_blk_name
  ;       (if  ;pre_select_ssget_or_post_select_ssget
  ;         (=
  ;           (setq ss_pre_filter_set_xx_ (ssget "i"
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;           nil
  ;         )
  ;         (progn
  ;           (setq ss_pre_filter_set_xx_ (ssget "c" (car (car ss_obj_extr_boundingbox_)) (caddr (car ss_obj_extr_boundingbox_))
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;         )
  ;         (sslength ss_pre_filter_set_xx_)
  ;       )
  ;   ;
  ;   (command "zoom" "p" )
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object  ss_pre_filter_set_xx_ename_))
  ;       (if (or
  ;             (= (LM:effectivename ss_pre_filter_set_xx_obj_ ) "000 - DYNAMIC_COMBINE+VIEW_ASSCESSORIES_FAMELINE_BRACKET-L-PROFILE_50x68mm.+HEX_BOLT-M5-SET_non-code_COMBINE_SET")
  ;             (= (LM:effectivename ss_pre_filter_set_xx_obj_ ) "000 - DYNAMIC_COMBINE+VIEW_ASSCESSORIES_FAMELINE_BRACKET-L-PROFILE_50x45mm.+HEX_BOLT-M5-SET_non-code_COMBINE_SET")
  ;             (= (LM:effectivename ss_pre_filter_set_xx_obj_ ) "000 - DYNAMIC_COMBINE+VIEW_ASSCESSORIES_FAMELINE_AL.EXTR._REC-PROFILE_50x100mm._non-code_COMBINE_VIEW")
  ;             (= (LM:effectivename ss_pre_filter_set_xx_obj_ ) "000 - DYNAMIC_COMBINE+VIEW_ASSCESSORIES_FAMELINE_AL.EXTR._C-PROFILE_50x100mm._non-code_COMBINE_VIEW")
  ;           )
  ;         (progn
  ;           (TA:move_axis_insertionpoint ss_pre_filter_set_xx_obj_ "y" polar_move_val )
  ;         )
  ;       )
        
  ;       (setq ss_pre_filter_set_xx_i (+ ss_pre_filter_set_xx_i 1))
  ;     )
  ;   ;
  ;   (setq polar_move_val 12.5)
  ;   (setq ss_ename_ (car (entsel "specify Object")))
  ;   (setq ss_obj_ (vlax-ename->vla-object ss_ename_))
  ;   (setq ss_obj_extr_boundingbox_ (TA:get-visible-boundingbox ss_obj_ ))
  ;   (command "erase" "l" "")
  ;   (command "zoom" "ob" ss_ename_ "")
  ;   ;selection_set_for_fillter_blk_name
  ;       (if  ;pre_select_ssget_or_post_select_ssget
  ;         (=
  ;           (setq ss_pre_filter_set_xx_ (ssget "i"
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;           nil
  ;         )
  ;         (progn
  ;           (setq ss_pre_filter_set_xx_ (ssget "c" (car (car ss_obj_extr_boundingbox_)) (caddr (car ss_obj_extr_boundingbox_))
  ;                                             (list
  ;                                               (cons 0 "INSERT") ;type of object
  ;                                               ; (cons 8 "000 - GRID")   ;kind of layer
  ;                                               ; (cons 2 "000-GRID_LINE_DYN")       ;kind of nameblock
  ;                                               ; (cons 62 1)           ;kind of color call sign with color code index
  ;                                             )
  ;                                       )
  ;           )
  ;         )
  ;         (sslength ss_pre_filter_set_xx_)
  ;       )
  ;   ;
  ;   (command "zoom" "p" )
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object  ss_pre_filter_set_xx_ename_))
  ;       (if (or
  ;             (= (LM:effectivename ss_pre_filter_set_xx_obj_ ) "000 - DYNAMIC_COMBINE+VIEW_ASSCESSORIES_FAMELINE_BRACKET-L-PROFILE_50x68mm.+HEX_BOLT-M5-SET_non-code_COMBINE_SET")
  ;             (= (LM:effectivename ss_pre_filter_set_xx_obj_ ) "000 - DYNAMIC_COMBINE+VIEW_ASSCESSORIES_FAMELINE_BRACKET-L-PROFILE_50x45mm.+HEX_BOLT-M5-SET_non-code_COMBINE_SET")
  ;             (= (LM:effectivename ss_pre_filter_set_xx_obj_ ) "000 - DYNAMIC_COMBINE+VIEW_ASSCESSORIES_FAMELINE_AL.EXTR._REC-PROFILE_50x100mm._non-code_COMBINE_VIEW")
  ;             (= (LM:effectivename ss_pre_filter_set_xx_obj_ ) "000 - DYNAMIC_COMBINE+VIEW_ASSCESSORIES_FAMELINE_AL.EXTR._C-PROFILE_50x100mm._non-code_COMBINE_VIEW")
  ;           )
  ;         (progn
  ;           (TA:move_axis_insertionpoint ss_pre_filter_set_xx_obj_ "y" (- polar_move_val) )
  ;         )
  ;       )
        
  ;       (setq ss_pre_filter_set_xx_i (+ ss_pre_filter_set_xx_i 1))
  ;     )
  ;   ;
  ;   (setvar "osmode" 1215)


  ; )
  ; (defun c:repall ()
  ;   (setvar "CMDECHO" 0)
  ;   ;presetting
  ;     (setq wildcard_string_1 (strcase (strcat "*" 
  ;                                             "air supply" 
  ;                                             "*"
  ;                                     )
  ;                           ) 
  ;     )
  ;     (setq wildcard_string_2 (strcase (strcat "*" 
  ;                                             "luminaire" 
  ;                                             "*"
  ;                                     )
  ;                           ) 
  ;     )
  ;     (setq wildcard_string_3 (strcase (strcat "*" 
  ;                                             "Horizontal with Gap" 
  ;                                             "*"
  ;                                     )
  ;                           ) 
  ;     )
  ;   ;
  ;   ;Extr process type
  ;     (setq Extr_EFNAME_ ;Get-string by keep previous value
  ;         (if
  ;           (or
  ;             (/= (setq Extr_EFNAME_val (getstring (strcat "\nSpecify EXTR. type <" (if Extr_EFNAME_ Extr_EFNAME_ "") ">: ") ) ) "" )
  ;           )
  ;             (progn
  ;               (setq Extr_EFNAME_ Extr_EFNAME_val)
  ;               (setq Extr_EFNAME_keep_val_ Extr_EFNAME_val)
  ;             )
  ;           (setq Extr_EFNAME_val Extr_EFNAME_keep_val_)
  ;         )
  ;     )
  ;     (if 
  ;       (and 
  ;         (/= (strcase Extr_EFNAME_) "R")
  ;         (/= (strcase Extr_EFNAME_) "C")
  ;       )
  ;       (progn
  ;         (alert "EXTR process error")
  ;       )
  ;     )
  ;   ;
  ;   ;selection_set_for_fillter_blk_name
  ;     (if  ;pre_select_ssget_or_post_select_ssget
  ;       (=
  ;         (setq ss_pre_filter_set_xx_ (ssget "i"
  ;                                           (list
  ;                                             ; (cons 0 "INSERT") ;type of object
  ;                                             ; (cons 8 "000 - GRID")   ;kind of layer
  ;                                             ; (cons 2 "000-GRID_LINE_DYN")       ;kind of nameblock
  ;                                             ; (cons 62 1)           ;kind of color call sign with color code index
  ;                                           )
  ;                                     )
  ;         )
  ;         nil
  ;       )
  ;       (progn
  ;         (setq ss_pre_filter_set_xx_ (ssget
  ;                                           (list
  ;                                             ; (cons 0 "INSERT") ;type of object
  ;                                             ; (cons 8 "000 - GRID")   ;kind of layer
  ;                                             ; (cons 2 "000-GRID_LINE_DYN")       ;kind of nameblock
  ;                                             ; (cons 62 1)           ;kind of color call sign with color code index
  ;                                           )
  ;                                     )
  ;         )
  ;       )
  ;       (sslength ss_pre_filter_set_xx_)
  ;     )
  ;   ;
    
  ;   ;preloop_and_while
  ;     (setq ss_pre_filter_set_xx_i 0)
  ;     (while (< ss_pre_filter_set_xx_i (sslength ss_pre_filter_set_xx_))
  ;       (setq ss_pre_filter_set_xx_ename_ (ssname ss_pre_filter_set_xx_ ss_pre_filter_set_xx_i))
  ;       (setq ss_pre_filter_set_xx_obj_ (vlax-ename->vla-object  ss_pre_filter_set_xx_ename_))
  ;       (if (= (vla-get-objectname ss_pre_filter_set_xx_obj_) "AcDbBlockReference")
  ;         (progn
  ;           (setq ss_pre_filter_set_xx_obj_rotation (vla-get-rotation ss_pre_filter_set_xx_obj_))
  ;           (cond
  ;             ((and  ;"000 - DYNAMIC_ARRAY+COMBINE+VIEW_ASSCESSORIES_PLAN_SUPPLY_AIR_REC.1600x175mm_COMBINE_SET"
  ;                   (= (vla-get-objectname ss_pre_filter_set_xx_obj_) 
  ;                      "AcDbBlockReference"
  ;                   )
  ;                   (wcmatch (strcase (LM:effectivename ss_pre_filter_set_xx_obj_)) 
  ;                            wildcard_string_1
  ;                   )
  ;              ) 
  ;               (progn 
  ;                 (setq new_boundingbox_ (TA:get-visible-boundingbox 
  ;                                          ss_pre_filter_set_xx_obj_
  ;                                        )
  ;                 )
  ;                 (command "erase" "l" "")
  ;                 (setq new_midPT_ (TA:midpoint 
  ;                                    (car (car new_boundingbox_))
  ;                                    (caddr (car new_boundingbox_))
  ;                                  )
  ;                 )

  ;                 (TA:vla-insertblock 
  ;                   "000 - DYNAMIC_ARRAY+COMBINE+VIEW_ASSCESSORIES_PLAN_SUPPLY_AIR_REC.1600x175mm_COMBINE_SET"
  ;                   new_midPT_
  ;                   1
  ;                   ss_pre_filter_set_xx_obj_rotation
  ;                 )
  ;               )
  ;               ;new_blk_entlast object
  ;               (setq newblk_ename (entlast))
  ;               (setq newblk_obj_ (vlax-ename->vla-object newblk_ename))
  ;               (LM:setdynpropvalue newblk_obj_ "view" "6_bottom_view")
  ;               ;
  ;             )
  ;             ((and ;"000 - DYNAMIC_ARRAY+COMBINE+VIEW_ASSCESSORIES_PLAN_SUPPLY_AIR_REC.1600x175mm_COMBINE_SET"
  ;                   (= (vla-get-objectname ss_pre_filter_set_xx_obj_) "AcDbBlockReference")
  ;                   (wcmatch (strcase (LM:effectivename ss_pre_filter_set_xx_obj_)) wildcard_string_2)
  ;               )
  ;               (progn
  ;                 (setq new_boundingbox_ (TA:get-visible-boundingbox ss_pre_filter_set_xx_obj_ ))
  ;                 (command "erase" "l" "" )
  ;                 (setq new_midPT_ (TA:midpoint (car (car new_boundingbox_))  (caddr (car new_boundingbox_))))
  ;                 (TA:vla-insertblock 
  ;                   "000 - DYNAMIC_ARRAY+COMBINE+VIEW_ASSCESSORIES_TRAKC_LIGHT_REC.1257x120mm_COMBINE_SET"
  ;                   new_midPT_
  ;                   1
  ;                   ss_pre_filter_set_xx_obj_rotation
  ;                 )              
  ;               )
  ;               ;new_blk_entlast object
  ;                 (setq newblk_ename (entlast))
  ;                 (setq newblk_obj_ (vlax-ename->vla-object newblk_ename))
  ;                 (LM:setdynpropvalue newblk_obj_ "view" "6_bottom_view")
  ;               ;
  ;             )
  ;             ((and ;"DPA_CP_Metal Ceiling Panel - Horizontal with Gap-29911815-4150-01 - CONCOURSE LEVEL PLAN - REFLECTED CEILING PLAN"
  ;                   (= (vla-get-objectname ss_pre_filter_set_xx_obj_) "AcDbBlockReference")
  ;                   (wcmatch (strcase (LM:effectivename ss_pre_filter_set_xx_obj_)) wildcard_string_3)
  ;               )
  ;               (progn
  ;                 (setq new_boundingbox_ (TA:get-visible-boundingbox ss_pre_filter_set_xx_obj_ ))
  ;                 (command "erase" "l" "" )
  ;                 (setq new_midPT_ (TA:midpoint (car (car new_boundingbox_))  (caddr (car new_boundingbox_))))
  ;                 (TA:vla-insertblock 
  ;                   (if (= (strcase Extr_EFNAME_) "R")
  ;                     (progn
  ;                       "000 - DYNAMIC_LENGTH+COMBINE+VIEW_ASSCESSORIES_FAMELINE_AL.SOLID_SHEET_HAT-PROFILE-TYPE-R_non_code_COMBINE_SET"
  ;                     )
  ;                     "000 - DYNAMIC_LENGTH+COMBINE+VIEW_ASSCESSORIES_FAMELINE_AL.SOLID_SHEET_HAT-PROFILE-TYPE-C_non_code_COMBINE_SET"
  ;                   )
  ;                   (if (> (car (cadr new_boundingbox_)) (cadr (cadr new_boundingbox_)))
  ;                     (progn
  ;                       (TA:midpoint  (car (car new_boundingbox_)) (cadddr (car new_boundingbox_)) )
  ;                     )
  ;                     (TA:midpoint  (caddr (car new_boundingbox_)) (cadddr (car new_boundingbox_)) )
  ;                   )
  ;                   1
  ;                   (if (> (car (cadr new_boundingbox_)) (cadr (cadr new_boundingbox_)))
  ;                     (progn
  ;                       (deg-to-rad 0 )
  ;                     )
  ;                     (deg-to-rad 270)
  ;                   )
  ;                 )              
  ;               )
  ;               ;new_blk_entlast object
  ;                 (setq newblk_ename (entlast))
  ;                 (setq newblk_obj_ (vlax-ename->vla-object newblk_ename))

  ;                 (LM:setdynpropvalue newblk_obj_ "view" "6_bottom_view")
              
  ;                 (if (and 
  ;                       (> (car (cadr new_boundingbox_)) (cadr (cadr new_boundingbox_)))
  ;                     )
  ;                   (progn
  ;                     (setq L (distance  (car (car new_boundingbox_)) (cadr (car new_boundingbox_)) ))
  ;                   )
  ;                   (setq L (distance  (car (car new_boundingbox_)) (cadddr (car new_boundingbox_)) ))
  ;                 )
  ;                 (LM:setdynpropvalue newblk_obj_ "L" L)
  ;                 (LM:setdynpropvalue newblk_obj_ "L2" L)
  ;                 (LM:setdynpropvalue newblk_obj_ "L3" L)
  ;                 (LM:setdynpropvalue newblk_obj_ "L4" L)
  ;                 (LM:setdynpropvalue newblk_obj_ "L5" L)
  ;                 (LM:setdynpropvalue newblk_obj_ "L6" L)
  ;               ;
  ;             )
  ;           )
  ;         )
  ;       )
  ;       (TA:textscr_process_v2 "update" ss_pre_filter_set_xx_i ss_pre_filter_set_xx_ )
  ;       (setq ss_pre_filter_set_xx_i (+ ss_pre_filter_set_xx_i 1))
  ;     )
  ;   ;
  ;   ;get-data_
  ;       (setq main_border_ (TA:ss_vla-getboundingbox ss_pre_filter_set_xx_ ) )
  ;       (setq ptmid_ (TA:midpoint (car main_border_) (cadr main_border_)))  
  ;       (setq bol_datalist_ 
  ;         (list
  ;           (list
  ;             (setq pt1 (list 
  ;                 (car (car main_border_)) 
  ;                 (cadr (car main_border_)) 
  ;                 0 
  ;               )
  ;             )
  ;             (setq pt2 (list 
  ;                 (car (cadr main_border_)) 
  ;                 (cadr (car main_border_)) 
  ;                 0 
  ;               )
  ;             )
  ;             (setq pt3 (list 
  ;                 (car (cadr main_border_)) 
  ;                 (cadr (cadr main_border_)) 
  ;                 0 
  ;               )
  ;             )
  ;             (setq pt4 (list 
  ;               (car (car main_border_)) 
  ;               (cadr (cadr main_border_)) 
  ;               0 
  ;             )
  ;           )
  ;           )
  ;           (list
  ;             (setq Len_1 (distance pt1 pt2))
  ;             (setq Len_2 (distance pt2 pt3))
  ;             (setq Len_3 (distance pt3 pt4))
  ;             (setq Len_4 (distance pt4 pt1))
  ;           )
  ;         )
  ;       )
  ;       (if (> Len_1 Len_4)
  ;         (progn
  ;           (setq Extr_midpt_ (TA:midpoint pt1 pt4 ))
  ;         )
  ;       )
  ;     ;top 
  ;       (TA:vla-insertblock 
  ;         (if (= (strcase Extr_EFNAME_) "R")
  ;           (progn
  ;             "000 - DYNAMIC_COMBINE+VIEW_ASSCESSORIES_FAMELINE_AL.EXTR._REC-PROFILE_50x100mm._non-code_COMBINE_VIEW"
  ;           )
  ;           "000 - DYNAMIC_COMBINE+VIEW_ASSCESSORIES_FAMELINE_AL.EXTR._C-PROFILE_50x100mm._non-code_COMBINE_VIEW"
  ;         )
  ;         (if (> Len_1 Len_4)
  ;           (progn
  ;             (setq Extr_midpt_ (TA:midpoint pt1 pt4 ))
  ;           )
  ;           (setq Extr_midpt_ (TA:midpoint pt1 pt2 ))
  ;         )
  ;         1
  ;         (if (> Len_1 Len_4)
  ;           (progn
  ;             (deg-to-rad 270 )
  ;           )
  ;           (deg-to-rad 0)
  ;         )
  ;       )
  ;       ;new_blk_entlast object
  ;       (cond
  ;         (;_case_1
  ;            (and
  ;               (> Len_1 Len_4)
  ;            )
  ;            (progn
  ;               (setq newExtr_ename (entlast))
  ;               (setq newExtr_obj_ (vlax-ename->vla-object newExtr_ename))
  ;               (TA:move_axis_insertionpoint newExtr_obj_ "y" (+ 125))
  ;               (LM:setdynpropvalue newExtr_obj_  "view" "6_bottom_view")
  ;               (LM:setdynpropvalue newExtr_obj_  "H" Len_1)
  ;               (LM:setdynpropvalue newExtr_obj_  "Hsub" Len_1)
  ;               (LM:setdynpropvalue newExtr_obj_  "Rail_1" Len_1)
  ;               (LM:setdynpropvalue newExtr_obj_  "Rail_2" Len_1)
  ;               (vla-copy newExtr_obj_)
  ;               (TA:move_axis_insertionpoint (setq newExtr_obj_ (vlax-ename->vla-object (entlast))) "y" (- 250))
  ;               (princ "_case_1")
  ;            )
  ;         )
  ;         (;_case_2
  ;            (and
  ;               (< Len_1 Len_4)
  ;            )
  ;            (progn
  ;              (setq newExtr_ename (entlast))
  ;               (setq newExtr_obj_ (vlax-ename->vla-object newExtr_ename))
  ;               (TA:move_axis_insertionpoint newExtr_obj_ "x" (+ 125))
  ;               (LM:setdynpropvalue newExtr_obj_  "view" "6_bottom_view")
  ;               (LM:setdynpropvalue newExtr_obj_  "H" Len_4)
  ;               (LM:setdynpropvalue newExtr_obj_  "Hsub" Len_4)
  ;               (LM:setdynpropvalue newExtr_obj_  "Rail_1" Len_4)
  ;               (LM:setdynpropvalue newExtr_obj_  "Rail_2" Len_4)
  ;               (vla-copy newExtr_obj_)
  ;               (TA:move_axis_insertionpoint (setq newExtr_obj_ (vlax-ename->vla-object (entlast))) "x" (- 250))
  ;               (princ "_case_1")
  ;              (princ "_case_2")
  ;            )
  ;         )

  ;       )


  ;       ;
  ;     ;
  ;   ;   
  ; )
;







(defun c:Reinsy ()
  (setq blk_ename_ (car (entsel "specify Object")))
  (setq blk_obj_ (vlax-ename->vla-object blk_ename_))
  (setq blk_obj_ins_ (vlax-safearray->list (vlax-variant-value (vla-get-insertionpoint blk_obj_))))
  
    (vla-put-insertionpoint 
      blk_obj_
      (vlax-3d-point 
        (list
          (car blk_obj_ins_ )
          (TA:round-05 (cadr blk_obj_ins_ ))
          (caddr blk_obj_ins_ )
        )

      )
      
    )
  
)

(defun c:Dlist_temp ()
  ;selection_set_for_fillter_blk_name
    (if  ;pre_select_ssget_or_post_select_ssget
      (=
        (setq ss_pre_filter_set_xx_ (ssget "i"
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq inslist_mtext_list_ ())
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins_ (vlax-safearray->list (vlax-variant-value (vla-get-insertionpoint ss_pre_filter_set_xx_obj_))))
      (setq ss_pre_filter_set_xx_textstring (vla-get-textstring ss_pre_filter_set_xx_obj_ ))
      (setq sumlist_ (list  ss_pre_filter_set_xx_obj_ins_ ss_pre_filter_set_xx_textstring))
      (TA:textscr_process_V2 "listing" ss_pre_filter_set_xx_i ss_pre_filter_set_xx_ )
      (setq inslist_mtext_list_ (cons  sumlist_ inslist_mtext_list_ ))
      (setq ss_pre_filter_set_xx_i (+ ss_pre_filter_set_xx_i 1))
    )
  ;
    (textscr)
  (setq enter_process (getstring "Please enter for continue "))
  (setq all_vlains_ (TA:corrd_sorting_group inslist_mtext_list_ 5))
  ;preloop_and_while
    (setq getpt_  (getpoint "SSSSS"))
    (setq all_vlains_i 0)
    (while (< all_vlains_i (length all_vlains_))
      (setq all_vlains_list_ (nth  all_vlains_i all_vlains_))
      
      (TA:vla-insertblock 
        "A$C3f8d30b1"
        (list 
          (+ (car getpt_) 0)
          (- (cadr getpt_) (* 75 all_vlains_i))
          (caddr getpt_)
        )
        1
        0
      )
      ;new_blk_entlast object
        (setq newtextatt_ename (entlast))
        (setq newtextatt_obj (vlax-ename->vla-object newtextatt_ename))
        (LM:vl-setattributevalue newtextatt_obj "num" (cadr (nth 0 all_vlains_list_)) )
        (LM:vl-setattributevalue newtextatt_obj "DRAWING_NO" (cadr (nth 1 all_vlains_list_)) )
        (LM:vl-setattributevalue newtextatt_obj "status" (cadr (nth 2 all_vlains_list_)) )
        (LM:vl-setattributevalue newtextatt_obj "DRAWING_NAME" (cadr (nth 3 all_vlains_list_)) )
        (TA:textscr_process_V2 "generate ATT DATA" ss_pre_filter_set_xx_i ss_pre_filter_set_xx_ )
      ;
      (setq all_vlains_i (+ all_vlains_i 1))
    )
  ;
)

(defun c:seltext ()
    (if  ;pre_select_ssget_or_post_select_ssget
      (=
        (setq ss_pre_filter_set_xx_ (ssget "i"
                                          (list
                                            (cons 0 "mtext,text") ;type of object
                                            (cons 8 "G-ANNO-SCHD")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "mtext,text") ;type of object
                                            (cons 8 "G-ANNO-SCHD")   ;kind of layer
                                            ; (cons 2 "000-GRID_LINE_DYN")       ;kind of nameblock
                                            ; (cons 62 1)           ;kind of color call sign with color code index
                                          )
                                    )
        )
      )
      (sslength ss_pre_filter_set_xx_)
    )
  (command "pselect"  ss_pre_filter_set_xx_ "" )
)








   
  

  
  
  
  

(defun c:PPLINE-CKST_300update_ ()
  ; (setq ssssssxxxxxx (TA:get_name_block_in_drawing_to_list_v2))
      ; (vl-catch-all-apply 
      ;   (function 
      ;     (lambda () 
      ;       (command "rename" "b" "A$Ccf731a84" "000 - ASSCESSORIES_FAMELINE_GALV.BRACKET_FITTING_U-PROFILE_BK-07_CUT_VIEW" )
            
            
      ;     )
      ;   )
      ; )
      ; (vl-catch-all-apply 
      ;   (function 
      ;     (lambda () 
      ;       (command "rename" "b" "A$C5aec95aa" "000 - ASSCESSORIES_FAMELINE_GALV.BRACKET_FITTING_L-PROFILE_BK-08_ISOMATRIC_VIEW" )
      ;     )
      ;   )
      ; )
  
  (setq 300HK_blk_list_ 
    (list
      '("HEX_BOLT-M5_set" 1)
      '("000 - PROTOTYPE-DYNAMIC_WAHER_AND_SPRING_WASHER_" 0)
      '("000 - PROTOTYPE-DYNAMIC_THREAD_BOLT" 1)
      '("000 - PROTOTYPE-DYNAMIC_HEX_NUT" 0)
      '("000 - PROTOTYPE-DYNAMIC_HEX_BOLT" 0)
      '("000 - DYNAMIC_VIEW_ASSCESSORIES_SPRING_WASHER_M5_COMBINE_VIEW" 0)
      '("000 - DYNAMIC_VIEW_ASSCESSORIES_RIVET_4-4_TOP_VIEW" 1)
      '("000 - DYNAMIC_VIEW_ASSCESSORIES_RIVET_4-4_COMBINE_VIEW" 1)
      '("000 - DYNAMIC_VIEW_ASSCESSORIES_HEX_BOLT_M5_COMBINE_VIEW" 0)
      '("000 - DYNAMIC_VIEW_ASSCESSORIES_GALV.STUD_FULL_THREAD_1-4_TOP_VIEW" 0)
      '("000 - DYNAMIC_VIEW_ASSCESSORIES_GALV.STUD_FULL_THREAD_1-4_COMBINE_VIEW" 1)
      '("000 - DYNAMIC_LENGTH+VIEW_ACESSORIES_HEX_BOLT-M5_COMBINE_SET" 1)
      '("000 - DYNAMIC_LENGTH+COMBINE+VIEW_ASSCESSORIES_FAMELINE_BK-08_HANGING_SYSTEM_300HK_COMBINE_SET" 0)
      '("000 - DYNAMIC_LENGTH+COMBINE+VIEW_ASSCESSORIES_FAMELINE_AL.SOLID_SHEET_HAT-PROFILE-TYPE-R_non_code_COMBINE_SET" 1)
      '("000 - DYNAMIC_LENGTH+COMBINE+VIEW_ASSCESSORIES_FAMELINE_AL.SOLID_SHEET_HAT-PROFILE-TYPE-C_non_code_COMBINE_SET" 1)
      '("000 - DYNAMIC_COMBINE+VIEW_ASSCESSORIES_FAMELINE_GALV.BRACKET_FITTING_Z-PROFILE_HR-02B_COMBINE_VIEW" 0)
      '("000 - DYNAMIC_COMBINE+VIEW_ASSCESSORIES_FAMELINE_GALV.BRACKET_FITTING_Z-PROFILE_HR-02AA_COMBINE_VIEW" 0)
      '("000 - DYNAMIC_COMBINE+VIEW_ASSCESSORIES_FAMELINE_GALV.BRACKET_FITTING_U-PROFILE_CC-01_COMBINE_VIEW" 1)
      '("000 - DYNAMIC_COMBINE+VIEW_ASSCESSORIES_FAMELINE_GALV.BRACKET_FITTING_U-PROFILE_BK-07_COMBINE_VIEW" 0)
      '("000 - DYNAMIC_COMBINE+VIEW_ASSCESSORIES_FAMELINE_GALV.BRACKET_FITTING_L-PROFILE_LK-04_COMBINE_VIEW" 1)
      '("000 - DYNAMIC_COMBINE+VIEW_ASSCESSORIES_FAMELINE_GALV.BRACKET_FITTING_L-PROFILE_LK-01_COMBINE_VIEW" 1)
      '("000 - DYNAMIC_COMBINE+VIEW_ASSCESSORIES_FAMELINE_GALV.BRACKET_FITTING_L-PROFILE_BK-08_COMBINE_VIEW" 0)
      '("000 - DYNAMIC_COMBINE+VIEW_ASSCESSORIES_FAMELINE_GALV.BRACKET_FITTING_COMPLEX-PROFILE_V-HOOK_COMBINE_VIEW" 1)
      '("000 - DYNAMIC_COMBINE+VIEW_ASSCESSORIES_FAMELINE_GALV.BRACKET_FITTING_COMPLEX-PROFILE_U-HOOK_COMBINE_VIEW" 0)
      '("000 - DYNAMIC_COMBINE+VIEW_ASSCESSORIES_FAMELINE_GALV._SPICE-FOR_HR-02B_COMBINE_VIEW" 1)
      '("000 - DYNAMIC_COMBINE+VIEW_ASSCESSORIES_FAMELINE_GALV._SPICE-FOR_CC-01_COMBINE_VIEW" 1)
      '("000 - DYNAMIC_COMBINE+VIEW_ASSCESSORIES_FAMELINE_BRACKET-L-PROFILE_50x68mm.+HEX_BOLT-M5-SET_non-code_COMBINE_SET" 0)
      '("000 - DYNAMIC_COMBINE+VIEW_ASSCESSORIES_FAMELINE_AL.EXTR._REC-PROFILE_50x100mm._non-code_COMBINE_VIEW" 1)
      '("000 - DYNAMIC_COMBINE+VIEW_ASSCESSORIES_FAMELINE_AL.EXTR._L-PROFILE_50x68mm._non-code_COMBINE_SET" 0)
      '("000 - DYNAMIC_COMBINE+VIEW_ASSCESSORIES_FAMELINE_AL.EXTR._L-PROFILE_50x45mm._non-code_COMBINE_SET" 0)
      '("000 - DYNAMIC_COMBINE+VIEW_ASSCESSORIES_FAMELINE_AL.EXTR._C-PROFILE_50x100mm._non-code_COMBINE_VIEW" 1)
      '("000 - DYNAMIC_ARRAY+COMBINE+VIEW_ASSCESSORIES_TRAKC_LIGHT_REC.1257x120mm_COMBINE_SET" 1)
      '("000 - DYNAMIC_ARRAY+COMBINE+VIEW_ASSCESSORIES_PLAN_SUPPLY_AIR_REC.1600x175mm_COMBINE_SET" 1)
      '("000 - DYNAMIC_ARRAY+COMBINE+VIEW_ASSCESSORIES_FAMELINE_AL.CELL_CELING_PANEL_300HK_@400mm_COMBINE_SET" 0)
      '("000 - DYNAM5IC_VIEW_ASSCESSORIES_WASHER_M5_COM5BINE_VIEW" 0)
      '("000 - BOX_EF_NAME_REV02" 1)
      '("000 - ASSCESSORIES_WASHER_M5_TOP_VIEW" 0)
      '("000 - ASSCESSORIES_WASHER_M5_FRONT-SIDE-BACK_VIEW" 0)
      '("000 - ASSCESSORIES_TRAKC_LIGHT_REC.1257x120mm_FRONT_VIEW" 1)
      '("000 - ASSCESSORIES_TRAKC_LIGHT_REC.1257x120mm_CUT_VIEW" 1)
      '("000 - ASSCESSORIES_SPRING_WASHER_M5_TOP_VIEW" 0)
      '("000 - ASSCESSORIES_SPRING_WASHER_M5_FRONT-SIDE-BACK_VIEW" 0)
      '("000 - ASSCESSORIES_HEX_BOLT_M5_NUT" 0)
      '("000 - ASSCESSORIES_FAMELINE_GALV.BRACKET_FITTING_Z-PROFILE_HR-02B_TOP_VIEW" 0)
      '("000 - ASSCESSORIES_FAMELINE_GALV.BRACKET_FITTING_Z-PROFILE_HR-02B_RIGHT_VIEW" 0)
      '("000 - ASSCESSORIES_FAMELINE_GALV.BRACKET_FITTING_Z-PROFILE_HR-02B_LEFT_VIEW" 0)
      '("000 - ASSCESSORIES_FAMELINE_GALV.BRACKET_FITTING_Z-PROFILE_HR-02B_CUT_VIEW" 0)
      '("000 - ASSCESSORIES_FAMELINE_GALV.BRACKET_FITTING_Z-PROFILE_HR-02AA_TOP_VIEW" 0)
      '("000 - ASSCESSORIES_FAMELINE_GALV.BRACKET_FITTING_Z-PROFILE_HR-02AA_RIGHT_VIEW" 0)
      '("000 - ASSCESSORIES_FAMELINE_GALV.BRACKET_FITTING_Z-PROFILE_HR-02AA_LEFT_VIEW" 0)
      '("000 - ASSCESSORIES_FAMELINE_GALV.BRACKET_FITTING_Z-PROFILE_HR-02AA_ISOMATRIC_VIEW" 0)
      '("000 - ASSCESSORIES_FAMELINE_GALV.BRACKET_FITTING_Z-PROFILE_HR-02AA_CUT_VIEW" 0)
      '("000 - ASSCESSORIES_FAMELINE_GALV.BRACKET_FITTING_U-PROFILE_CC-01_TOP_VIEW" 0)
      '("000 - ASSCESSORIES_FAMELINE_GALV.BRACKET_FITTING_U-PROFILE_CC-01_LEFT-RIGHT_VIEW" 0)
      '("000 - ASSCESSORIES_FAMELINE_GALV.BRACKET_FITTING_U-PROFILE_CC-01_CUT_VIEW" 0)
      '("000 - ASSCESSORIES_FAMELINE_GALV.BRACKET_FITTING_U-PROFILE_BK-07_TOP_VIEW" 0)
      '("000 - ASSCESSORIES_FAMELINE_GALV.BRACKET_FITTING_U-PROFILE_BK-07_LEFT-RIGHT_VIEW" 0)
      '("000 - ASSCESSORIES_FAMELINE_GALV.BRACKET_FITTING_U-PROFILE_BK-07_ISOMATRIC_VIEW" 0)
      '("000 - ASSCESSORIES_FAMELINE_GALV.BRACKET_FITTING_U-PROFILE_BK-07_CUT_VIEW" 0)
      '("000 - ASSCESSORIES_FAMELINE_GALV.BRACKET_FITTING_L-PROFILE_LK-04_TOP_VIEW" 0)
      '("000 - ASSCESSORIES_FAMELINE_GALV.BRACKET_FITTING_L-PROFILE_LK-04_ISOMATRIC_VIEW" 0)
      '("000 - ASSCESSORIES_FAMELINE_GALV.BRACKET_FITTING_L-PROFILE_LK-04_FRONT_VIEW" 0)
      '("000 - ASSCESSORIES_FAMELINE_GALV.BRACKET_FITTING_L-PROFILE_LK-04_CUT_VIEW" 0)
      '("000 - ASSCESSORIES_FAMELINE_GALV.BRACKET_FITTING_L-PROFILE_LK-01_TOP_VIEW" 0)
      '("000 - ASSCESSORIES_FAMELINE_GALV.BRACKET_FITTING_L-PROFILE_LK-01_LEFT-RIGHT_VIEW" 0)
      '("000 - ASSCESSORIES_FAMELINE_GALV.BRACKET_FITTING_L-PROFILE_LK-01_FRONT_VIEW" 0)
      '("000 - ASSCESSORIES_FAMELINE_GALV.BRACKET_FITTING_L-PROFILE_LK-01_CUT_VIEW" 0)
      '("000 - ASSCESSORIES_FAMELINE_GALV.BRACKET_FITTING_L-PROFILE_LK-01_BACK_VIEW" 0)
      '("000 - ASSCESSORIES_FAMELINE_GALV.BRACKET_FITTING_L-PROFILE_BK-08_TOP_VIEW" 0)
      '("000 - ASSCESSORIES_FAMELINE_GALV.BRACKET_FITTING_L-PROFILE_BK-08_ISOMATRIC_VIEW" 0)
      '("000 - ASSCESSORIES_FAMELINE_GALV.BRACKET_FITTING_L-PROFILE_BK-08_FRONT_VIEW" 0)
      '("000 - ASSCESSORIES_FAMELINE_GALV.BRACKET_FITTING_L-PROFILE_BK-08_CUT_VIEW" 0)
      '("000 - ASSCESSORIES_FAMELINE_GALV.BRACKET_FITTING_L-PROFILE_BK-08_BACK_VIEW" 0)
      '("000 - ASSCESSORIES_FAMELINE_GALV.BRACKET_FITTING_COMPLEX-PROFILE_V-HOOK_LEFT_VIEW" 0)
      '("000 - ASSCESSORIES_FAMELINE_GALV.BRACKET_FITTING_COMPLEX-PROFILE_U-HOOK_LEFT_VIEW" 0)
      '("000 - ASSCESSORIES_FAMELINE_GALV._SPICE-FOR_HR-02B_TOP_VIEW" 1)
      '("000 - ASSCESSORIES_FAMELINE_GALV._SPICE-FOR_HR-02A_TOP_VIEW" 1)
      '("000 - ASSCESSORIES_FAMELINE_GALV._SPICE-FOR_CC-01_TOP_VIEW" 0)
      '("000 - ASSCESSORIES_FAMELINE_GALV._SPICE-FOR_CC-01_LEFT-RIGHT_VIEW" 0)
      '("000 - ASSCESSORIES_FAMELINE_GALV._SPICE-FOR_CC-01_CUT_VIEW" 0)
      '("000 - ASSCESSORIES_FAMELINE_AL.SOLID_SHEET_HAT-PROFILE-TYPE-R_CUT_VIEW" 1)
      '("000 - ASSCESSORIES_FAMELINE_AL.SOLID_SHEET_HAT-PROFILE-TYPE-C_CUT_VIEW" 1)
      '("000 - ASSCESSORIES_FAMELINE_AL.EXTR._L-PROFILE_50x68mm._non-code_TOP_VIEW" 0)
      '("000 - ASSCESSORIES_FAMELINE_AL.EXTR._L-PROFILE_50x68mm._non-code_FRONT_VIEW" 1)
      '("000 - ASSCESSORIES_FAMELINE_AL.EXTR._L-PROFILE_50x68mm._non-code_CUT_VIEW" 1)
      '("000 - ASSCESSORIES_FAMELINE_AL.EXTR._L-PROFILE_50x68mm._non-code_BOTTOM_VIEW" 0)
      '("000 - ASSCESSORIES_FAMELINE_AL.EXTR._L-PROFILE_50x68mm._non-code_BACK_VIEW" 0)
      '("000 - ASSCESSORIES_FAMELINE_AL.EXTR._L-PROFILE_50x45mm._non-code_TOP_VIEW" 0)
      '("000 - ASSCESSORIES_FAMELINE_AL.EXTR._L-PROFILE_50x45mm._non-code_FRONT_VIEW" 0)
      '("000 - ASSCESSORIES_FAMELINE_AL.EXTR._L-PROFILE_50x45mm._non-code_CUT_VIEW" 0)
      '("000 - ASSCESSORIES_FAMELINE_AL.EXTR._L-PROFILE_50x45mm._non-code_BOTTOM_VIEW" 0)
      '("000 - ASSCESSORIES_FAMELINE_AL.EXTR._L-PROFILE_50x45mm._non-code_BACK_VIEW" 0)
      '("000 - ASSCESSORIES_FAMELINE_AL.BRACKET_FITTING_COMPLEX-PROFILE_V-HOOK_TOP_VIEW" 0)
      '("000 - ASSCESSORIES_FAMELINE_AL.BRACKET_FITTING_COMPLEX-PROFILE_V-HOOK_RIGHT_VIEW" 0)
      '("000 - ASSCESSORIES_FAMELINE_AL.BRACKET_FITTING_COMPLEX-PROFILE_V-HOOK_ISOMATRIC_VIEW" 0)
      '("000 - ASSCESSORIES_FAMELINE_AL.BRACKET_FITTING_COMPLEX-PROFILE_V-HOOK_CUT_VIEW" 0)
      '("000 - ASSCESSORIES_FAMELINE_AL.BRACKET_FITTING_COMPLEX-PROFILE_U-HOOK_TOP_VIEW" 0)
      '("000 - ASSCESSORIES_FAMELINE_AL.BRACKET_FITTING_COMPLEX-PROFILE_U-HOOK_RIGHT_VIEW" 0)
      '("000 - ASSCESSORIES_FAMELINE_AL.BRACKET_FITTING_COMPLEX-PROFILE_U-HOOK_ISOMATRIC_VIEW" 0)
      '("000 - ASSCESSORIES_FAMELINE_AL.BRACKET_FITTING_COMPLEX-PROFILE_U-HOOK_CUT_VIEW" 0)
    )
  )
  (length 300HK_blk_list_)
  ; (setq pp18_path "C:/TA WORK/PPLINE CKST/20250701_new_merge_C1-C2_Finishes-Reflected Ceiling Plan/C1-C2_Finishes-Reflected Ceiling Plan/PP20/CAD/") ;use /w PC
  ; (setq pp18_path "C:/TA WORK/PPLINE CKST/20250701_new_merge_C1-C2_Finishes-Reflected Ceiling Plan/C1-C2_Finishes-Reflected Ceiling Plan/PP18/CAD/NEW FL") ;use /w PC
  (setq pp18_path "C:/TA FAMELINE old data/TA/TA_WORK/MASS TRANSIT/TA_PPLINE CKST/TA_PPLINE CKST_combine_CSD-ceiling-plan/20250701_new_merge_C1-C2_Finishes-Reflected Ceiling Plan/C1-C2_Finishes-Reflected Ceiling Plan/PP20/CAD/")
  (setq filePath (getfiled "Select the DWG file" pp18_path "dwg" 4))
  (textscr)
  (setq temp_pt (getpoint "specify point" ))
  ;preloop_and_while
    (setq 300HK_blk_list_i 0)
    (setvar "BLOCKREDEFINEMODE" 1)
    (while (< 300HK_blk_list_i (length 300HK_blk_list_))
      (setq 300HK_blk_list_ename_ (car (nth  300HK_blk_list_i 300HK_blk_list_)))
        ; (if (= (cadr (nth  300HK_blk_list_i 300HK_blk_list_)) 0)
        ;   (progn
        ;     (TA:set-block-blockscaling 300HK_blk_list_ename_ acAny )
        ;     (command "-INSERTCONTENT" filePath 300HK_blk_list_ename_ "Y" 1 temp_pt 0    )
        ;   )
        ; )
        ; (if (= (cadr (nth  300HK_blk_list_i 300HK_blk_list_)) 1)
        ;   (progn
        ;     (TA:set-block-blockscaling 300HK_blk_list_ename_ acUniform )
        ;     (command "-INSERTCONTENT" filePath 300HK_blk_list_ename_ "Y" temp_pt 1 0    )
        ;   )
        ; )
        (command "-INSERTCONTENT" filePath 300HK_blk_list_ename_  temp_pt 1 1 0)
      (TA:textscr_process "update" 300HK_blk_list_i 300HK_blk_list_)
      ; (command "erase" "l" "")
      (setq 300HK_blk_list_i (+ 300HK_blk_list_i 1))
    )
  ;
  
)
  (defun c:PPLINE-CKST_CSDupdate_ ()
    ; (TA:get_name_block_in_drawing_to_list)
    ; (TA:get_name_block_in_drawing_to_list)
    ;presetting
      (setvar "BLOCKREDEFINEMODE" 1)
      (setvar "ATTREQ" 0)
      (setvar "ATTDIA" 0)
    ;
    (setq input_station_no_ (cond ( (getint (strcat "\nspecify input_station_no_  \n<" (rtos (setq input_station_no_ (cond (input_station_no_) (1.0) ) ) ) "> : " ) ) ) (input_station_no_) ) )
    (setq station_fullname_ (strcat "PP" (rtos input_station_no_ 2 0 )))
    (setq CSD_MERGE_LIST_ ())
    (setq err_ "S")
    (while (/= (wcmatch (strcase (vl-princ-to-string err_)) "*ERROR*") T) 
      (setq err_ (vl-catch-all-apply 
                  (function 
                    (lambda () 
                      (setq CSD_MERGE_LIST_ (cons (LM:effectivename (setq ee (vlax-ename->vla-object (car (entsel "specify Object")) ) ) ) CSD_MERGE_LIST_ ) )
                    )
                  )
                )
      )
    )
    (setq CSD_MERGE_LIST_ (mapcar 'car (TA:Count_item_in_list_ CSD_MERGE_LIST_)))
    (setq Er-msg_finder nil)
    (setq Er-msg_finder
      (vl-catch-all-apply 
        (function 
          (lambda () 
            (cond
              (;_case_1
                (and 
                  ; (/= (type err_ ) 'VL-CATCH-ALL-APPLY-ERROR)
                  (= (getenv "COMPUTERNAME") "NONGSAISUEARAIH")
                  ;  (/= (wcmatch (strcase (vl-princ-to-string err_)) "*ERROR*") T)
                )
                (progn
                  (setq pp18_path (strcat "C:/TA/PPLINE CKST/C1-C2_Finishes-Reflected Ceiling Plan/" station_fullname_ "/CAD/"))
                  (princ "_case_1")
                )
              )
              (;_case_2
                (and 
                  ; (/= (type err_ ) 'VL-CATCH-ALL-APPLY-ERROR)
                  (= (getenv "COMPUTERNAME") "NONGSAISUEARAI")
                  (= (getenv "USERNAME") "NONGSAISUEARAI")
                  ;  (/= (wcmatch (strcase (vl-princ-to-string err_)) "*ERROR*") T)
                )
                (progn
                  (setq pp18_path (strcat "C:/TA FAMELINE old data/TA/TA_WORK/MASS TRANSIT/TA_PPLINE CKST/TA_PPLINE CKST_combine_CSD-ceiling-plan/C1-C2_Finishes-Reflected Ceiling Plan/" station_fullname_ "/CAD/"))
                  (princ "_case_2")
                )
              )
              (;case_3
                (and
                  ; (/= (type err_ ) 'VL-CATCH-ALL-APPLY-ERROR)
                  (= (getenv "COMPUTERNAME") "DESKTOP-VNKD8FJ")
                  (= (getenv "USERNAME") "tawan.t")
                )
                (progn
                  (setq pp18_path (strcat "C:/TA/PPLINE CKST/C1-C2_Finishes-Reflected Ceiling Plan/" station_fullname_ "/CAD/"))
                )
              )
            )
          )
        )
      )
    )
    (if (= input_station_no_ 1)
      (progn
        (setq pp18_path (getvar "DWGPREFIX"))
      )
    )
    
    ;
    
    (setq filePath (getfiled "Select the DWG file" pp18_path "dwg" 4))
    (textscr)
    (setq temp_pt (getpoint "specify point" ))
    ;preloop_and_while
      (setq CSD_MERGE_LIST_i 0)
      (setq CER_ 0)
      (while 
        (and 
          (/= CSD_MERGE_LIST_ nil)
          (< CSD_MERGE_LIST_i (length CSD_MERGE_LIST_))
          (/= (wcmatch (strcase (vl-princ-to-string CER_)) "NIL"))
        )
        (setq CSD_MERGE_LIST_efname (nth CSD_MERGE_LIST_i CSD_MERGE_LIST_))
        (command "-INSERTCONTENT" filePath CSD_MERGE_LIST_efname temp_pt 1 1 0)
        (vla-delete (vlax-ename->vla-object (entlast)))
        (setq CSD_MERGE_LIST_i (+ CSD_MERGE_LIST_i 1))
      )
    ;
    
    (setvar "BLOCKREDEFINEMODE" 1)
    (alert "complete")
  )
  (defun c:csdtemp ()
        (command "-INSERTCONTENT" 
                 "C:\\TA\\PPLINE CKST\\C1-C2_Finishes-Reflected Ceiling Plan\\PP19\\CAD\\W-1-PP19-AR-4251-01-A.dwg" 
                 "Title Block_Under Ground_C1 v3" 
                 (list 500 500 0) 
                 1 1 0
        )
        (vla-delete (vlax-ename->vla-object (entlast)))
  )
  (defun c:PPLINE-CKST_CSDaboveupdate_ ()
    ; (TA:get_name_block_in_drawing_to_list)
    ; (TA:get_name_block_in_drawing_to_list)
    ;presetting
      (setvar "BLOCKREDEFINEMODE" 1)
      (setvar "ATTREQ" 0)
      (setvar "ATTDIA" 0)
    ;
    (setq input_station_no_ (cond ( (getint (strcat "\nspecify input_station_no_  \n<" (rtos (setq input_station_no_ (cond (input_station_no_) (1.0) ) ) ) "> : " ) ) ) (input_station_no_) ) )
    (setq station_fullname_ (strcat "PP" (rtos input_station_no_ 2 0 )))
    (setq CSD_MERGE_LIST_ ())
    (setq err_ "S")
    (while (/= (wcmatch (strcase (vl-princ-to-string err_)) "*ERROR*") T) 
      (setq err_ (vl-catch-all-apply 
                  (function 
                    (lambda () 
                      (setq CSD_MERGE_LIST_ (cons (LM:effectivename (setq ee (vlax-ename->vla-object (car (entsel "specify Object")) ) ) ) CSD_MERGE_LIST_ ) )
                    )
                  )
                )
      )
    )
    (setq CSD_MERGE_LIST_ (mapcar 'car (TA:Count_item_in_list_ CSD_MERGE_LIST_)))
    (cond
      (;_case_1
        (and 
          ; (/= (type err_ ) 'VL-CATCH-ALL-APPLY-ERROR)
          (= (getenv "COMPUTERNAME") "NONGSAISUEARAIH")
          ;  (/= (wcmatch (strcase (vl-princ-to-string err_)) "*ERROR*") T)
        )
        (progn
          (setq pp18_path (strcat "C:/TA/PPLINE CKST/CKST_PPLINE_ABOVE/ABOVE/C1&C2_0121-1 Update (29.01.26)/" station_fullname_ "/"))
          (princ "_case_1")
        )
      )
      (;_case_2
        (and 
          ; (/= (type err_ ) 'VL-CATCH-ALL-APPLY-ERROR)
          (= (getenv "COMPUTERNAME") "NONGSAISUEARAI")
          (= (getenv "USERNAME") "NONGSAISUEARAI")
          ;  (/= (wcmatch (strcase (vl-princ-to-string err_)) "*ERROR*") T)
        )
        (progn
          (setq pp18_path (strcat "C:/TA FAMELINE old data/TA/TA_WORK/MASS TRANSIT/TA_PPLINE CKST/TA_PPLINE CKST_combine_CSD-ceiling-plan/C1-C2_Finishes-Reflected Ceiling Plan/" station_fullname_ "/CAD/"))
          (princ "_case_2")
        )
      )
      (;case_3
        (and
          ; (/= (type err_ ) 'VL-CATCH-ALL-APPLY-ERROR)
          (= (getenv "COMPUTERNAME") "DESKTOP-VNKD8FJ")
          (= (getenv "USERNAME") "tawan.t")
        )
        (progn
          (setq pp18_path (strcat "C:/TA/PPLINE CKST/C1-C2_ABOVE/ABOVE/C1_C2_0121-1 Update (29.01.26)/C1&C2_0121-1 Update (29.01.26)/"))
        )
      )
    )
    
    
    (setq filePath (getfiled "Select the DWG file" pp18_path "dwg" 4))
    (textscr)
    (setq temp_pt (getpoint "specify point" ))
    ;preloop_and_while
      (setq CSD_MERGE_LIST_i 0)
      (setq CER_ 0)
      (while 
        (and 
          (/= CSD_MERGE_LIST_ nil)
          (< CSD_MERGE_LIST_i (length CSD_MERGE_LIST_))
          (/= (wcmatch (strcase (vl-princ-to-string CER_)) "NIL"))
        )
        (setq CSD_MERGE_LIST_efname (nth CSD_MERGE_LIST_i CSD_MERGE_LIST_))
        (command "-INSERTCONTENT" filePath CSD_MERGE_LIST_efname temp_pt 1 1 0)
        (vla-delete (vlax-ename->vla-object (entlast)))
        (setq CSD_MERGE_LIST_i (+ CSD_MERGE_LIST_i 1))
      )
    ;
    
    (setvar "BLOCKREDEFINEMODE" 1)
    (alert "complete")
  )
  
  (defun TA:PPLINE-CKST_CSDautoupdate_ (input_station_no_ CSD_MERGE_LIST__ filePath)
    ; (TA:get_name_block_in_drawing_to_list)
    ; (TA:get_name_block_in_drawing_to_list)
    ;presetting
      (setvar "BLOCKREDEFINEMODE" 1)
      (setvar "ATTREQ" 0)
      (setvar "ATTDIA" 0)
    ;
    ; (setq input_station_no_ 17 )
    (setq station_fullname_ (strcat "PP" (rtos input_station_no_ 2 0 )))
    (setq CSD_MERGE_LIST_ ())
    (setq err_ "S")
    ; (while (/= (wcmatch (strcase (vl-princ-to-string err_)) "*ERROR*") T) 
    ;   (setq err_ (vl-catch-all-apply 
    ;               (function 
    ;                 (lambda () 
    ;                   (setq CSD_MERGE_LIST_ (list "A$C9312df8d") )
    ;                 )
    ;               )
    ;             )
    ;   )
    ; )
    ; (setq CSD_MERGE_LIST_ (list "W-1-PP17-AR-4150-01-A_20260302-141613_AHP_C06_OVL") )
    (setq CSD_MERGE_LIST_ (mapcar 'car (TA:Count_item_in_list_ CSD_MERGE_LIST__)))
    
    
    
    ; (setq filePath (getfiled "Select the DWG file" pp18_path "dwg" 4)) ;bypass file path below this line
    
    ; (setq filePath "C:\\TA\\PPLINE CKST\\C1-C2_Finishes-Reflected Ceiling Plan\\PP17\\CAD\\W-1-PP17-AR-4150-01-A.dwg")
    (textscr)
    ; (setq temp_pt (getpoint "specify point" )) 
    (setq temp_pt (list 0.0 0.0 0.0)) 
    ;preloop_and_while
      (setq CSD_MERGE_LIST_i 0)
      (setq CER_ 0)
      (while 
        (and 
          (/= CSD_MERGE_LIST_ nil)
          (< CSD_MERGE_LIST_i (length CSD_MERGE_LIST_))
          (/= (wcmatch (strcase (vl-princ-to-string CER_)) "NIL"))
        )
        (setq CSD_MERGE_LIST_efname (nth CSD_MERGE_LIST_i CSD_MERGE_LIST_))
        (command "-INSERTCONTENT" filePath CSD_MERGE_LIST_efname temp_pt 1 1 0)
        (vla-delete (vlax-ename->vla-object (entlast)))
        (setq CSD_MERGE_LIST_i (+ CSD_MERGE_LIST_i 1))
      )
    ;
    
    (setvar "BLOCKREDEFINEMODE" 1)
    (alert "complete")
  )
  (defun c:csdautoupdate ()
    ; (setq input_station_no_ 17 )
    ; (setq station_fullname_ (strcat "PP" (rtos input_station_no_ 2 0 )))
    ; (setq CSD_MERGE_LIST__ (list "W-1-PP17-AR-4150-01-A_20260302-141613_AHP_C06_OVL") )
    ; (setq filePath "C:\\TA\\PPLINE CKST\\C1-C2_Finishes-Reflected Ceiling Plan\\PP17\\CAD\\W-1-PP17-AR-4150-01-A.dwg")
    ; (TA:PPLINE-CKST_CSDautoupdate_ input_station_no_ 
    ;                                 CSD_MERGE_LIST__
    ;                               filePath

    ; )
    (TA:PPLINE-CKST_CSDautoupdate_ 17
                                    (list "W-1-PP17-AR-4180-01-A_20260303-141224_AHP_C06_OVL")
                                  "C:\\TA\\PPLINE CKST\\C1-C2_Finishes-Reflected Ceiling Plan\\PP17\\CAD\\W-1-PP17-AR-4180-01-A.dwg"

    )
  )






(defun TA:Combine-SS (ss1 ss2 / newSS i ent)
  (setq newSS (ssadd)) ; สร้าง selection set ว่าง
  
  ;; ใส่สมาชิกจาก ss1
  (if ss1
    (progn
      (setq i 0)
      (while (< i (sslength ss1))
        (setq ent (ssname ss1 i))
        (ssadd ent newSS)
        (setq i (1+ i))
      )
    )
  )

  ;; ใส่สมาชิกจาก ss2
  (if ss2
    (progn
      (setq i 0)
      (while (< i (sslength ss2))
        (setq ent (ssname ss2 i))
        (ssadd ent newSS)
        (setq i (1+ i))
      )
    )
  )

  newSS ; return selection set ที่รวมแล้ว
)
;s



(defun c:breakline_Brdist ()
  (setq pline_ename_ (car (entsel "specify Object")))
  (setq pline_obj_ (vlax-ename->vla-object pline_ename_))
  (if (= (vla-get-objectname pline_obj_) "AcDbPolyline")
    (progn
      (setq osmode (getvar "osmode"))
      (setvar "osmode" 0)
      (if (< (setq real (getreal "specify dist.")) 0)
        (progn
          (setq ss (+ (vla-get-length pline_obj_) real))
          
          (command "breakatpoint" pline_ename_ (vlax-curve-getPointAtDist pline_obj_ ss))
        )
        (command "breakatpoint" pline_ename_ (vlax-curve-getPointAtDist pline_obj_ real))
      )
      
      (setvar "osmode" osmode)
    )
  )
)
(defun TA:pair-data-list_ (target-list_ )
  ;preloop_and_while
    (setq target-list_i 0)
    (setq x1 1)
    (setq x2 2)
    (setq target-list_new-list_ ())
    (while (< target-list_i (/ (length target-list_) 2))
      (setq target-list_new-list_ (cons 
                                      (list 
                                        (setq target-list_val_car (nth (+ x1 target-list_i ) target-list_ ) )
                                        (setq target-list_val_cadr (nth (+ x2 target-list_i ) target-list_ ) )
                                      )
                                      target-list_new-list_
                                    )
      )
      (setq target-list_i (+ target-list_i 1))
      (setq x1 (+ x1 1))
      (setq x2 (+ x2 1))
    )
    (setq target-list_new-list_ (reverse target-list_new-list_))
  ;

)
(defun c:ss-panel ()
  ;presetting
    (setq newss_pline_real_ (ssadd))
    (setq newss_pline_gap_ (ssadd))
    (setq pre-en nil)
    (setq pre-en (ssadd))
    (setq folding 50)
    (setq gap 50)
  ;
  (setq pline_ename_ (car (entsel "specify Object")))
  (setq pre-en (ssadd pline_ename_  pre-en))
  (setq pline_obj_ (vlax-ename->vla-object pline_ename_))
  (setq pline_obj_existing_ (vlax-ename->vla-object pline_ename_))
  (setq pline_obj_existing_length (vla-get-length pline_obj_))
  (setq real (+ (getreal "specify dist.") gap))
  (setq real_total_time_ (fix (/ (vla-get-length pline_obj_) (+ real gap))))
  (setq pline_obj_ss (vlax-curve-getPointAtDist pline_obj_ real))
  (setq real_total_time_i 0)
  (setvar "osmode" 0)
  ;assembly panel by user input length
    (while (and
            (> real 0 )
            (< real pline_obj_existing_length )
            (< real_total_time_i real_total_time_)
          )
      (command "breakatpoint" pline_ename_ (vlax-curve-getPointAtDist pline_obj_ real))
      ; (if (= real_total_time_i 0) (progn (setq pre-en (ssname (ssget "P") 0)) ) )
      ;new_blk_entlast object

        (setq pline_ename_ (entlast))
        (setq newss_pline_real_ (ssadd pline_ename_ newss_pline_real_   )) 
        (setq pline_obj_ (vlax-ename->vla-object pline_ename_))
      ;
      (command "breakatpoint" pline_ename_ (vlax-curve-getPointAtDist pline_obj_ gap))
      ;new_blk_entlast object
        (setq pline_ename_ (entlast))
        (setq newss_pline_gap_ (ssadd pline_ename_ newss_pline_gap_   )) 
        (setq pline_obj_ (vlax-ename->vla-object pline_ename_))
      ;
      (setq real_total_time_i (+ real_total_time_i 1))
    )
  ;
  (setq newss_pline_gap_ (ssadd (ssname pre-en 0) newss_pline_gap_))
  ; (command "pselect"  pline_ename_  "" )
  ; (command "pselect"  pre-en  "" )
  ; (command "pselect"  newss_pline_real_  "" )
  ; (command "pselect"  newss_pline_gap_  "" )
  

  ;preloop_and_while
    (setq newss_pline_ newss_pline_gap_ )
    (setq newss_pline_i 0)
    (while (< newss_pline_i (sslength newss_pline_))
      (setq newss_pline_ename_ (ssname newss_pline_ newss_pline_i))
      (setq list-coords ())
      (setq newss_pline_obj_ (vlax-ename->vla-object  newss_pline_ename_))
      (setvar "osmode" 0)
      (setq coords (reverse (vlax-safearray->list (vlax-variant-value (vla-get-coordinates newss_pline_obj_)))))
      (setq target-list_ (append (list "0") (vlax-safearray->list (vlax-variant-value (vla-get-coordinates newss_pline_obj_)))))
      (setq list-coords (TA:pair-data-list_ target-list_))
      (if (= (length list-coords) 3 )
        (progn
          (setq folding_1_ (TA:ModifyRotation (rad-to-deg (angle (nth 0 list-coords) (nth 1 list-coords))) -90))
          (setq folding_1_pt (polar (nth 0 list-coords) (deg-to-rad folding_1_) folding))
          (setq folding_2_ (TA:ModifyRotation (rad-to-deg (angle  (nth 1 list-coords) (nth 2 list-coords))) -90))
          (setq folding_2_pt (polar (nth 2 list-coords) (deg-to-rad folding_2_) folding))
          (TA:vla-addvertex_ newss_pline_obj_ 0 folding_1_pt  )
          (TA:vla-addvertex_ newss_pline_obj_ 4 folding_2_pt  )
          
        )
      )
      (if (= (length list-coords) 2 )
        (progn
          (setq folding_1_ (TA:ModifyRotation (rad-to-deg (angle (nth 0 list-coords) (nth 1 list-coords))) -90))
          (setq folding_1_pt (polar (nth 0 list-coords) (deg-to-rad folding_1_) folding))
          (TA:vla-addvertex_ newss_pline_obj_ 0 folding_1_pt  )
          
          (setq folding_2_ (TA:ModifyRotation (rad-to-deg (angle (nth 0 list-coords) (nth 1 list-coords))) -90))
          (setq folding_2_pt (polar (nth 1 list-coords) (deg-to-rad folding_2_) folding))
          
          (TA:vla-addvertex_ newss_pline_obj_ 3 folding_2_pt  )
          
        )
      )
      (setq newss_pline_i (+ newss_pline_i 1))
    )
  ;
  
  (command "erase"  newss_pline_real_ "" )
  
  (setvar "osmode" 1215)
)




(defun c:reprec ()
  ;selection_set_for_fillter_blk_name
    (if  ;pre_select_ssget_or_post_select_ssget
      (=
        (setq ss_pre_filter_set_xx_ (ssget "i"
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_ename_cenpt (LM:PolyCentroid ss_pre_filter_set_xx_ename_ ))
      (command "boundary" ss_pre_filter_set_xx_ename_cenpt "" )
      (setq ss_pre_filter_set_xx_i (+ ss_pre_filter_set_xx_i 1))
    )
  ;

)
(defun c:Indigo_IDIfindpanel ()
  
  ;selection_set_for_fillter_blk_name
    (if  ;pre_select_ssget_or_post_select_ssget
      (=
        (setq pline_ (ssget "i"
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq pline_ (ssget
                                          (list
                                            (cons 0 "lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength pline_)
    )
  ;
  
  ;preloop_and_while
    (setq pline_i 0)
    (while (< pline_i (sslength pline_))
      (setq pline_ename_ (ssname pline_ pline_i))
      (setq pline_obj_ (vlax-ename->vla-object  pline_ename_))
      (setq vertex_data_ (cadr (TA:Get_Pline_vertext_ins_point_ pline_ename_)))
      (setq vertex_data_cenpt (LM:PolyCentroid pline_ename_ ))
      ;TA:stanndard_lambda_sorting
        (setq vertex_data_sorted_ (vl-sort vertex_data_  ;bigest open indent list
                                                  (function 
                                                    (lambda (a b) 
                                                      (< (car a) (car b))
                                                    )
                                                  )
                              ) ;bigest close indent list
        )
        (setq vertex_data_sorted_xminset (vl-sort 
                                          (list (car vertex_data_sorted_) (cadr vertex_data_sorted_) ) ;bigest open indent list
                                          (function 
                                            (lambda (a b) 
                                              (< (cadr a) (cadr b))
                                            )
                                          )
                                        )
        )
        (setq vertex_data_sorted_yminset (vl-sort 
                                          (list (caddr vertex_data_sorted_) (cadddr vertex_data_sorted_)) ;bigest open indent list
                                          (function 
                                            (lambda (a b) 
                                              (< (cadr a) (cadr b))
                                            )
                                          )
                                        )
        )
        (setq summary_xy_list_ (list (car vertex_data_sorted_xminset) (car vertex_data_sorted_yminset ) (cadr vertex_data_sorted_yminset)  (cadr vertex_data_sorted_xminset)   ))
      ;
      ;recreate rec process
      (create-plines summary_xy_list_ "close" )
      ;
        (setq pline_i (+ pline_i 1))
    )
  ;
  (command "pselect"  pline_ "" ) 
)
  
(defun c:tran_solid_panel_TRSO_ ( )
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (setq ss_pre_filter_set_xx_ (TA:EF_Filter_ss_set_v2_ ss_pre_filter_set_xx_ (list "000 - DYNAMIC_COMBINE_FAMELINE_SOLID_PANEL_2-STEP_COMBINE_VIEW" "000 - DYNAMIC_COMBINE_FAMELINE_SOLID_PANEL_3-STEP_COMBINE_VIEW")))
  ;
  ;preloop_and_while tranfering sec to front process
      (setq new_inspt_ (getpoint (vlax-safearray->list (vlax-variant-value (vla-get-insertionpoint (vlax-ename->vla-object (car (entsel "specify reference point"))))))) )
      (setq keyword_value_detect "mode3")
      (setq ss_pre_filter_set_xx_i 0)
      (setq new_pre_filter_set_xx_ (ssadd))
      (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (defun TA:solid_section-to-front (blk_obj_ keyword_value_detect new_inspt_ )
            ;Note By Code_Developer
            ;principle of codework is developed method of tranfering section view to front elevation view by retrieving data via selection set
            ;to create a front elevation view from a section view, the process retrieves the block’s dynamic length data and calculates the bounding box size based on the coordinate system.
            ;After calculating the bounding box height for each panel, the panel height is then applied as the dynamic length.
            ;
            ; (setq blk_ename_ (car (entsel "specify Object"))) ;for tesing code
            ; (setq blk_obj_ (vlax-ename->vla-object blk_ename_))
            (setq blk_obj_rotation (vla-get-rotation blk_obj_))
            (setq blk_obj_ins_ (vlax-safearray->list (vlax-variant-value (vla-get-insertionpoint blk_obj_))))
            (setq blk_list_ ())
            (if (= (vla-get-objectname blk_obj_) "AcDbBlockReference")
              (progn
                (setq visible_list_ (ssadd))
                (setq blkname (cdr (assoc 2 (entget (vlax-vla-object->ename blk_obj_)))))
                (setq bdef (tblobjname "BLOCK" blkname))
                (if (= (vl-prin1-to-string (type bdef)) "ENAME") ;สำหรับ ดึงข้อมูลเพื่อทำ vla-getboundingbox
                  (progn
                    (setq nested (entnext bdef))
                    (setq main_border_assembly_ ())
                    (while 
                      (and nested 
                          (/= (cdr (assoc 0 (entget nested))) "ENDBLK")
                      )
                      (if (and 
                            (setq nested_obj_ (vlax-ename->vla-object nested))
                            (/= (vla-get-linetypescale nested_obj_) 1.234 )
                            (/= (vla-get-objectname nested_obj_) "AcDbAttributeDefinition")
                            (/= (vla-get-objectname nested_obj_) "AcDbAttribute")
                            (/= (vla-get-objectname nested_obj_) "AcDbSequenceEnd")
                            (= (vla-get-visible nested_obj_) :vlax-true)
                          )
                        (progn 
                          (setq nested_ename (vlax-vla-object->ename nested_obj_))
                          (setq nested_obj_getboundingbox (vla-getboundingbox nested_obj_ 'min_ 'max_)) 
                          (setq nested_min_ (vlax-safearray->list min_)) 
                          (setq nested_max_ (vlax-safearray->list max_)) 
                          (setq main_border_ (list nested_min_ nested_max_ ))
                          (setq main_border_assembly_ (cons (TA:assembly_coordinate_coner (list nested_min_ nested_max_ )   ) main_border_assembly_))
                          
                          (setq visible_list_ (ssadd (entlast) visible_list_))
                          (sslength visible_list_)
                        )
                      )
                      (setq nested (entnext nested))
                      
                    )
                  )
                )
                ;preloop_and_while
                  (setq main_border_assembly_i 0)
                  (setq dynamic_length_cut_list_ (list "3_PANEL-1" "3_PANEL-2" "3_PANEL-3"))
                  (setq dynamic_length_front_list_ (list "Front_3_PANEL-1" "Front_3_PANEL-2" "Front_3_PANEL-3" "Front_3_PANEL-4"))
                  (setq dynamic_length_new_front_list_ ())
                  (setq main_border_assembly_ (reverse main_border_assembly_))
                  (while (< main_border_assembly_i (length main_border_assembly_)) ;get dyn val for make front view 
                    (setq main_border_assembly_list_ (nth  main_border_assembly_i main_border_assembly_))
                    (setq dynamic_length_cut_list_val (nth  main_border_assembly_i dynamic_length_cut_list_))
                    (setq dynamic_length_front_list_val (nth  main_border_assembly_i dynamic_length_front_list_))
                    (LM:setdynpropvalue blk_obj_ dynamic_length_front_list_val (distance (car main_border_assembly_list_) (cadddr main_border_assembly_list_) ))
                    (setq dynamic_length_new_front_list_ (cons 
                                                          (cons dynamic_length_front_list_val 
                                                                (distance (car main_border_assembly_list_) (cadddr main_border_assembly_list_) ) 
                                                                
                                                          )
                                                          dynamic_length_new_front_list_
                                                        )
                    )
                    (setq main_border_assembly_i (+ main_border_assembly_i 1))
                  )
                  
                  (if (= keyword_value_detect nil)
                    (progn
                      (setq keyword_value_detect (TA:getkword "Insert new block ?"  "Yes" "No" "Y" "N" ) )
                    )
                  )
                  (cond 
                    ( ;_case_1
                      (and 
                        (= keyword_value_detect "Y")
                      )
                      (progn 
                        ;new_blk_entlast object
                        (vla-copy blk_obj_)
                        (setq new_front_blk_ename (entlast))
                        (setq new_front_blk_obj_ (vlax-ename->vla-object new_front_blk_ename))
                        (vla-move new_front_blk_obj_ 
                                  (vlax-3d-point (setq blk_obj_ins_ (vlax-safearray->list (vlax-variant-value (vla-get-insertionpoint blk_obj_) ) ) ) )
                                  (vlax-3d-point (getpoint blk_obj_ins_))
                        )
                        (LM:setdynpropvalue new_front_blk_obj_ "view" "3_front_view")
                        ;
                        (princ "_case_2")
                      )
                    )
                    ( ;_case_2
                      (and 
                        (= keyword_value_detect "N")
                      )
                      (progn 
                        ;new_blk_entlast object
                        (setq new_front_blk_ename (car (entsel "specify Object")))
                        (setq new_front_blk_obj_ (vlax-ename->vla-object new_front_blk_ename))
                        (LM:setdynpropvalue new_front_blk_obj_ "view" "3_front_view")
                        ;
                        (princ "_case_1")
                      )
                    )
                    ( ;_case_3 for selection set
                      (and 
                        (= keyword_value_detect "mode3")
                      )
                      (progn 
                        ;new_blk_entlast object
                        (vla-copy blk_obj_)
                        (setq new_front_blk_ename (entlast))
                        (setq new_front_blk_obj_ (vlax-ename->vla-object new_front_blk_ename))
                        (vla-move new_front_blk_obj_ 
                                  (vlax-3d-point (setq blk_obj_ins_ (vlax-safearray->list (vlax-variant-value (vla-get-insertionpoint blk_obj_) ) ) ) )
                                  (vlax-3d-point (list 
                                                  (car new_inspt_)
                                                  (cadr blk_obj_ins_)
                                                  (caddr blk_obj_ins_)
                                                )
                                  )
                        )
                        (LM:setdynpropvalue new_front_blk_obj_ "view" "3_front_view")
                        ;
                        (princ "_case_3")
                      )
                    )
                  )
                    
                  ;preloop_and_while
                    (setq dynamic_length_new_front_list_i 0)
                    (while (< dynamic_length_new_front_list_i (length dynamic_length_new_front_list_))
                      (setq dynamic_length_new_front_list_tag_ (car (nth  dynamic_length_new_front_list_i dynamic_length_new_front_list_)))
                      (setq dynamic_length_new_front_list_val_ (cdr (nth  dynamic_length_new_front_list_i dynamic_length_new_front_list_)))
                      (LM:setdynpropvalue new_front_blk_obj_ dynamic_length_new_front_list_tag_ dynamic_length_new_front_list_val_ )
                  
                      (setq dynamic_length_new_front_list_i (+ dynamic_length_new_front_list_i 1))
                    )
                  ;
                ;
              )
            )
          )
          (TA:solid_section-to-front ss_pre_filter_set_xx_obj_ "mode3" new_inspt_)
          (setq new_pre_filter_set_xx_ (ssadd (entlast) new_pre_filter_set_xx_ ))
          (setq ss_pre_filter_set_xx_i (+ ss_pre_filter_set_xx_i 1))
      )
  ;
  ;preloop_and_while
    (setq new_pre_filter_set_xx_i 0)
    (setq new_inspt_ (getpoint (setq expoint_ (vlax-safearray->list (vlax-variant-value (vla-get-insertionpoint (vlax-ename->vla-object (car (entsel "specify reference point")))))))) )
    (while (< new_pre_filter_set_xx_i (sslength new_pre_filter_set_xx_))
      (setq new_pre_filter_set_xx_ename_ (ssname new_pre_filter_set_xx_ new_pre_filter_set_xx_i))
      (setq new_pre_filter_set_xx_obj_ (vlax-ename->vla-object  new_pre_filter_set_xx_ename_))
      (LM:setdynpropvalue new_pre_filter_set_xx_obj_ "width_panel" (distance expoint_ (list (car new_inspt_ ) (cadr new_inspt_ ) (caddr new_inspt_ )) ))
      (setq new_pre_filter_set_xx_i (+ new_pre_filter_set_xx_i 1))
    )
  ;
)



(defun c:revex ()
  (setq rec_ename_ (car (entsel "specify Object")))
  (setq rec_obj_ (vlax-ename->vla-object rec_ename_))
  (setq assembly_val_ (TA:assembly_coordinate_coner (TA:Find_boundary_line_ rec_ename_ )))
  ;pt1
    (TA:vla-insertblock
      "000 - TRANSFER"
      (nth 2 assembly_val_)
      1
      (angle (nth 2 assembly_val_) (nth 3 assembly_val_))
    )
    ;new_blk_entlast object
      (setq new1_ename (entlast))
      (setq new1_obj_ (vlax-ename->vla-object new1_ename))
      (LM:setdynpropvalue new1_obj_ "TRANSFER_L" (+ (distance (nth 2 assembly_val_) (nth 3 assembly_val_)) 100))
    ;
  ;
  ;pt2
    (TA:vla-insertblock
      "000 - TRANSFER"
      (nth 1 assembly_val_)
      1
      (angle (nth 1 assembly_val_) (nth 0 assembly_val_))
    )
    ;new_blk_entlast object
      (setq new2_ename (entlast))
      (setq new2_obj_ (vlax-ename->vla-object new2_ename))
      (LM:setdynpropvalue new2_obj_ "TRANSFER_L" (+ (distance (nth 1 assembly_val_) (nth 0 assembly_val_)) 100))
    ;
  ;
  ;pt3
    (TA:vla-insertblock
      "000 - TRANSFER"
      (nth 2 assembly_val_)
      1
      (angle (nth 2 assembly_val_) (nth 1 assembly_val_))
    )
    ;new_blk_entlast object
      (setq new3_ename (entlast))
      (setq new3_obj_ (vlax-ename->vla-object new3_ename))
      (LM:setdynpropvalue new3_obj_ "TRANSFER_L" (- (distance (nth 2 assembly_val_) (nth 1 assembly_val_)) 50))
      (TA:move_polar_insertionpoint new3_obj_ "y" -75)
    ;
  ;
  ; ;pt4
  ;   (TA:vla-insertblock
  ;     "000 - TRANSFER"
  ;     (nth 3 assembly_val_)
  ;     1
  ;     (angle (nth 3 assembly_val_) (nth 0 assembly_val_))
  ;   )
  ;   ;new_blk_entlast object
  ;     (setq new4_ename (entlast))
  ;     (setq new4_obj_ (vlax-ename->vla-object new4_ename))
  ;     (LM:setdynpropvalue new4_obj_ "TRANSFER_L" (+ (distance (nth 3 assembly_val_) (nth 0 assembly_val_)) 50))
  ;     (TA:move_polar_insertionpoint new4_obj_ "y" -25)
  ;   ;
  ; ;
  
)
  

(defun c:Rotate-vertex-pline_rovxpl () ;สำหรับ
  ;1st process recrete vertex point
    (setq sss_ename_ (car (entsel "specify Object"))) 
    (setq sss_ename_entget_ (entget sss_ename_))
    (setq sss_obj_ (vlax-ename->vla-object sss_ename_))
    (setq i 0)
    (setq sss_ename_vertex_ (vl-remove-if-not '(lambda (x) (= 10 (car x))) sss_ename_entget_))
    (setq sss_ename_vertex_ (mapcar 'cdr sss_ename_vertex_))
    (setq sss_ename_vertex_list_ (mapcar 
                                  '(lambda (x) 
                                      (cons x (setq i (+ i 1)))
                                    )
                                  sss_ename_vertex_
                                )
    )
    ;TA:stanndard_lambda_sorting
      (setq sss_ename_vertex_list_sorted_ (vl-sort sss_ename_vertex_list_  ;bigest open indent list
                                                (function 
                                                  (lambda (a b) 
                                                    (< (nth 0 (car a)) (nth 0 (car b))) ;กำหนดจุดให้ทำงาน ซ้ายบนของ vertex ทั้งหมด
                                                  )
                                                )
                            ) ;bigest close indent list
      )
    ;
    ;preloop_and_while
      (setq xest_nopt_ (cdr (car sss_ename_vertex_list_sorted_)))
      (setq xest_new_ ())
      (setq xest_old_ ())
      (setq sss_ename_vertex_list_sorted_i 0)
      ;preloop_and_while
        (while (< sss_ename_vertex_list_sorted_i (length sss_ename_vertex_list_))
          (setq sss_ename_vertex_list_sorted_val_ (nth  sss_ename_vertex_list_sorted_i sss_ename_vertex_list_))
          (if (< sss_ename_vertex_list_sorted_i (- xest_nopt_ 1) )
            (progn
              (setq xest_new_ (cons sss_ename_vertex_list_sorted_val_ xest_new_ ))
            )
            (setq xest_old_ (cons sss_ename_vertex_list_sorted_val_ xest_old_ ))
          )
          (setq sss_ename_vertex_list_sorted_i (+ sss_ename_vertex_list_sorted_i 1))
        )
      ;
      (setq xest_new_ (reverse xest_new_)) 
      (setq xest_old_ (reverse xest_old_))
      (setq xest_all (append  xest_old_ xest_new_))
      (setq xest_all-1 (mapcar 
                        '(lambda (x) 
                          (car x) ;; ลบค่า cdr ของ x ออกจาก xest_all
                        )
                        xest_all ;; <- นี่คือลิสต์ที่เราจะวน
                      )
      )
      (setvar "osmode" 0)

      (create-plines xest_all-1 "close" )
      (setvar "osmode" 1215)
    ;
  ;
  ;new_blk_entlast object
    (command "erase" sss_ename_ "")
    (setq pline_ename (entlast))
    ; (if (= (setq check_val_ (check-clockwise xest_all-1)) "Counter-clockwise")
    ;   (progn
    ;     (command "reverse" pline_ename "" )
    ;   )
    ; )
  ;
  ;process
    (TA:assembly_coordinate_coner (TA:Find_boundary_line_ pline_ename))
  ;
)

(defun shoelace-area (pts / n sum xi yi xi1 yi1 term i)
  (setq n (length pts))
  (setq sum 0)
  (setq i 0)
  (while (< i n)
    (setq xi (car (nth i pts)))
    (setq yi (cadr (nth i pts)))
    (setq xi1 (car (nth (if (= i (- n 1)) 0 (1+ i)) pts)))
    (setq yi1 (cadr (nth (if (= i (- n 1)) 0 (1+ i)) pts)))
    
    (setq term (- (* xi yi1) (* xi1 yi)))
    (setq sum (+ sum term))
    (setq i (1+ i))
  )
  (/ sum 2)
)
(defun check-clockwise (pts / area)
  (setq area (shoelace-area pts))
  (if (< area 0)
    ; (alert (princ "\nClockwise"))
    (setq check_val_ "Clockwise")
    (if (> area 0)
      (setq check_val_ "Counter-clockwise")
    )
  )
)
(defun c:check-clock_pline_ckclpl_ ()
  (setq sss_ename_ (car (entsel "specify Object"))) 
  (setq sss_ename_entget_ (entget sss_ename_))
  (setq sss_obj_ (vlax-ename->vla-object sss_ename_))
  (setq i 0)
  (setq sss_ename_vertex_ (vl-remove-if-not '(lambda (x) (= 10 (car x))) sss_ename_entget_))
  (setq sss_ename_vertex_ (mapcar 'cdr sss_ename_vertex_))
  (check-clockwise sss_ename_vertex_)
)

;REwork_tittle_block
  (defun C:FL-LOGO ( )
    (setq line_color 7)
    (setq hatch_color 7)
    (setq hatches_ '())
    (setq blkdef (tblobjname "BLOCK" "FAMELINE - EXAMPLE PART 2025_20250912-111943_FAMELINE_LOGO"))
    (setq ent (entnext blkdef))
    (while ent
      (setq ed (entget ent))
      (if (= (cdr (assoc 0 ed)) "HATCH")
        (progn
          (setq hatches_ (cons ent hatches_))
          ;main idea of code keep or delete don't affect with core code
            (setq hatches_obj_ (vlax-ename->vla-object (cdr (assoc -1 ed))))
            (vla-put-color hatches_obj_  hatch_color)
            ; (vla-put-EntityTransparency hatches_obj_ 80 )
          ;
        )
      )
      (if (= (cdr (assoc 0 ed)) "ARC")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (if (= (cdr (assoc 0 ed)) "LINE")
        (progn
          ; (setq hatches_ (cons ent hatches_))
          ;main idea of code keep or delete don't affect with core code
            (setq hatches_obj_ (vlax-ename->vla-object (cdr (assoc -1 ed))))
            (if (/= (vla-get-layer hatches_obj_ ) "A-ANNO-SYMB")
              (progn
                (vla-put-color hatches_obj_  line_color)
              )
            )
          ;
        )
      )
      (if (= (cdr (assoc 0 ed)) "LWPOLYLINE")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (if (= (cdr (assoc 0 ed)) "SPLINE")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (if (= (cdr (assoc 0 ed)) "ELLIPSE")
        (progn
          ; (setq hatches_ (cons ent hatches_))
          ;main idea of code keep or delete don't affect with core code
            (setq hatches_obj_ (vlax-ename->vla-object (cdr (assoc -1 ed))))
            (vla-put-color hatches_obj_  line_color)
            
          ;
        )
      )
      (setq ent (entnext ent))
    )
    (reverse hatches)
  )
  (defun C:Rework_TTB_legend1 ( )
    (setq blk_list_ (list "TA-FL-CKST-TTB__20251003-150151LE6" "TA-FL-CKST-TTB__20251003-150158LE7" "TA-FL-CKST-TTB__20251003-150204LE8" "TA-FL-CKST-TTB__20251003-150213LE8"))
    ;preloop_and_while
      (setq blk_list_i 0)
      (while (< blk_list_i (length blk_list_))
        (setq blk_list_name_ (nth  blk_list_i blk_list_))
        ;
          (setq hatches_ '())
          (setq blkdef (tblobjname "BLOCK" blk_list_name_))
          (setq ent (entnext blkdef))
          (while ent
            (setq ed (entget ent))
            (if (= (cdr (assoc 0 ed)) "LWPOLYLINE")
              (progn
                ; (setq hatches_ (cons ent hatches_))
                ;main idea of code keep or delete don't affect with core code
                  (setq hatches_obj_ (vlax-ename->vla-object (cdr (assoc -1 ed))))
                  (if (= (vla-get-color hatches_obj_) 8 )
                    (progn
                      (vla-put-layer hatches_obj_  "Defpoints")
                    )
                  )
                  
                ;
              )
            )
            (setq ent (entnext ent))
          )
        ;
        (setq blk_list_i (+ blk_list_i 1))
      )
    ;
  )
  (defun C:REwork-TTB_legend2 ( )
    (setq blk_list_ (list "TA-FL-CKST-TTB__20251003-165007_PP17_V2"))
    ;preloop_and_while
      (setq blk_list_i 0)
      (while (< blk_list_i (length blk_list_))
        (setq blk_list_name_ (nth  blk_list_i blk_list_))
        ;
          (setq hatches_ '())
          (setq blkdef (tblobjname "BLOCK" blk_list_name_))
          (setq ent (entnext blkdef))
          (while ent
            (setq ed (entget ent))
            (if (= (cdr (assoc 0 ed)) "HATCH")
              (progn
                (setq hatches_ (cons ent hatches_))
                ;main idea of code keep or delete don't affect with core code
                  (setq hatches_obj_ (vlax-ename->vla-object (cdr (assoc -1 ed))))
                  (if (and 
                        (= (vla-get-layer hatches_obj_ ) "A-DETL-GENF")
                        (= (vla-get-color hatches_obj_ ) 7)
                      )
                    (progn
                      (vla-erase hatches_obj_)
                    )
                  )
                ;
              )
            )
            (setq ent (entnext ent))
          )
        ;
        (setq blk_list_i (+ blk_list_i 1))
      )
    ;
  )
  (defun C:REwork-TTB_legend3 ( )
    (setq blk_list_ (list "CVA-C2-P-PP00-TBKA1 (WD)$0$CVA-C2-P-OR00-TBKA1-WD" "CVA-C2-P-PP00-TBKA1 (WD)$0$CVA-C2-P-OR00-TBKA1-WD"))
    ;preloop_and_while
      (setq blk_list_i 0)
      (while (< blk_list_i (length blk_list_))
        (setq blk_list_name_ (nth  blk_list_i blk_list_))
        ;
          (setq hatches_ '())
          (setq blkdef (tblobjname "BLOCK" blk_list_name_))
          (setq ent (entnext blkdef))
          (while ent
            (setq ed (entget ent))
            (if (= (cdr (assoc 0 ed)) "TEXT")
              (progn
                (setq hatches_ (cons ent hatches_))
                ;main idea of code keep or delete don't affect with core code
                  (setq hatches_obj_ (vlax-ename->vla-object (cdr (assoc -1 ed))))
                  (if (and 
                        (= (vla-get-textstring hatches_obj_ ) "PURPLE LINE PROJECT")
                      )
                    (progn
                      (vla-put-color hatches_obj_ 7 )
                    )
                  )
                ;
              )
            )
            (setq ent (entnext ent))
          )
        ;
        (setq blk_list_i (+ blk_list_i 1))
      )
    ;
  )
  (defun C:REwork-TTB_legend4 ( )
    (setq blk_list_ (list "CVA-C2-P-PP00-TBKA1 (WD)$0$CVA-C2-P-OR00-TBKA1-WD"))
    ;preloop_and_while
      (setq blk_list_i 0)
      (while (< blk_list_i (length blk_list_))
        (setq blk_list_name_ (nth  blk_list_i blk_list_))
        ;
          (setq hatches_ '())
          (setq blkdef (tblobjname "BLOCK" blk_list_name_))
          (setq ent (entnext blkdef))
          (while ent
            (setq ed (entget ent))
            (if (= (cdr (assoc 0 ed)) "TEXT")
              (progn
                (setq hatches_ (cons ent hatches_))
                ;main idea of code keep or delete don't affect with core code
                  (setq hatches_obj_ (vlax-ename->vla-object (cdr (assoc -1 ed))))
                  (if (and 
                        (= (vla-get-textstring hatches_obj_ ) "PURPLE LINE PROJECT")
                      )
                    (progn
                      (vla-put-color hatches_obj_ 7 )
                    )
                  )
                ;
              )
            )
            (setq ent (entnext ent))
          )
        ;
        (setq blk_list_i (+ blk_list_i 1))
      )
    ;
  )
  (defun c:repairttb ()
    (C:FL-LOGO)

    (C:REwork-TTB_legend2)

    (C:REwork-TTB_legend4)
  )

;

(defun c:te1 ()
  ;presetting
    (setq replace_target_ "+3.00,+2.70")
    (setq replace_value_ "+3.30")
  ;
  ;selection_set_for_fillter_blk_name
    (if  ;pre_select_ssget_or_post_select_ssget
      (=
        (setq ss_pre_filter_set_xx_ (ssget "i"
                                          (list
                                            (cons 0 "MTEXT") ;type of object
                                            (cons 8 "G-ANNO-TEXT")   ;kind of layer
                                            (cons 1 replace_target_)   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "MTEXT") ;type of object
                                            (cons 8 "G-ANNO-TEXT")   ;kind of layer
                                            (cons 1 replace_target_)   ;kind of layer
                                            ; (cons 2 "000-GRID_LINE_DYN")       ;kind of nameblock
                                            ; (cons 62 1)           ;kind of color call sign with color code index
                                          )
                                    )
        )
      )
      (sslength ss_pre_filter_set_xx_)
    )
  ;
  (_startundo doc)
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (vla-put-textstring ss_pre_filter_set_xx_obj_ replace_value_) 
      (setq ss_pre_filter_set_xx_i (+ ss_pre_filter_set_xx_i 1))
    )
  ;
  (_endundo doc)
)
(defun c:xline_intersect_block_xl1_ ()
  ;presettting
    (setq blkname_inter_target_ ("A$C40eac883"))
    (setq match_layer_name_ "008 - E&M_ALARM_MAIN_COLOR_1")
    (setq match_color 256)
  ;
  ;selection_set_for_fillter_blk_name
    (if  ;pre_select_ssget_or_post_select_ssget
      (=
        (setq ss_pre_filter_set_xx_ (ssget "i"
                                          (list
                                            (cons 0 "xline") ;type of object
                                            ; (cons 8 "Defpoints")   ;kind of layer
                                            ; (cons 2 "000-GRID_LINE_DYN")       ;kind of nameblock
                                            ; (cons 62 6)           ;kind of color call sign with color code index
                                          )
                                    )
        )
        nil
      )
      (progn
        (setq ss_pre_filter_set_xx_ (ssget
                                          (list
                                            (cons 0 "xline") ;type of object
                                            ; (cons 8 "Defpoints")   ;kind of layer
                                            ; (cons 2 "000-GRID_LINE_DYN")       ;kind of nameblock
                                            (cons 62 1)           ;kind of color call sign with color code index
                                          )
                                    )
        )
      )
      (sslength ss_pre_filter_set_xx_)
    )
  ;
  (setq ss_pre_filter_set_xx_ename (ssname ss_pre_filter_set_xx_ 0 ))
  (setq ss_pre_filter_set_xx_obj_ (vlax-ename->vla-object ss_pre_filter_set_xx_ename))
  (setq ss_pre_filter_set_xx_obj_ins_ (vlax-safearray->list (vlax-variant-value (vla-get-basepoint ss_pre_filter_set_xx_obj_))))
  (setq ss_pre_filter_set_xx_obj_2ndins_ (vlax-safearray->list (vlax-variant-value (vla-get-SecondPoint  ss_pre_filter_set_xx_obj_))))
  (setq inters_list_ (LM:intersectionsinset  ss_pre_filter_set_xx_))
  (setq inters_ss_ (ssadd))
  (foreach x inters_list_
    (TA:vla-insertblock
      blkname_inter_target_
      x
      1
      0 ; (angle ss_pre_filter_set_xx_obj_ins_ ss_pre_filter_set_xx_obj_2ndins_)
    
    )
    ;new_blk_entlast object
      (setq new_dn_ename (entlast))
      (setq new_dn_obj (vlax-ename->vla-object new_dn_ename))
      (vla-put-layer new_dn_obj match_layer_name_)
      (vla-put-color new_dn_obj match_color)
    
      (LM:vl-setattributevalue new_dn_obj "1" "SD")
      (LM:vl-setattributevalue new_dn_obj "2" "R")
      (LM:vl-setattributevalue new_dn_obj "3" "A")
      (setq inters_ss_ (ssadd new_dn_ename inters_ss_))
    ;
  )
  (command "pselect"  inters_ss_ "" )
) 
(defun c:XL00 ()
  ;selection_set_for_fillter_blk_name
    (if  ;pre_select_ssget_or_post_select_ssget
      (=
        (setq xliness_ (ssget "i"
                                          (list
                                            (cons 0 "xline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq xliness_ (ssget
                                          (list
                                            (cons 0 "xline") ;type of object
                                            ; (cons 8 "000 - GRID")   ;kind of layer
                                            ; (cons 2 "000-GRID_LINE_DYN")       ;kind of nameblock
                                            ; (cons 62 1)           ;kind of color call sign with color code index
                                          )
                                    )
        )
      )
      (sslength xliness_)
    )
    
  ;
  ;preloop_and_while
    (setq xliness_i 0)
    (while (< xliness_i (sslength xliness_))
      (setq xliness_ename_ (ssname xliness_ xliness_i))
      (setq xliness_obj_ (vlax-ename->vla-object  xliness_ename_))
      (setq xline_obj_ xliness_obj_ )
      (TA:xline00 xliness_obj_)
      (TA:yline00 xliness_obj_)
      (setq xliness_i (+ xliness_i 1))
    )
  ;
)
(defun TA:xline00 (xline_obj_)
  
  (setq xline_obj_basept (vlax-safearray->list (vlax-variant-value (vla-get-basepoint xline_obj_))))
  (vla-put-basepoint
    xline_obj_
    (if (= (getvar "worlducs") 0)
      (progn
          (setq 1st_trans (list 
                            (LM:round (car (trans xline_obj_basept 0 1) ) )
                            (cadr (trans xline_obj_basept 0 1))
                            (LM:round (caddr (trans xline_obj_basept 0 1) ) )
                          )
          )
          (vlax-3d-point 
            (car (trans 1st_trans 1 0))
            (cadr (trans 1st_trans 1 0))
            0
          )
        
      )
      (vlax-3d-point 
        (LM:round  (car xline_obj_basept))
        (cadr xline_obj_basept)
        (TA:round-05 (caddr xline_obj_basept))
      )
    )
    
  )
  (vla-put-basepoint
    xline_obj_
    (if (= (getvar "worlducs") 0)
      (progn
          (setq 1st_trans (list 
                            (LM:round (car (trans xline_obj_basept 0 1) ) )
                            (cadr (trans xline_obj_basept 0 1))
                            (LM:round (caddr (trans xline_obj_basept 0 1) ) )
                          )
          )
          (vlax-3d-point 
            (car (trans 1st_trans 1 0))
            (cadr (trans 1st_trans 1 0))
            0
          )
        
      )
      (vlax-3d-point 
        (LM:round  (car xline_obj_basept))
        (cadr xline_obj_basept)
        (TA:round-05 (caddr xline_obj_basept))
      )
    )
    
  )
)
(defun TA:yline00 (xline_obj_)
  
  (setq xline_obj_basept (vlax-safearray->list (vlax-variant-value (vla-get-basepoint xline_obj_))))
  (vla-put-basepoint
    xline_obj_
    (if (= (getvar "worlducs") 0)
      (progn
          (setq 1st_trans (list 
                            (car (trans xline_obj_basept 0 1) )
                            (LM:round (cadr (trans xline_obj_basept 0 1)))
                            (LM:round (caddr (trans xline_obj_basept 0 1) ) )
                          )
          )
          (vlax-3d-point 
            (car (trans 1st_trans 1 0))
            (cadr (trans 1st_trans 1 0))
            0
          )
        
      )
      (vlax-3d-point 
        (car xline_obj_basept)
        (LM:round(cadr xline_obj_basept))
        (TA:round-05 (caddr xline_obj_basept))
      )
    )
    
  )
  (vla-put-basepoint
    xline_obj_
    (if (= (getvar "worlducs") 0)
      (progn
          (setq 1st_trans (list 
                            (car (trans xline_obj_basept 0 1) )
                            (LM:round (cadr (trans xline_obj_basept 0 1)))
                            (LM:round (caddr (trans xline_obj_basept 0 1) ) )
                          )
          )
          (vlax-3d-point 
            (car (trans 1st_trans 1 0))
            (cadr (trans 1st_trans 1 0))
            0
          )
        
      )
      (vlax-3d-point 
        (car xline_obj_basept)
        (LM:round(cadr xline_obj_basept))
        (TA:round-05 (caddr xline_obj_basept))
      )
    )
    
  )
)
(defun TA:xline00 (xline_obj_)
  
  (setq xline_obj_basept (vlax-safearray->list (vlax-variant-value (vla-get-basepoint xline_obj_))))
  (vla-put-basepoint
    xline_obj_
    (if (= (getvar "worlducs") 0)
      (progn
          (setq 1st_trans (list 
                            (LM:round (car (trans xline_obj_basept 0 1) ) )
                            (cadr (trans xline_obj_basept 0 1))
                            (LM:round (caddr (trans xline_obj_basept 0 1) ) )
                          )
          )
          (vlax-3d-point 
            (car (trans 1st_trans 1 0))
            (cadr (trans 1st_trans 1 0))
            0
          )
        
      )
      (vlax-3d-point 
        (LM:round  (car xline_obj_basept))
        (cadr xline_obj_basept)
        (TA:round-05 (caddr xline_obj_basept))
      )
    )
    
  )
  (vla-put-basepoint
    xline_obj_
    (if (= (getvar "worlducs") 0)
      (progn
          (setq 1st_trans (list 
                            (LM:round (car (trans xline_obj_basept 0 1) ) )
                            (cadr (trans xline_obj_basept 0 1))
                            (LM:round (caddr (trans xline_obj_basept 0 1) ) )
                          )
          )
          (vlax-3d-point 
            (car (trans 1st_trans 1 0))
            (cadr (trans 1st_trans 1 0))
            0
          )
        
      )
      (vlax-3d-point 
        (LM:round  (car xline_obj_basept))
        (cadr xline_obj_basept)
        (TA:round-05 (caddr xline_obj_basept))
      )
    )
    
  )
)
(defun TA:yline00 (xline_obj_)
  
  (setq xline_obj_basept (vlax-safearray->list (vlax-variant-value (vla-get-basepoint xline_obj_))))
  (vla-put-basepoint
    xline_obj_
    (if (= (getvar "worlducs") 0)
      (progn
          (setq 1st_trans (list 
                            (car (trans xline_obj_basept 0 1) )
                            (LM:round (cadr (trans xline_obj_basept 0 1)))
                            (LM:round (caddr (trans xline_obj_basept 0 1) ) )
                          )
          )
          (vlax-3d-point 
            (car (trans 1st_trans 1 0))
            (cadr (trans 1st_trans 1 0))
            0
          )
        
      )
      (vlax-3d-point 
        (car xline_obj_basept)
        (LM:round(cadr xline_obj_basept))
        (TA:round-05 (caddr xline_obj_basept))
      )
    )
    
  )
  (vla-put-basepoint
    xline_obj_
    (if (= (getvar "worlducs") 0)
      (progn
          (setq 1st_trans (list 
                            (car (trans xline_obj_basept 0 1) )
                            (LM:round (cadr (trans xline_obj_basept 0 1)))
                            (LM:round (caddr (trans xline_obj_basept 0 1) ) )
                          )
          )
          (vlax-3d-point 
            (car (trans 1st_trans 1 0))
            (cadr (trans 1st_trans 1 0))
            0
          )
        
      )
      (vlax-3d-point 
        (car xline_obj_basept)
        (LM:round(cadr xline_obj_basept))
        (TA:round-05 (caddr xline_obj_basept))
      )
    )
    
  )
)

(defun c:input_subfix_name_block ()
  (setq file_block_list_ (TA:get_name_block_in_drawing_to_list))
  ;preloop_and_while
    (setq file_block_list_i 0)
    (while (< file_block_list_i (length file_block_list_))
      (setq file_block_list_val_ (nth  file_block_list_i file_block_list_))
      (command "rename" "b" file_block_list_val_ (strcat file_block_list_val_ "_" "sub" ) )
  
      (setq file_block_list_i (+ file_block_list_i 1))
    )
  ;
)
(defun c:ssss_ss2 ()
  ;selection_set_for_fillter_blk_name
    (if  ;pre_select_ssget_or_post_select_ssget
      (=
        (setq ss_pre_filter_set_ssss_ (ssget "i"
            (list
              (cons 0 "line") ;type of object
              (cons 8 "A-WALL")   ;kind of layer
              ; (cons 2 "000-GRID_LINE_DYN")       ;kind of nameblock
              ; (cons 62 1)           ;kind of color call sign with color code index
            )
          )
        )
        nil
      )
      (progn
        (setq ss_pre_filter_set_ssss_ (ssget
            (list
              (cons 0 "line") ;type of object
              (cons 8 "A-WALL")   ;kind of layer
              ; (cons 2 "000-GRID_LINE_DYN")       ;kind of nameblock
              ; (cons 62 1)           ;kind of color call sign with color code index
            )
          )
        )
        (sslength ss_pre_filter_set_ssss_)
      )
    )
  ;
  (command "pselect"  ss_pre_filter_set_ssss_ "" )
)
(defun c:tee3 ()
  (setq blkname_inter_target_ "D2 - D2-18784047-4150-01 CONCOURSE LEVEL - REFLECTED CEILING PLAN")
  (setq sss (getpoint  "specify Object 1"))
  (setq koo (getpoint sss "specify Object 2"))
  (setq ss_pre_filter_set_ssssssssssasasass_ (ssget "W" sss koo
      (list
        (cons 0 "insert") ;type of object
        ; (cons 8 "Defpoints")   ;kind of layer
        ; (cons 2 "000-GRID_LINE_DYN")       ;kind of nameblock
        ; (cons 62 1)           ;kind of color call sign with color code index
      )
    )
  )
  
  (TA:vla-insertblock
    blkname_inter_target_
    (nth 4 (TA:assembly_coordinate_coner (list sss koo) ))
    1
    0
  )
  (command "erase" ss_pre_filter_set_ssssssssssasasass_ "")
)
  
(defun c:rrr1_ ()
  ;selection_set_for_fillter_blk_name
    (if  ;pre_select_ssget_or_post_select_ssget
      (=
        (setq ss_pre_filter_set_xx_filter_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_filter_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_filter_)
    )
  ;
  ; (setq ss_pre_filter_set_xx_filter_ (TA:EF_Filter_ss_set_V2_ ss_pre_filter_set_xx_ (list "L1-2 RECESSED FLUORESCENT - L1-2  RECESSED FLUORESCENT-14230294-CONCOURSE LEVEL_LIGHTING Copy 1")))
  ; (setq ss_pre_filter_set_xx_filter_length_ (sslength ss_pre_filter_set_xx_filter_ ))
  ;preloop_and_while
    (setq ss_pre_filter_set_xx_filter_i 0)
    (while (< ss_pre_filter_set_xx_filter_i (sslength ss_pre_filter_set_xx_filter_))
      (setq ss_pre_filter_set_xx_filter_ename_ (ssname ss_pre_filter_set_xx_filter_ ss_pre_filter_set_xx_filter_i))
      (setq ss_pre_filter_set_xx_filter_obj_ (vlax-ename->vla-object  ss_pre_filter_set_xx_filter_ename_))
      (setq ss_pre_filter_set_xx_filter_obj_ins_ (vlax-safearray->list (vlax-variant-value (vla-get-insertionpoint ss_pre_filter_set_xx_filter_obj_))))
      (setq ss_pre_filter_set_xx_filter_obj_ro (LM:round (rad-to-deg (vla-get-rotation ss_pre_filter_set_xx_filter_obj_))))
      (cond
        ( (and 
            (wcmatch (LM:effectivename ss_pre_filter_set_xx_filter_obj_) "*L1-2 RECESSED FLUORESCENT*")
              ( = ss_pre_filter_set_xx_filter_obj_ro 90)
            )
          (progn
            (TA:vla-insertblock 
              "000 - DYNAMIC_ARRAY+COMBINE+VIEW_ASSCESSORIES_TRAKC_LIGHT_REC.1257x120mm_COMBINE_SET"
              ss_pre_filter_set_xx_filter_obj_ins_
              1
              (vla-get-rotation ss_pre_filter_set_xx_filter_obj_)
            )
            ;new_blk_entlast object
              (setq newblk_ename (entlast))
              (setq newblk_obj_ (vlax-ename->vla-object newblk_ename))
              (LM:setdynpropvalue newblk_obj_ "view" "6_bottom_view")
              (TA:move_polar_insertionpoint newblk_obj_ "x" 52.50)
            ;
          )
        )
        ( (and 
            (wcmatch (LM:effectivename ss_pre_filter_set_xx_filter_obj_) "*L1-2 RECESSED FLUORESCENT*")
            ( = ss_pre_filter_set_xx_filter_obj_ro 180)
          )
          (progn
            (TA:vla-insertblock 
              "000 - DYNAMIC_ARRAY+COMBINE+VIEW_ASSCESSORIES_TRAKC_LIGHT_REC.1257x120mm_COMBINE_SET"
              ss_pre_filter_set_xx_filter_obj_ins_
              1
              (vla-get-rotation ss_pre_filter_set_xx_filter_obj_)
            )
            ;new_blk_entlast object
              (setq newblk_ename (entlast))
              (setq newblk_obj_ (vlax-ename->vla-object newblk_ename))
              (LM:setdynpropvalue newblk_obj_ "view" "6_bottom_view")
              (TA:move_polar_insertionpoint newblk_obj_ "x" 52.50)
            ;
          )
        )
        ( (and 
            (wcmatch (LM:effectivename ss_pre_filter_set_xx_filter_obj_) "*L1-2 RECESSED FLUORESCENT*")
            ( = ss_pre_filter_set_xx_filter_obj_ro 270)
          )
          (progn
            (TA:vla-insertblock 
              "000 - DYNAMIC_ARRAY+COMBINE+VIEW_ASSCESSORIES_TRAKC_LIGHT_REC.1257x120mm_COMBINE_SET"
              ss_pre_filter_set_xx_filter_obj_ins_
              1
              (vla-get-rotation ss_pre_filter_set_xx_filter_obj_)
            )
            ;new_blk_entlast object
              (setq newblk_ename (entlast))
              (setq newblk_obj_ (vlax-ename->vla-object newblk_ename))
              (LM:setdynpropvalue newblk_obj_ "view" "6_bottom_view")
              (TA:move_polar_insertionpoint newblk_obj_ "x" 52.50)
            ;
          )
        )
      )
      (setq ss_pre_filter_set_xx_filter_i (+ ss_pre_filter_set_xx_filter_i 1))
    )
  ;

  
)

(defun c:xl_to_block_xlblk ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ; (setq ss_pre_filter_set_xx_ (TA:EF_Filter_ss_set_ ss_pre_filter_set_xx_ (LM:effectivename (vlax-ename->vla-object (car (entsel "filter name block")))) ))
  (setq xxxxx (cond ( (getint (strcat "\nspecify get color \n<" (rtos (setq xxxxx (cond (xxxxx) (1.0) ) ) ) "> : " ) ) ) (xxxxx) ) )
  (setq ss_pre_filter_set_xx_ ss_pre_filter_set_xx_)
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins_ (vlax-safearray->list (vlax-variant-value (vla-get-insertionpoint ss_pre_filter_set_xx_obj_))))
      (if (= (vla-get-ActiveSpace (setq doc (vla-get-ActiveDocument (vlax-get-acad-object)))) acModelSpace) 
        ;; อยู่ใน Model Space
        (setq space (vla-get-ModelSpace doc))
        ;; ถ้าไม่ใช่ = อยู่ใน Paper Space ของ Layout
        (setq space (vla-get-PaperSpace doc))
      )
      (vla-addxline space 
        (vlax-3d-point ss_pre_filter_set_xx_obj_ins_)
        (vlax-3d-point (polar ss_pre_filter_set_xx_obj_ins_ (deg-to-rad xxxxx) 80))          

      )
      (setq ss_pre_filter_set_xx_i (+ ss_pre_filter_set_xx_i 1))
    )
  ;
)
(defun c:bolupins_TEMP ()
  ;selection_set_for_fillter_blk_name
    (if  ;pre_select_ssget_or_post_select_ssget
      (=
        (setq ss_bol_ (ssget "i"
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_bol_ (ssget
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
      )
      (sslength ss_bol_)
    )
  ;
  (setq ss_bol_assmbly_crood_ (TA:assembly_coordinate_coner (TA:ss_vla-getboundingbox ss_bol_)))
  (setq ss_bol_assmbly_crood_int_topleft_ (nth 0 ss_bol_assmbly_crood_))
  (setvar "osmode" 0)  
  (TA:vla-insertblock 
    "temp5temp5"
    ss_bol_assmbly_crood_int_topleft_
    1
    0
  )
  ;preloop_and_while
    (setq ss_bol_i 0)
    (while (< ss_bol_i (sslength ss_bol_))
      (setq ss_bol_ename_ (ssname ss_bol_ ss_bol_i))
      (setq ss_bol_obj_ (vlax-ename->vla-object  ss_bol_ename_))
      (vla-delete ss_bol_obj_)
      (setq ss_bol_i (+ ss_bol_i 1))
    )
  ;
  (setvar "osmode" 1215)
  
)
(defun c:boldownins_TEMP ()
  ;selection_set_for_fillter_blk_name
    (if  ;pre_select_ssget_or_post_select_ssget
      (=
        (setq ss_bol_ (ssget "i"
                                          (list
                                            (cons 0 "line") ;type of object
                                            (cons 8 "EC2")   ;kind of layer
                                            ; (cons 2 "000-GRID_LINE_DYN")       ;kind of nameblock
                                            ; (cons 62 1)           ;kind of color call sign with color code index
                                          )
                                    )
        )
        nil
      )
      (progn
        (setq ss_bol_ (ssget
                                          (list
                                            (cons 0 "line") ;type of object
                                            (cons 8 "EC2")   ;kind of layer
                                            ; (cons 2 "000-GRID_LINE_DYN")       ;kind of nameblock
                                            ; (cons 62 1)           ;kind of color call sign with color code index
                                          )
                                    )
        )
      )
      (sslength ss_bol_)
    )
  ;
  (setq ss_bol_assmbly_crood_ (TA:assembly_coordinate_coner (TA:ss_vla-getboundingbox ss_bol_)))
  (setq ss_bol_assmbly_crood_int_topleft_ (nth 3 ss_bol_assmbly_crood_))
  (setvar "osmode" 0)  
  (TA:vla-insertblock 
    "temp2temp4"
    ss_bol_assmbly_crood_int_topleft_
    1
    0
  )
  ;preloop_and_while
    (setq ss_bol_i 0)
    (while (< ss_bol_i (sslength ss_bol_))
      (setq ss_bol_ename_ (ssname ss_bol_ ss_bol_i))
      (setq ss_bol_obj_ (vlax-ename->vla-object  ss_bol_ename_))
      (vla-delete ss_bol_obj_)
      (setq ss_bol_i (+ ss_bol_i 1))
    )
  ;
  (setvar "osmode" 1215)
  
)

(defun c:bolmidins_TEMP ()
  ;selection_set_for_fillter_blk_name
    (if  ;pre_select_ssget_or_post_select_ssget
      (=
        (setq ss_bol_ (ssget "i"
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_bol_ (ssget
                                          (list
                                            (cons 0 "line") ;type of object
                                            ; (cons 8 "000 - GRID")   ;kind of layer
                                            ; (cons 2 "000-GRID_LINE_DYN")       ;kind of nameblock
                                            ; (cons 62 1)           ;kind of color call sign with color code index
                                          )
                                    )
        )
      )
      (sslength ss_bol_)
    )
  ;
  (setq ss_bol_assmbly_crood_ (TA:assembly_coordinate_coner (TA:ss_vla-getboundingbox ss_bol_)))
  (setq ss_bol_assmbly_crood_int_topleft_ (nth 3 ss_bol_assmbly_crood_))
  (setvar "osmode" 0)  
  (TA:vla-insertblock 
    "temp2temp4"
    ss_bol_assmbly_crood_int_topleft_
    1
    0
  )
  ;preloop_and_while
    (setq ss_bol_i 0)
    (while (< ss_bol_i (sslength ss_bol_))
      (setq ss_bol_ename_ (ssname ss_bol_ ss_bol_i))
      (setq ss_bol_obj_ (vlax-ename->vla-object  ss_bol_ename_))
      (vla-delete ss_bol_obj_)
      (setq ss_bol_i (+ ss_bol_i 1))
    )
  ;
  (setvar "osmode" 1215)
  
)
(defun c:enbopo ()
  (setq nnn_ename_ (car (nentsel "specify Object")))
  (setq nnn_obj_ (vlax-ename->vla-object nnn_ename_))
  (setq nnn_obj_getboundingbox (vla-getboundingbox nnn_obj_ 'min_ 'max_)) 
  (setq nnn_min_ (vlax-safearray->list min_)) 
  (setq nnn_max_ (vlax-safearray->list max_)) 
  (command "rectangle"  nnn_min_ nnn_max_)
  
)



(defun TA:editblock_ (blockname line_color layer_name)
  ; (setq blockname "PZG35")
  ; (setq line_color 256)
  ; (setq layer_name "008 - E&M_ACESSORIES_MAIN_COLOR_1")
  (setq target_ '())
  (setq blkdef (tblobjname "BLOCK" blockname))
  (setq ent (entnext blkdef))
  (while ent
    (setq ed (entget ent))
    (if (= (cdr (assoc 0 ed)) "HATCH")
      (progn
        (setq target_ (cons ent target_))
        ;main idea of code keep or delete don't affect with core code
          (setq target_obj_ (vlax-ename->vla-object (cdr (assoc -1 ed))))
          (vla-put-color target_obj_  line_color)
          (vla-put-layer target_obj_  layer_name)
          ; (vla-put-EntityTransparency target_obj_ 80 )
        ;
      )
    )
    (if (= (cdr (assoc 0 ed)) "ARC")
      (progn
        ; (setq target_ (cons ent target_))
        ;main idea of code keep or delete don't affect with core code
          (setq target_obj_ (vlax-ename->vla-object (cdr (assoc -1 ed))))
          (vla-put-color target_obj_  line_color)
          (vla-put-layer target_obj_  layer_name)
          
        ;
      )
    )
    (if (= (cdr (assoc 0 ed)) "LINE")
      (progn
        ; (setq target_ (cons ent target_))
        ;main idea of code keep or delete don't affect with core code
          (setq target_obj_ (vlax-ename->vla-object (cdr (assoc -1 ed))))
          (if (/= (vla-get-layer target_obj_ ) "A-ANNO-SYMB")
            (progn
              (vla-put-color target_obj_  line_color)
              (vla-put-layer target_obj_  layer_name)
            )
          )
        ;
      )
    )
    (if (= (cdr (assoc 0 ed)) "LWPOLYLINE")
      (progn
        ; (setq target_ (cons ent target_))
        ;main idea of code keep or delete don't affect with core code
          (setq target_obj_ (vlax-ename->vla-object (cdr (assoc -1 ed))))
          (vla-put-color target_obj_  line_color)
          (vla-put-layer target_obj_  layer_name)
          
        ;
      )
    )
    (if (= (cdr (assoc 0 ed)) "SPLINE")
      (progn
        ; (setq target_ (cons ent target_))
        ;main idea of code keep or delete don't affect with core code
          (setq target_obj_ (vlax-ename->vla-object (cdr (assoc -1 ed))))
          (vla-put-color target_obj_  line_color)
          (vla-put-layer target_obj_  layer_name)
          
        ;
      )
    )
    (if (= (cdr (assoc 0 ed)) "ELLIPSE")
      (progn
        ; (setq target_ (cons ent target_))
        ;main idea of code keep or delete don't affect with core code
          (setq target_obj_ (vlax-ename->vla-object (cdr (assoc -1 ed))))
          (vla-put-color target_obj_  line_color)
          (vla-put-layer target_obj_  layer_name)
          
        ;
      )
    )
    (if (= (cdr (assoc 0 ed)) "CIRCLE")
      (progn
        ; (setq target_ (cons ent target_))
        ;main idea of code keep or delete don't affect with core code
          (setq target_obj_ (vlax-ename->vla-object (cdr (assoc -1 ed))))
          (vla-put-color target_obj_  line_color)
          (vla-put-layer target_obj_  layer_name)
          
        ;
      )
    )
    (if (= (cdr (assoc 0 ed)) "TEXT")
      (progn
        ; (setq target_ (cons ent target_))
        ;main idea of code keep or delete don't affect with core code
          (setq target_obj_ (vlax-ename->vla-object (cdr (assoc -1 ed))))
          (vla-put-color target_obj_  line_color)
          (vla-put-layer target_obj_  layer_name)
          
        ;
      )
    )
    (setq ent (entnext ent))
  )
  (reverse target)
)


(defun c:mkcanopy()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "A-CANOPY")
          )
        )
      (setq ss_pre_filter_set_xx_i (+ ss_pre_filter_set_xx_i 1))
    ) 
  ;
)
(defun c:mkEM()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "008 - E&M_ACESSORIES_MAIN_COLOR_1")
          )
        )
      (setq ss_pre_filter_set_xx_i (+ ss_pre_filter_set_xx_i 1))
    ) 
  ;
)
(defun c:mkcsem ()
  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (if (or 
            (= (vla-get-objectname ss_pre_filter_set_xx_obj_ ) "AcDbPolyline"  )
            (= (vla-get-objectname ss_pre_filter_set_xx_obj_ ) "AcDbLine"  )
          )
        (progn
          (vla-put-layer ss_pre_filter_set_xx_obj_ "008 - E&M_ACESSORIES_SUB_COLOR_1" )
          (vla-put-color ss_pre_filter_set_xx_obj_ 256)
        )
      )
      (if (or 
            (= (vla-get-objectname ss_pre_filter_set_xx_obj_ ) "AcDbMText"  )
            (= (vla-get-objectname ss_pre_filter_set_xx_obj_ ) "AcDbText"  )
          )
        (progn
          (vla-put-layer ss_pre_filter_set_xx_obj_ "008 - E&M_ACESSORIES_TEXT" )
          (vla-put-color ss_pre_filter_set_xx_obj_ 256)
        )
      )
      (setq ss_pre_filter_set_xx_i (+ ss_pre_filter_set_xx_i 1))
    )
  ;
)
(defun c:mkalarm()

  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "008 - E&M_ALARM_MAIN_COLOR_1")
          )
        )
      (setq ss_pre_filter_set_xx_i (+ ss_pre_filter_set_xx_i 1))
    ) 
  ;
)
(defun c:mklight()

  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "008 - E&M_ACESSORIES_MAIN_COLOR_1")
          )
        )
      (setq ss_pre_filter_set_xx_i (+ ss_pre_filter_set_xx_i 1))
    ) 
  ;
)
(defun c:mkflu()
  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (vlax-get-property   ss_pre_filter_set_xx_obj_ 'EffectiveName) 256 "008 - LIGHT_FLUORESCENT_MAIN_COLOR_1")
          )
        )
      (setq ss_pre_filter_set_xx_i (+ ss_pre_filter_set_xx_i 1))
    ) 
  ;
)
(defun c:mkdn()

  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "008 - LIGHT_DN_MAIN_COLOR_1")
          )
        )
      (setq ss_pre_filter_set_xx_i (+ ss_pre_filter_set_xx_i 1))
    ) 
  ;
)
(defun c:mkair1()
  (defun TAS:editair_ (blockname line_color layer_name)
    ; (setq blockname "PZG35")
    ; (setq line_color 256)
    ; (setq layer_name "008 - E&M_ACESSORIES_MAIN_COLOR_1")
    (setq target_ '())
    (setq blkdef (tblobjname "BLOCK" blockname))
    (setq ent (entnext blkdef))
    (while ent
      (setq ed (entget ent))
      (if (= (cdr (assoc 0 ed)) "HATCH")
        (progn
          (setq target_ (cons ent target_))
          ;main idea of code keep or delete don't affect with core code
            (setq target_obj_ (vlax-ename->vla-object (cdr (assoc -1 ed))))
            (vla-put-color target_obj_  line_color)
            (vla-put-layer target_obj_  layer_name)
            ; (vla-put-EntityTransparency target_obj_ 80 )
          ;
        )
      )
      (if (= (cdr (assoc 0 ed)) "ARC")
        (progn
          ; (setq target_ (cons ent target_))
          ;main idea of code keep or delete don't affect with core code
            (setq target_obj_ (vlax-ename->vla-object (cdr (assoc -1 ed))))
            (vla-put-color target_obj_  line_color)
            (vla-put-layer target_obj_  layer_name)
            
          ;
        )
      )
      (if (= (cdr (assoc 0 ed)) "LINE")
        (progn
          ; (setq target_ (cons ent target_))
          ;main idea of code keep or delete don't affect with core code
            (setq target_obj_ (vlax-ename->vla-object (cdr (assoc -1 ed))))
            (if (/= (vla-get-layer target_obj_ ) "A-ANNO-SYMB")
              (progn
                (vla-put-color target_obj_  line_color)
                (vla-put-layer target_obj_  "008 - AIR_MASK_SUB_COLOR_3")
              )
            )
          ;
        )
      )
      (if (= (cdr (assoc 0 ed)) "LWPOLYLINE")
        (progn
          ; (setq target_ (cons ent target_))
          ;main idea of code keep or delete don't affect with core code
            (setq target_obj_ (vlax-ename->vla-object (cdr (assoc -1 ed))))
            (vla-put-color target_obj_  line_color)
            (vla-put-layer target_obj_  layer_name)
            
          ;
        )
      )
      (if (= (cdr (assoc 0 ed)) "SPLINE")
        (progn
          ; (setq target_ (cons ent target_))
          ;main idea of code keep or delete don't affect with core code
            (setq target_obj_ (vlax-ename->vla-object (cdr (assoc -1 ed))))
            (vla-put-color target_obj_  line_color)
            (vla-put-layer target_obj_  layer_name)
            
          ;
        )
      )
      (if (= (cdr (assoc 0 ed)) "ELLIPSE")
        (progn
          ; (setq target_ (cons ent target_))
          ;main idea of code keep or delete don't affect with core code
            (setq target_obj_ (vlax-ename->vla-object (cdr (assoc -1 ed))))
            (vla-put-color target_obj_  line_color)
            (vla-put-layer target_obj_  layer_name)
            
          ;
        )
      )
      (if (= (cdr (assoc 0 ed)) "CIRCLE")
        (progn
          ; (setq target_ (cons ent target_))
          ;main idea of code keep or delete don't affect with core code
            (setq target_obj_ (vlax-ename->vla-object (cdr (assoc -1 ed))))
            (vla-put-color target_obj_  line_color)
            (vla-put-layer target_obj_  layer_name)
            
          ;
        )
      )
      (setq ent (entnext ent))
    )
    (reverse target)
  )
  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TAS:editair_ (LM:effectivename ss_pre_filter_set_xx_obj_) 256 "008 - AIR_MASK_MAIN_COLOR_1")
            (TA:editblock_ (LM:effectivename ss_pre_filter_set_xx_obj_) 256 "008 - AIR_MASK_MAIN_COLOR_1")
          )
        )
      (setq ss_pre_filter_set_xx_i (+ ss_pre_filter_set_xx_i 1))
    ) 
  ;
)
(defun c:mksko()

  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "000_PPLINE_CKST_SMOKE_ACESSORIES_SUB_COLOR_2")
            (vla-put-layer ss_pre_filter_set_xx_obj_ "0")
          )
        )
      (setq ss_pre_filter_set_xx_i (+ ss_pre_filter_set_xx_i 1))
    ) 
  ;
)
(defun c:mkspk ()
  ;selection_set_for_fillter_blk_name
    (if  ;pre_select_ssget_or_post_select_ssget
      (=
        (setq ss_pre_filter_set_xx_ (ssget "i"
                                          (list
                                            (cons 0 "INSERT,arc,circle,line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,arc,circle,line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq ss_pre_filter_set_xx_obj_center_ins_ nil)
    (setq end t )
    (while (and 
             (< ss_pre_filter_set_xx_i (sslength ss_pre_filter_set_xx_))
             (= end t)
           )
      (setq ss_pre_filter_set_xx_ename_ (ssname ss_pre_filter_set_xx_ ss_pre_filter_set_xx_i))
      (setq ss_pre_filter_set_xx_obj_ (vlax-ename->vla-object  ss_pre_filter_set_xx_ename_))
      (if (or 
            (= (vla-get-objectname ss_pre_filter_set_xx_obj_ ) "AcDbCircle")
            (= (vla-get-objectname ss_pre_filter_set_xx_obj_ ) "AcDbArc")
          )
        (progn
          (setq ss_pre_filter_set_xx_obj_center_ins_ (vlax-safearray->list (vlax-variant-value (vla-get-center ss_pre_filter_set_xx_obj_ ))))
          (setq end nil)
        )
      )
      (setq ss_pre_filter_set_xx_i (+ ss_pre_filter_set_xx_i 1))
    )
  ;
  ;insert process
    (if (/= ss_pre_filter_set_xx_obj_center_ins_ nil)
      (progn
        (TA:vla-insertblock 
          "000 - CKST_E&M_SPRINKLER_HEAD"
          ss_pre_filter_set_xx_obj_center_ins_
          1
          0
        )
      )
    )
  ;
  (TA:ss-erase ss_pre_filter_set_xx_)
)
(defun c:mkEXCL()

  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "A-GLAZ-CURT")
          )
        )
      (setq ss_pre_filter_set_xx_i (+ ss_pre_filter_set_xx_i 1))
    ) 
  ;
)    
(defun c:ASPGmkfas ()

  ;selection_set_for_fillter_blk_name
    (if  ;pre_select_ssget_or_post_select_ssget
      (=
        (setq ss_pre_filter_set_xx_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "010 - ASPG_FASTERN_MAIN_COLOR_1")
          )
        )
      (setq ss_pre_filter_set_xx_i (+ ss_pre_filter_set_xx_i 1))
    ) 
  ;
)    
(defun c:mkhideDEF0 ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "000 - 0_HIDE_OBJ_FRAMING_DEF_SUB")
          )
          
        )
      (setq ss_pre_filter_set_xx_i (+ ss_pre_filter_set_xx_i 1))
    ) 
  ;
)    
(defun c:mkhideDEF1 ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "000 - 0_HIDE_OBJ_FRAMING_DEF_SUB_1")
          )
        )
      (setq ss_pre_filter_set_xx_i (+ ss_pre_filter_set_xx_i 1))
    ) 
  ;
)    
(defun c:mkLac10s2 ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "010 - SOLID_10_PANEL_SUB_COLOR_2")
          )
        )
      (setq ss_pre_filter_set_xx_i (+ ss_pre_filter_set_xx_i 1))
    ) 
  ;
)    
(defun c:mkLac10s3 ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "010 - SOLID_10_PANEL_SUB_COLOR_3")
          )
        )
      (setq ss_pre_filter_set_xx_i (+ ss_pre_filter_set_xx_i 1))
    ) 
  ;
)    
(defun c:mktemp10 ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "010 - SOLID_10_FASTERN_SUB_COLOR_3")
          )
        )
      (setq ss_pre_filter_set_xx_i (+ ss_pre_filter_set_xx_i 1))
    ) 
  ;
)    
(defun c:mkc06 ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "009 - AHP_06_PANEL_MAIN_COLOR_1")
              
          )
        )
      (setq ss_pre_filter_set_xx_i (+ ss_pre_filter_set_xx_i 1))
    ) 
  ;
)    
(defun c:mksmok_ac ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "000_PPLINE_CKST_SMOKE_ACESSORIES_MAIN_COLOR")
              
          )
        )
      (setq ss_pre_filter_set_xx_i (+ ss_pre_filter_set_xx_i 1))
    ) 
  ;
)    
(defun c:mksmok_M ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "000_PPLINE_CKST_SMOKE_GLASS_FIN_MAIN_COLOR")
              
          )
        )
      (setq ss_pre_filter_set_xx_i (+ ss_pre_filter_set_xx_i 1))
    ) 
  ;
)  
(defun c:mkdefpoints ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "Defpoints")
              
          )
        )
      (setq ss_pre_filter_set_xx_i (+ ss_pre_filter_set_xx_i 1))
    ) 
  ;
)
(defun TAS:editsteel_ (blockname line_color layer_name line_linetype)
  ; (setq blockname "A$Cd76d3661")
  ; (setq line_color 256)
  ; (setq layer_name "*A21941098")
  (setq target_ '())
  (setq blkdef (tblobjname "BLOCK" blockname))
  (setq ent (entnext blkdef))
  (while ent
    (setq ed (entget ent))
    (if (= (cdr (assoc 0 ed)) "HATCH")
      (progn
        (setq target_ (cons ent target_))
        ;main idea of code keep or delete don't affect with core code
          (setq target_obj_ (vlax-ename->vla-object (cdr (assoc -1 ed))))
          (vla-put-linetype target_obj_  line_linetype)
          (vla-put-color target_obj_  line_color)
          (vla-put-layer target_obj_  layer_name)
          ; (vla-put-EntityTransparency target_obj_ 80 )
        ;
      )
    )
    (if (= (cdr (assoc 0 ed)) "ARC")
      (progn
        ; (setq target_ (cons ent target_))
        ;main idea of code keep or delete don't affect with core code
          (setq target_obj_ (vlax-ename->vla-object (cdr (assoc -1 ed))))
          (vla-put-linetype target_obj_  line_linetype)
          (vla-put-color target_obj_  line_color)
          (vla-put-layer target_obj_  layer_name)
          
        ;
      )
    )
    (if (= (cdr (assoc 0 ed)) "LINE")
      (progn
        ; (setq target_ (cons ent target_))
        ;main idea of code keep or delete don't affect with core code
          (setq target_obj_ (vlax-ename->vla-object (cdr (assoc -1 ed))))
          (if (/= (vla-get-layer target_obj_ ) "A-ANNO-SYMB")
            (progn
              (vla-put-linetype target_obj_  line_linetype)
              (vla-put-color target_obj_  line_color)
              (vla-put-layer target_obj_  layer_name)
            )
          )
        ;
      )
    )
    (if (= (cdr (assoc 0 ed)) "LWPOLYLINE")
      (progn
        ; (setq target_ (cons ent target_))
        ;main idea of code keep or delete don't affect with core code
          (setq target_obj_ (vlax-ename->vla-object (cdr (assoc -1 ed))))
          (vla-put-linetype target_obj_  line_linetype)
          (vla-put-color target_obj_  line_color)
          (vla-put-layer target_obj_  layer_name)
          
        ;
      )
    )
    (if (= (cdr (assoc 0 ed)) "SPLINE")
      (progn
        ; (setq target_ (cons ent target_))
        ;main idea of code keep or delete don't affect with core code
          (setq target_obj_ (vlax-ename->vla-object (cdr (assoc -1 ed))))
          (vla-put-linetype target_obj_  line_linetype)
          (vla-put-color target_obj_  line_color)
          (vla-put-layer target_obj_  layer_name)
          
        ;
      )
    )
    (if (= (cdr (assoc 0 ed)) "ELLIPSE")
      (progn
        ; (setq target_ (cons ent target_))
        ;main idea of code keep or delete don't affect with core code
          (setq target_obj_ (vlax-ename->vla-object (cdr (assoc -1 ed))))
          (vla-put-linetype target_obj_  line_linetype)
          (vla-put-color target_obj_  line_color)
          (vla-put-layer target_obj_  layer_name)
          
        ;
      )
    )
    (if (= (cdr (assoc 0 ed)) "CIRCLE")
      (progn
        ; (setq target_ (cons ent target_))
        ;main idea of code keep or delete don't affect with core code
          (setq target_obj_ (vlax-ename->vla-object (cdr (assoc -1 ed))))
          (vla-put-linetype target_obj_  line_linetype)
          (vla-put-color target_obj_  line_color)
          (vla-put-layer target_obj_  layer_name)
          
        ;
      )
    )
    (setq ent (entnext ent))
  )
  (reverse target)
)
(defun c:mksteel ()
  (defun TAS:editsteel_ (blockname line_color layer_name line_linetype)
    ; (setq blockname "A$Cd76d3661")
    ; (setq line_color 256)
    ; (setq layer_name "*A21941098")
    (setq target_ '())
    (setq blkdef (tblobjname "BLOCK" blockname))
    (setq ent (entnext blkdef))
    (while ent
      (setq ed (entget ent))
      (if (= (cdr (assoc 0 ed)) "HATCH")
        (progn
          (setq target_ (cons ent target_))
          ;main idea of code keep or delete don't affect with core code
            (setq target_obj_ (vlax-ename->vla-object (cdr (assoc -1 ed))))
            (vla-put-linetype target_obj_  line_linetype)
            (vla-put-color target_obj_  line_color)
            (vla-put-layer target_obj_  layer_name)
            ; (vla-put-EntityTransparency target_obj_ 80 )
          ;
        )
      )
      (if (= (cdr (assoc 0 ed)) "ARC")
        (progn
          ; (setq target_ (cons ent target_))
          ;main idea of code keep or delete don't affect with core code
            (setq target_obj_ (vlax-ename->vla-object (cdr (assoc -1 ed))))
            (vla-put-linetype target_obj_  line_linetype)
            (vla-put-color target_obj_  line_color)
            (vla-put-layer target_obj_  layer_name)
            
          ;
        )
      )
      (if (= (cdr (assoc 0 ed)) "LINE")
        (progn
          ; (setq target_ (cons ent target_))
          ;main idea of code keep or delete don't affect with core code
            (setq target_obj_ (vlax-ename->vla-object (cdr (assoc -1 ed))))
            (if (/= (vla-get-layer target_obj_ ) "A-ANNO-SYMB")
              (progn
                (vla-put-linetype target_obj_  line_linetype)
                (vla-put-color target_obj_  line_color)
                (vla-put-layer target_obj_  layer_name)
              )
            )
          ;
        )
      )
      (if (= (cdr (assoc 0 ed)) "LWPOLYLINE")
        (progn
          ; (setq target_ (cons ent target_))
          ;main idea of code keep or delete don't affect with core code
            (setq target_obj_ (vlax-ename->vla-object (cdr (assoc -1 ed))))
            (vla-put-linetype target_obj_  line_linetype)
            (vla-put-color target_obj_  line_color)
            (vla-put-layer target_obj_  layer_name)
            
          ;
        )
      )
      (if (= (cdr (assoc 0 ed)) "SPLINE")
        (progn
          ; (setq target_ (cons ent target_))
          ;main idea of code keep or delete don't affect with core code
            (setq target_obj_ (vlax-ename->vla-object (cdr (assoc -1 ed))))
            (vla-put-linetype target_obj_  line_linetype)
            (vla-put-color target_obj_  line_color)
            (vla-put-layer target_obj_  layer_name)
            
          ;
        )
      )
      (if (= (cdr (assoc 0 ed)) "ELLIPSE")
        (progn
          ; (setq target_ (cons ent target_))
          ;main idea of code keep or delete don't affect with core code
            (setq target_obj_ (vlax-ename->vla-object (cdr (assoc -1 ed))))
            (vla-put-linetype target_obj_  line_linetype)
            (vla-put-color target_obj_  line_color)
            (vla-put-layer target_obj_  layer_name)
            
          ;
        )
      )
      (if (= (cdr (assoc 0 ed)) "CIRCLE")
        (progn
          ; (setq target_ (cons ent target_))
          ;main idea of code keep or delete don't affect with core code
            (setq target_obj_ (vlax-ename->vla-object (cdr (assoc -1 ed))))
            (vla-put-linetype target_obj_  line_linetype)
            (vla-put-color target_obj_  line_color)
            (vla-put-layer target_obj_  layer_name)
            
          ;
        )
      )
      (setq ent (entnext ent))
    )
    (reverse target)
  )
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TAS:editsteel_ (LM:effectivename ss_pre_filter_set_xx_obj_) 256 "000 - STRUCTURE_STEEL_FRAMING_MAIN_COLOR_2" "byblock")
              
          )
        )
      (setq ss_pre_filter_set_xx_i (+ ss_pre_filter_set_xx_i 1))
    ) 
  ;
)
(defun c:mksteelstructure ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TAS:editsteel_ (LM:effectivename ss_pre_filter_set_xx_obj_) 256 "000 - STRUCTURE_STEEL_FRAMING_SUB_COLOR_1" "bylayer")
              
          )
        )
      (setq ss_pre_filter_set_xx_i (+ ss_pre_filter_set_xx_i 1))
    ) 
  ;
)
(defun c:mksteelbk ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TAS:editsteel_ (LM:effectivename ss_pre_filter_set_xx_obj_) 256 "000 - STRUCTURE_STEEL_ACCESORIES_SUB_COLOR_2" "bylayer")
              
          )
        )
      (setq ss_pre_filter_set_xx_i (+ ss_pre_filter_set_xx_i 1))
    ) 
  ;
)
(defun c:mkdefpoints ()

  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
        (if (and 
              (= 1 1) 
              ; (= (wcmatch (LM:effectivename ss_pre_filter_set_xx_obj_) "*Alarm*") T)
            )
          (progn
            (TA:editblock_ (LM:effectivename ss_pre_filter_set_xx_obj_) 256 "000 - STRUCTURE_STEEL_FRAMING_MAIN_COLOR_2")
              
          )
        )
      (setq ss_pre_filter_set_xx_i (+ ss_pre_filter_set_xx_i 1))
    ) 
  ;
)












(defun C:showlight  ()
  (setq layer_list_ (TA:get_name_layer_in_drawing))
  (TA:interface_text_ T)
  ;preloop_and_while
    (setq layer_list_i 0)
    (command "vplayer" 
              "f" 
              "E-LITE-EQPM"
              "c" 
              ""
    )
    (command "vplayer" 
              "f" 
              "A-ANNO-DIMS-100"
              "c" 
              ""
    )
    (while (< layer_list_i (length layer_list_))
      (setq layer_list_ename_ (nth  layer_list_i layer_list_))
      (cond
        (;_case_1
          (and
              (= 1 1)
              (= (wcmatch layer_list_ename_ "008 - E&M*") t)
          )
          (progn
            (command "vplayer" 
                      "c" 
                      "T" 
                      "0,0,255" 
                      layer_list_ename_
                      "c"
                      ""
            )
            (princ "_case_1")
          )
        )
        (;_case_2
          (and
              (= 1 1)
              (= (wcmatch layer_list_ename_ "008 - LIGHT_*") t)
          )
          (progn
            (command "vplayer" 
                      "c" 
                      "T" 
                      "0,255,0" 
                      layer_list_ename_
                      "c"
                      ""
            )
            (princ "_case_2")
          )
        )
        (;_case_3
          (and
              (= 1 1)
              (= (wcmatch layer_list_ename_ "008 - AIR_MASK*") t)
          )
          (progn
            (command "vplayer" 
                      "c" 
                      "T" 
                      "255,0,0" 
                      layer_list_ename_
                      "c"
                      ""
            )
            (princ "_case_3")
          )
        )
        
      )
      (TA:textscr_process_V2 "sorting" layer_list_i layer_list_ )
      (setq layer_list_i (+ layer_list_i 1))
    )
)
(defun C:redlight  ()
  (setq color_val_ 1)
  (setq layer_list_ (TA:get_name_layer_in_drawing))
  (TA:interface_text_ T)
  ;preloop_and_while
    (setq layer_list_i 0)
    (while (< layer_list_i (length layer_list_))
      (setq layer_list_ename_ (nth  layer_list_i layer_list_))
      (cond
        (;_case_1
          (and
              (= 1 1)
              (= (wcmatch layer_list_ename_ "008 - E&M*") t)
          )
          (progn
            (command "vplayer" 
                      "c" 
                      color_val_
                      layer_list_ename_
                      "c"
                      ""
            )
            (princ "_case_1")
          )
        )
        (;_case_2
          (and
              (= 1 1)
              (= (wcmatch layer_list_ename_ "008 - LIGHT_*") t)
          )
          (progn
            (command "vplayer" 
                      "c" 
                      color_val_
                      layer_list_ename_
                      "c"
                      ""
            )
            (princ "_case_2")
          )
        )
        (;_case_3
          (and
              (= 1 1)
              (= (wcmatch layer_list_ename_ "008 - AIR_MASK*") t)
          )
          (progn
            (command "vplayer" 
                      "c" 
                      color_val_
                      layer_list_ename_
                      "c"
                      ""
            )
            (princ "_case_3")
          )
        )
        
      )
      (TA:textscr_process_V2 "sorting" layer_list_i layer_list_ )
      (setq layer_list_i (+ layer_list_i 1))
    )
)
; (defun C:yellight  ()
;   (setq color_val_ 2)
;   (setq layer_list_ (TA:get_name_layer_in_drawing))
;   (TA:interface_text_ T)
;   ;preloop_and_while
;     (setq layer_list_i 0)
;     (while (< layer_list_i (length layer_list_))
;       (setq layer_list_ename_ (nth  layer_list_i layer_list_))
;       (cond
;         (;_case_1
;           (and
;               (= 1 1)
;               (= (wcmatch layer_list_ename_ "008 - E&M*") t)
;           )
;           (progn
;             (command "vplayer" 
;                       "c" 
;                       color_val_
;                       layer_list_ename_
;                       "c"
;                       ""
;             )
;             (princ "_case_1")
;           )
;         )
;         (;_case_2
;           (and
;               (= 1 1)
;               (= (wcmatch layer_list_ename_ "008 - LIGHT_*") t)
;           )
;           (progn
;             (command "vplayer" 
;                       "c" 
;                       color_val_
;                       layer_list_ename_
;                       "c"
;                       ""
;             )
;             (princ "_case_2")
;           )
;         )
;         (;_case_3
;           (and
;               (= 1 1)
;               (= (wcmatch layer_list_ename_ "008 - AIR_MASK*") t)
;           )
;           (progn
;             (command "vplayer" 
;                       "c" 
;                       color_val_
;                       layer_list_ename_
;                       "c"
;                       ""
;             )
;             (princ "_case_3")
;           )
;         )
        
;       )
;       (TA:textscr_process_V2 "sorting" layer_list_i layer_list_ )
;       (setq layer_list_i (+ layer_list_i 1))
;     )
; )
(defun C:droplight  ()
  (setq color_val_ 251)
  (setq layer_list_ (TA:get_name_layer_in_drawing))
  (TA:interface_text_ T)
  ;preloop_and_while
    (setq layer_list_i 0)
    (while (< layer_list_i (length layer_list_))
      (setq layer_list_ename_ (nth  layer_list_i layer_list_))
      (cond
        (;_case_1
          (and
              (= 1 1)
              (= (wcmatch layer_list_ename_ "008 - E&M*") t)
          )
          (progn
            (command "vplayer" 
                      "c" 
                      color_val_
                      layer_list_ename_
                      "c"
                      ""
            )
            (princ "_case_1")
          )
        )
        (;_case_2
          (and
              (= 1 1)
              (= (wcmatch layer_list_ename_ "008 - LIGHT_*") t)
          )
          (progn
            (command "vplayer" 
                      "c" 
                      color_val_
                      layer_list_ename_
                      "c"
                      ""
            )
            (princ "_case_2")
          )
        )
        (;_case_3
          (and
              (= 1 1)
              (= (wcmatch layer_list_ename_ "008 - AIR_MASK*") t)
          )
          (progn
            (command "vplayer" 
                      "c" 
                      color_val_
                      layer_list_ename_
                      "c"
                      ""
            )
            (princ "_case_3")
          )
        )
        
      )
      (TA:textscr_process_V2 "sorting" layer_list_i layer_list_ )
      (setq layer_list_i (+ layer_list_i 1))
    )
)
(defun C:hidelight  ()
  (setq color_val_ 251)
  (setq layer_list_ (TA:get_name_layer_in_drawing))
  (TA:interface_text_ T)
  ;preloop_and_while
    (setq layer_list_i 0)
    (while (< layer_list_i (length layer_list_))
      (setq layer_list_ename_ (nth  layer_list_i layer_list_))
      (cond
        (;_case_1
          (and
              (= 1 1)
              (= (wcmatch layer_list_ename_ "008 - E&M*") t)
          )
          (progn
            (command "vplayer" 
                      "f" 
                      layer_list_ename_
                      "c" 
                      ""
            )
            (princ "_case_1")
          )
        )
        (;_case_2
          (and
              (= 1 1)
              (= (wcmatch layer_list_ename_ "008 - LIGHT_*") t)
          )
          (progn
            (command "vplayer" 
                      "f" 
                      layer_list_ename_
                      "c" 
                      ""
            )
            (princ "_case_2")
          )
        )
        (;_case_3
          (and
              (= 1 1)
              (= (wcmatch layer_list_ename_ "008 - AIR_MASK*") t)
          )
          (progn
            (command "vplayer" 
                      "f" 
                      layer_list_ename_
                      "c" 
                      ""
            )
            (princ "_case_3")
          )
        )
        
      )
      (TA:textscr_process_V2 "sorting" layer_list_i layer_list_ )
      (setq layer_list_i (+ layer_list_i 1))
    )
)
;
  
(defun c:temp_insSDD ()
  
  ;selection_set_for_fillter_blk_name
    (if  ;pre_select_ssget_or_post_select_ssget
      (=
        (setq ss_pre_filter_set_xx_ (ssget "i"
                                          (list
                                            (cons 0 "insert,circle,mtext,text,arc,Ellipse") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "insert,circle,mtext,text,arc,Ellipse") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (_startundo doc)
  ;preloop_and_while
    (setq ss_pre_filter_set_xx_i 0)
    (setq ss_pre_filter_set_xx_list_ ())
    (setq text_val_ ())
    (setq no1 ())
    (setq no2 ())
    (setq no3 ())
    (while (< ss_pre_filter_set_xx_i (sslength ss_pre_filter_set_xx_))
      (setq ss_pre_filter_set_xx_ename_ (ssname   ss_pre_filter_set_xx_ ss_pre_filter_set_xx_i))
      (setq ss_pre_filter_set_xx_obj_ (vlax-ename->vla-object  ss_pre_filter_set_xx_ename_))
      
      (setq sum_value_
        (cond
          ( (or 
              (= (vla-get-objectname ss_pre_filter_set_xx_obj_) "AcDbCircle")
              (= (vla-get-objectname ss_pre_filter_set_xx_obj_) "AcDbArc")
              (= (vla-get-objectname ss_pre_filter_set_xx_obj_) "AcDbEllipse")
            )
            (progn
              (list
                "circle"
                (setq ss_pre_filter_set_xx_obj_circle_ins_ (vlax-safearray->list (vlax-variant-value (vla-get-center ss_pre_filter_set_xx_obj_))))
              )
            )
          )
          ( (or 
              (= (vla-get-objectname ss_pre_filter_set_xx_obj_) "AcDbMText")
              (= (vla-get-objectname ss_pre_filter_set_xx_obj_) "AcDbText")
            )
            (progn
              (setq text_val_
                (list
                  (if (and 
                        (= (vla-get-objectname ss_pre_filter_set_xx_obj_) "AcDbMText")
                        (/= (vl-string-search ";" (vla-get-textstring ss_pre_filter_set_xx_obj_) 0) nil)
                      )
                    (progn
                      (substr (vla-get-textstring ss_pre_filter_set_xx_obj_) (+ (vl-string-search ";" (vla-get-textstring ss_pre_filter_set_xx_obj_) 0) 2) 22)
                    )
                    (vla-get-textstring ss_pre_filter_set_xx_obj_)
                  )
                  ; (vl-registry-read (vla-get-textstring ss_pre_filter_set_xx_obj_)) 
                  (setq ss_pre_filter_set_xx_obj_ins_ (vlax-safearray->list (vlax-variant-value (vla-get-insertionpoint ss_pre_filter_set_xx_obj_))))
                )
              )
              (setq ss_pre_filter_set_xx_list_ (cons text_val_ ss_pre_filter_set_xx_list_ ))
            )
          )
        )
      )
      
      (setq ss_pre_filter_set_xx_i (+ ss_pre_filter_set_xx_i 1))
    )
  ;
  
  (if (= (length ss_pre_filter_set_xx_list_) 3)
    (progn
      ;TA:stanndard_lambda_sorting
        (setq ss_pre_filter_set_xx_list_sorted_for_1_3_ (vl-sort ss_pre_filter_set_xx_list_  ;bigest open indent list
                                                  (function 
                                                    (lambda (a b) 
                                                      (> (nth 1 (cadr a)) (nth 1 (cadr b)))
                                                    )
                                                  )
                              ) ;bigest close indent list
        )
        (setq ss_pre_filter_set_xx_list_sorted_for_2 (vl-sort ss_pre_filter_set_xx_list_  ;bigest open indent list
                                                  (function 
                                                    (lambda (a b) 
                                                      (< (nth 0 (cadr a)) (nth 0 (cadr b)))
                                                    )
                                                  )
                              ) ;bigest close indent list
        )
        (setq no1 (nth 0 (nth 0 ss_pre_filter_set_xx_list_sorted_for_1_3_)))
        (setq no2 (nth 0 (nth 0 ss_pre_filter_set_xx_list_sorted_for_2)))
        (setq no3 (nth 0 (nth 2 ss_pre_filter_set_xx_list_sorted_for_1_3_)))
      ;
    )
  )
  (if (= (length ss_pre_filter_set_xx_list_) 2)
    (progn
      ;TA:stanndard_lambda_sorting
        (setq ss_pre_filter_set_xx_list_sorted_for_2 (vl-sort ss_pre_filter_set_xx_list_  ;bigest open indent list
                                                  (function 
                                                    (lambda (a b) 
                                                      (< (nth 0 (cadr a)) (nth 0 (cadr b)))
                                                    )
                                                  )
                              ) ;bigest close indent list
        )
        (if (> 
              (cadr (nth 1 (car ss_pre_filter_set_xx_list_sorted_for_2)))
              (cadr (nth 1 (cadr ss_pre_filter_set_xx_list_sorted_for_2)))
            )
          (progn
            (setq no3 (nth 0 (cadr ss_pre_filter_set_xx_list_sorted_for_2)))
          )
            (setq no1 (nth 0 (cadr ss_pre_filter_set_xx_list_sorted_for_2)))
        )
        (setq no2 (nth 0 (car ss_pre_filter_set_xx_list_sorted_for_2)) )
      ;
    )
  )

  (TA:vla-insertblock 
    "000 - CKST_E&M_SYMBOL"
     ss_pre_filter_set_xx_obj_circle_ins_
    1
    0
  )
  ;new_blk_entlast object
    (setq newcirblk_ename (entlast))
    (setq newcirblk_obj (vlax-ename->vla-object newcirblk_ename))
    (LM:vl-setattributevalue newcirblk_obj "1" (if (/= no2 nil) (progn no2) ""))
    (LM:vl-setattributevalue newcirblk_obj "2" (if (/= no1 nil) (progn no1 ) ""))
    (LM:vl-setattributevalue newcirblk_obj "3" (if (/= no3 nil) (progn no3 ) ""))
    
    ;esspecially condition 
      (if (and 
            (= no2 nil)
            (= no1 nil)
            (= no3 nil)
          )
        (progn
          (LM:vl-setattributevalue newcirblk_obj "1" "S") 
        )
      )
    ;
  
  ;
  
  (TA:ss-erase ss_pre_filter_set_xx_)
  (_endUndo doc)
  
)
(defun c:temp_inssignage_ ()
  (_StartUndo doc)
  ;presetting
    (setvar "osmode" 0)
  ;
  ;selection_set_for_fillter_blk_name
    (if  ;pre_select_ssget_or_post_select_ssget
      (=
        (setq ss_pre_filter_set_xx_ (ssget "i"
                                          (list
                                            (cons 0 "INSERT,mtext") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,mtext") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_S2S4 (ssadd))
    (setq new_Stext_ (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            ; ( =  (wcmatch (LM:effectivename ss_pre_filter_set_xx_obj_ ) "*U12*" ) T)
            (= (vla-get-objectname ss_pre_filter_set_xx_obj_) "AcDbBlockReference")
            (= 1 1)
            ; ( =  (wcmatch (LM:effectivename ss_pre_filter_set_xx_obj_ ) "*Slot_Supply_*" ) T)
          )
        (progn
          (setq ss_pre_filter_set_xx_obj_ins_ (vlax-safearray->list (vlax-variant-value (vla-get-insertionpoint ss_pre_filter_set_xx_obj_))))
          (setq ss_pre_filter_set_xx_obj_ro_ (vla-get-rotation ss_pre_filter_set_xx_obj_))
          (TA:vla-insertblock
            ; "ACM_Linear Slot_Supply_Side Connected _1590x200x450_ - 1590x200-21133948-CONCOURSE LEVEL CB CEILING PLAN"
            ; "000 - CSKT_ACESSORIES_FLUORESCENT_FIXTURE_BOTTOM_VIEW"
            "000 - CKST_SIGNAGE_SYMBOL"
            ss_pre_filter_set_xx_obj_ins_
            1
            (cond
              ( (or 
                    (= (rtos (rad-to-deg ss_pre_filter_set_xx_obj_ro_) 2 0) "179")
                    (= (rtos (rad-to-deg ss_pre_filter_set_xx_obj_ro_) 2 0) "180")
                    (= (rtos (rad-to-deg ss_pre_filter_set_xx_obj_ro_) 2 0) "181")
                  )
                (progn
                  0
                )
                
              )
              ( (or 
                    (= (rtos (rad-to-deg ss_pre_filter_set_xx_obj_ro_) 2 0) "89")
                    (= (rtos (rad-to-deg ss_pre_filter_set_xx_obj_ro_) 2 0) "90")
                    (= (rtos (rad-to-deg ss_pre_filter_set_xx_obj_ro_) 2 0) "91")
                    (= (rtos (rad-to-deg ss_pre_filter_set_xx_obj_ro_) 2 0) "269")
                    (= (rtos (rad-to-deg ss_pre_filter_set_xx_obj_ro_) 2 0) "270")
                    (= (rtos (rad-to-deg ss_pre_filter_set_xx_obj_ro_) 2 0) "271")
                  )
                (progn
                  (deg-to-rad 90)
                )
                
              )
            )
          )
          (setq new_S2S4 (ssadd ss_pre_filter_set_xx_ename_ new_S2S4))
          ;add on option
            ;new_blk_entlast object
              (setq newblk_ename (entlast))
              (setq newblk_obj_ (vlax-ename->vla-object newblk_ename))
              ; (LM:vl-setattributevalue newblk_obj_ "SIGNAGE_VAL_2" "L1-2")
              ; (TA:move_polar_insertionpoint newblk_obj_ "x" 300)
            ;
          ;
        )
        (if (and 
              ; ( =  (wcmatch (LM:effectivename ss_pre_filter_set_xx_obj_ ) "*U12*" ) T)
              (= (vla-get-objectname ss_pre_filter_set_xx_obj_) "AcDbMText" )
              (= 1 1)
              ; ( =  (wcmatch (LM:effectivename ss_pre_filter_set_xx_obj_ ) "*Slot_Supply_*" ) T)
            )
          (progn
            (setq new_Stext_ (ssadd ss_pre_filter_set_xx_ename_ new_Stext_))
          )
        )
        
      )
      
      (setq ss_pre_filter_set_xx_i (+ ss_pre_filter_set_xx_i 1))
    )
  ;
  ;preloop_and_while
    (setq new_Stext_i 0)
    (setq new_Stext_xylist_ ())
    (while (< new_Stext_i (sslength new_Stext_))
      (setq new_Stext_ename_ (ssname new_Stext_ new_Stext_i))
      (setq new_Stext_obj_ (vlax-ename->vla-object  new_Stext_ename_))
      (setq new_Stext_obj_txt_ (vla-get-textstring new_Stext_obj_ ))
      (setq new_Stext_obj_ins_ (vlax-safearray->list (vlax-variant-value (vla-get-insertionpoint new_Stext_obj_))))
      (setq new_Stext_xylist_ (cons (list new_Stext_obj_txt_  new_Stext_obj_ins_) new_Stext_xylist_ ))

      
      (setq new_Stext_i (+ new_Stext_i 1))
    )
  ; 
  ;TA:stanndard_lambda_sorting
    (setq new_Stext_xylist_sorted_ (vl-sort new_Stext_xylist_  ;bigest open indent list
                                            (function 
                                              (lambda (a b) 
                                                (> (nth 1 (cadr a)) 
                                                   (nth 1 (cadr b))
                                                )
                                              )
                                            )
                                   ) ;bigest close indent list
    )
  ;
  ;new_blk_entlast object
    (setq new_sign_ename (entlast))
    (setq new_sign_obj (vlax-ename->vla-object new_sign_ename))
    (if (= (length new_Stext_xylist_sorted_) 2)
      (progn
        (LM:vl-setattributevalue new_sign_obj "signage_val_1" (nth 0 (car new_Stext_xylist_sorted_)))
        (LM:vl-setattributevalue new_sign_obj "signage_val_2"(nth 0 (cadr new_Stext_xylist_sorted_)) )
      )
      (LM:vl-setattributevalue new_sign_obj "signage_val_1" (nth 0 (car new_Stext_xylist_sorted_)))
    )
    
    
  ;
  
  (command "pselect"  new_S2S4 "" )
  (command "pselect"  ss_pre_filter_set_xx_ "" )
  (TA:ss-erase ss_pre_filter_set_xx_)
  
  ;while selection process
    (setq ERR_ nil)
    (while ;for keep insertion point and dist. fix length one side
      (and
        (= (vl-catch-all-error-p ERR_) nil)
      )
      (setq ERR_
        (vl-catch-all-apply
          (function
            (lambda ()
              (getstring "enter for continue");input_cond entsel ssget
            )
          )
        )
      )
      (if (and
        (= (vl-catch-all-error-p ERR_) nil)
      )
        (progn
          (TAs:temp_sgsw_ new_sign_obj )
          
        )
      )
      
    )
  ;
  ;presetting
    (setvar "osmode" 1215)
  ;
  (_endundo doc)
) 
(defun TAs:temp_sgsw_ (sgsw_obj_ )
  ; (setq sgsw_ename_ (car (entsel "specify Object")))
  ; (setq sgsw_obj_ (vlax-ename->vla-object sgsw_ename_))
  (setq sgsw_obj_att1 (LM:vl-getattributevalue sgsw_obj_ "signage_val_1"  ))
  (setq sgsw_obj_att2 (LM:vl-getattributevalue sgsw_obj_ "signage_val_2"  ))
  (LM:vl-setattributevalue sgsw_obj_ "signage_val_1" sgsw_obj_att2 )
  (LM:vl-setattributevalue sgsw_obj_ "signage_val_2" sgsw_obj_att1 )
  
)
(defun c:temp_insdl2 ()
  
    ;selection_set_for_fillter_blk_name
      (if  ;pre_select_ssget_or_post_select_ssget
        (=
          (setq ss_pre_filter_set_xx_ (ssget "i"
                                            (list
                                              (cons 0 "insert,mtext,text") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "insert,mtext,text") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
  ;preloop_and_while
    (setq ss_pre_filter_set_xx_i 0)
    (setq new_fu1_ss_ (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins_ (vlax-safearray->list (vlax-variant-value (vla-get-insertionpoint ss_pre_filter_set_xx_obj_))))
      
      (if (and 
            (= (vla-get-objectname ss_pre_filter_set_xx_obj_) "AcDbBlockReference")
            (or 
              (= (LM:effectivename ss_pre_filter_set_xx_obj_) "A$C0176f62a")
              (= (LM:effectivename ss_pre_filter_set_xx_obj_) "A$Ce1811ff6")
            )
          )
        (progn
          (setvar "osmode" 0)
          (TA:vla-insertblock 
            "000 - CKST_DOWNLIGHT_SYMBOL"
            ss_pre_filter_set_xx_obj_ins_
            1
            0
          )
          (setq new_fu1_ss_ (ssadd (entlast ) new_fu1_ss_ ))
        )
        (ssdel ss_pre_filter_set_xx_ename_ ss_pre_filter_set_xx_)
      )
      
      (setq ss_pre_filter_set_xx_i (+ ss_pre_filter_set_xx_i 1))
    )
    (TA:ss-erase ss_pre_filter_set_xx_)
  ;

  (command "pselect"  new_fu1_ss_ "" )
  (setvar "osmode" 1215)
  (_endUndo doc)
  
)
(defun c:temp_insdl3 ()
  
  ;selection_set_for_fillter_blk_name
    (if  ;pre_select_ssget_or_post_select_ssget
      (=
        (setq ss_pre_filter_set_xx_ (ssget "i"
                                          (list
                                            (cons 0 "circle,line") ;type of object
                                            (cons 8 "FRAMING_HANGING_MAIN_COLOR_1*")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "circle,line") ;type of object
                                            (cons 8 "FRAMING_HANGING_MAIN_COLOR_1*")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_fu1_ss_ (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            (= (vla-get-objectname ss_pre_filter_set_xx_obj_) "AcDbCircle")
          )
        (progn
          (setvar "osmode" 0)
          ()
          (TA:vla-insertblock 
            "tt1t"
            (vlax-safearray->list (vlax-variant-value (vla-get-center ss_pre_filter_set_xx_obj_)))
            1
            0
          )
          (setq new_fu1_ss_ (ssadd (entlast ) new_fu1_ss_ ))
        )
      )
      
      (setq ss_pre_filter_set_xx_i (+ ss_pre_filter_set_xx_i 1))
    )
    (TA:ss-erase ss_pre_filter_set_xx_)
  ;

  (command "pselect"  new_fu1_ss_ "" )
  (setvar "osmode" 1215)
  (_endUndo doc)
  
)
(defun c:temp_insdl5 ()
  
  ;selection_set_for_fillter_blk_name
    (if  ;pre_select_ssget_or_post_select_ssget
      (=
        (setq ss_pre_filter_set_xx_ (ssget "i"
                                          (list
                                            (cons 0 "arc,circle,line") ;type of object
                                            (cons 8 "FRAMING_HANGING_MAIN_COLOR_1*")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "arc,circle,line") ;type of object
                                            (cons 8 "FRAMING_HANGING_MAIN_COLOR_1*")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_fu1_ss_ (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            (= (vla-get-objectname ss_pre_filter_set_xx_obj_) "AcDbCircle")
          )
        (progn
          (setvar "osmode" 0)
          ()
          (TA:vla-insertblock 
            "tt1t"
            (vlax-safearray->list (vlax-variant-value (vla-get-center ss_pre_filter_set_xx_obj_)))
            1
            0
          )
          (setq new_fu1_ss_ (ssadd (entlast ) new_fu1_ss_ ))
        )
      )
      
      (setq ss_pre_filter_set_xx_i (+ ss_pre_filter_set_xx_i 1))
    )
    (TA:ss-erase ss_pre_filter_set_xx_)
  ;

  (command "pselect"  new_fu1_ss_ "" )
  (setvar "osmode" 1215)
  (_endUndo doc)
  
)

(defun c:temp_insdl1 ()
  
  ;selection_set_for_fillter_blk_name
    (if  ;pre_select_ssget_or_post_select_ssget
      (=
        (setq ss_pre_filter_set_xx_ (ssget "i"
                                          (list
                                            (cons 0 "insert,mtext") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "insert,mtext") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins_ (vlax-safearray->list (vlax-variant-value (vla-get-insertionpoint ss_pre_filter_set_xx_obj_))))
      (if (= (vla-get-objectname ss_pre_filter_set_xx_obj_) "AcDbBlockReference")
        (progn
          (TA:vla-insertblock 
            "000 - CKST_DOWNLIGHT_SYMBOL_sed LED Downlight Luminaire - ø114 x 40H - 12W"
            ss_pre_filter_set_xx_obj_ins_
            1
            0
          )
        )
      )
      
      (setq ss_pre_filter_set_xx_i (+ ss_pre_filter_set_xx_i 1))
    )
    (TA:ss-erase ss_pre_filter_set_xx_)
  ;

  

  (_endUndo doc)
  
)
(defun c:temp_insfu1 ()
  ;selection_set_for_fillter_blk_name
    (if  ;pre_select_ssget_or_post_select_ssget
      (=
        (setq ss_pre_filter_set_xx_ (ssget "i"
                                          (list
                                            (cons 0 "INSERT,mtext,text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,mtext,text") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_S2S4 (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            ; ( =  (wcmatch (LM:effectivename ss_pre_filter_set_xx_obj_ ) "*U12*" ) T)
            (= (vla-get-objectname ss_pre_filter_set_xx_obj_) "AcDbBlockReference")
            (= 1 1)
            ; ( =  (wcmatch (LM:effectivename ss_pre_filter_set_xx_obj_ ) "*Slot_Supply_*" ) T)
          )
        (progn
          (setq ss_pre_filter_set_xx_obj_ins_ (vlax-safearray->list (vlax-variant-value (vla-get-insertionpoint ss_pre_filter_set_xx_obj_))))
          (setq ss_pre_filter_set_xx_obj_ro_ (vla-get-rotation ss_pre_filter_set_xx_obj_))
          (TA:vla-insertblock
            ; "ACM_Linear Slot_Supply_Side Connected _1590x200x450_ - 1590x200-21133948-CONCOURSE LEVEL CB CEILING PLAN"
            ; "000 - CSKT_ACESSORIES_FLUORESCENT_FIXTURE_BOTTOM_VIEW"
            "L1-2 RECESSED FLUORESCENT2 - L1-2  RECESSED FLUORESCENT"
            ss_pre_filter_set_xx_obj_ins_
            1
            ss_pre_filter_set_xx_obj_ro_
          )
          (setq new_S2S4 (ssadd ss_pre_filter_set_xx_ename_ new_S2S4))
          ;add on option
            ;new_blk_entlast object
              (setq newblk_ename (entlast))
              (setq newblk_obj_ (vlax-ename->vla-object newblk_ename))
              (LM:vl-setattributevalue newblk_obj_ "name" "L1-2")
              (TA:move_polar_insertionpoint newblk_obj_ "x" 52.5)
              (setq new_S2S4 (ssadd newblk_ename new_S2S4))
            ;
          ;
        )
      )
      
      (setq ss_pre_filter_set_xx_i (+ ss_pre_filter_set_xx_i 1))
    )
  ;
  
  (command "pselect"  ss_pre_filter_set_xx_ "" )
  (TA:ss-erase ss_pre_filter_set_xx_)
  (command "pselect"  new_S2S4 "" )
  
)
(defun c:temp_insfu2 ()
  ;selection_set_for_fillter_blk_name
    (if  ;pre_select_ssget_or_post_select_ssget
      (=
        (setq ss_pre_filter_set_xx_ (ssget "i"
                                          (list
                                            (cons 0 "insert") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_S2S4 (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            ; ( =  (wcmatch (LM:effectivename ss_pre_filter_set_xx_obj_ ) "*U12*" ) T)
            (= (vla-get-objectname ss_pre_filter_set_xx_obj_) "AcDbBlockReference")
            (= 1 1)
            ; ( =  (wcmatch (LM:effectivename ss_pre_filter_set_xx_obj_ ) "*Slot_Supply_*" ) T)
          )
        (progn
          (setq ss_pre_filter_set_xx_obj_ins_ (vlax-safearray->list (vlax-variant-value (vla-get-insertionpoint ss_pre_filter_set_xx_obj_))))
          (setq ss_pre_filter_set_xx_obj_ro_ (vla-get-rotation ss_pre_filter_set_xx_obj_))
          (TA:vla-insertblock
            ; "ACM_Linear Slot_Supply_Side Connected _1590x200x450_ - 1590x200-21133948-CONCOURSE LEVEL CB CEILING PLAN"
            ; "000 - CSKT_ACESSORIES_FLUORESCENT_FIXTURE_BOTTOM_VIEW"
            "Batten LED Tube Luminaire - 1224L x 102W x 80H  - 36W-V1-02_CONCOURSE LEVEL LIGHTING LAYOUT FOR COMBINE CEILING - Dependent 1"
            ss_pre_filter_set_xx_obj_ins_
            1
            ss_pre_filter_set_xx_obj_ro_
          )
          (setq new_S2S4 (ssadd ss_pre_filter_set_xx_ename_ new_S2S4))
          ;add on option
            ;new_blk_entlast object
              (setq newblk_ename (entlast))
              (setq newblk_obj_ (vlax-ename->vla-object newblk_ename))
              (setq new_S2S4 (ssadd newblk_ename new_S2S4))
              ; (LM:vl-setattributevalue newblk_obj_ "name" "L1-2")
              ; (TA:move_polar_insertionpoint newblk_obj_ "x" 52.5)
            ;
          ;
        )
      )
      
      (setq ss_pre_filter_set_xx_i (+ ss_pre_filter_set_xx_i 1))
    )
  ;
  
  (command "pselect"  ss_pre_filter_set_xx_ "" )
  (TA:ss-erase ss_pre_filter_set_xx_)
  (command "pselect"  new_S2S4 "" )
  
)
(defun c:temp_insfu5 ()
  
  ;selection_set_for_fillter_blk_name
    (if  ;pre_select_ssget_or_post_select_ssget
      (=
        (setq ss_pre_filter_set_xx_ (ssget "i"
                                          (list
                                            (cons 0 "insert,mtext") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "insert,mtext") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins_ (vlax-safearray->list (vlax-variant-value (vla-get-insertionpoint ss_pre_filter_set_xx_obj_))))
      (if (= (vla-get-objectname ss_pre_filter_set_xx_obj_) "AcDbBlockReference")
        (progn
          (TA:vla-insertblock 
            "000 - CKST_L5 - Ceiling Recessed_Surface Mounted Modular LED Tube - 1195L x 595W x 85H - 36W"
            ss_pre_filter_set_xx_obj_ins_
            1
            0
          )
        )
      )
      
      (setq ss_pre_filter_set_xx_i (+ ss_pre_filter_set_xx_i 1))
    )
    (TA:ss-erase ss_pre_filter_set_xx_)
  ;

  

  (_endUndo doc)
  
)
(defun c:temp_inssk ()
  (_startundo doc)
  ;selection_set_for_fillter_blk_name
    (if  ;pre_select_ssget_or_post_select_ssget
      (=
        (setq ss_pre_filter_set_xx_ (ssget "i"
                                          (list
                                            (cons 0 "arc,circle,line,lwpolyline") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "arc,circle,line,lwpolyline") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq check_ nil)
    (while (and 
            (= check_ nil)
            (< ss_pre_filter_set_xx_i (sslength ss_pre_filter_set_xx_))
          )
      (setq ss_pre_filter_set_xx_ename_ (ssname ss_pre_filter_set_xx_ ss_pre_filter_set_xx_i))
      (setq ss_pre_filter_set_xx_obj_ (vlax-ename->vla-object  ss_pre_filter_set_xx_ename_))
      
      (if (= (vla-get-objectname ss_pre_filter_set_xx_obj_) "AcDbCircle")
        
        (progn
          (setq ss_pre_filter_set_xx_obj_ins_ (vlax-safearray->list (vlax-variant-value (vla-get-center ss_pre_filter_set_xx_obj_))))
          (TA:vla-insertblock 
            "000 - CKST_SPRINKLER"
            ss_pre_filter_set_xx_obj_ins_
            1
            0
          )
          (setq check_ 1)
        )
      )
      
      (setq ss_pre_filter_set_xx_i (+ ss_pre_filter_set_xx_i 1))
    )
    (TA:ss-erase ss_pre_filter_set_xx_)
  ;

  

  (_endUndo doc)
  
)
(defun c:temp_insfu60 ()
  
  ;selection_set_for_fillter_blk_name
    (if  ;pre_select_ssget_or_post_select_ssget
      (=
        (setq ss_pre_filter_set_xx_ (ssget "i"
                                          (list
                                            (cons 0 "insert,mtext") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "insert,mtext") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins_ (vlax-safearray->list (vlax-variant-value (vla-get-insertionpoint ss_pre_filter_set_xx_obj_))))
      (if (= (vla-get-objectname ss_pre_filter_set_xx_obj_) "AcDbBlockReference")
        (progn
          (TA:vla-insertblock 
            "L6 - Ceiling Recessed Modular LED Tube - 1195L x 595W x 85H - 36W"
            ss_pre_filter_set_xx_obj_ins_
            1
            0
          )
        )
      )
      
      (setq ss_pre_filter_set_xx_i (+ ss_pre_filter_set_xx_i 1))
    )
    (TA:ss-erase ss_pre_filter_set_xx_)
  ;

  

  (_endUndo doc)
  
)
(defun c:temp_insfu61 ()
  ;selection_set_for_fillter_blk_name
    (if  ;pre_select_ssget_or_post_select_ssget
      (=
        (setq ss_pre_filter_set_xx_ (ssget "i"
                                          (list
                                            (cons 0 "INSERT,mtext") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,mtext") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_S2S4 (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            ; ( =  (wcmatch (LM:effectivename ss_pre_filter_set_xx_obj_ ) "*U12*" ) T)
            (= (vla-get-objectname ss_pre_filter_set_xx_obj_) "AcDbBlockReference")
            (= 1 1)
            ; ( =  (wcmatch (LM:effectivename ss_pre_filter_set_xx_obj_ ) "*Slot_Supply_*" ) T)
          )
        (progn
          (setq ss_pre_filter_set_xx_obj_ins_ (vlax-safearray->list (vlax-variant-value (vla-get-insertionpoint ss_pre_filter_set_xx_obj_))))
          (setq ss_pre_filter_set_xx_obj_ro_ (vla-get-rotation ss_pre_filter_set_xx_obj_))
          (TA:vla-insertblock
            ; "ACM_Linear Slot_Supply_Side Connected _1590x200x450_ - 1590x200-21133948-CONCOURSE LEVEL CB CEILING PLAN"
            ; "000 - CSKT_ACESSORIES_FLUORESCENT_FIXTURE_BOTTOM_VIEW"
            "L6 - Ceiling Recessed Modular LED Tube - 1195L x 595W x 85H - 36W"
            ss_pre_filter_set_xx_obj_ins_
            1
            ss_pre_filter_set_xx_obj_ro_
          )
          (setq new_S2S4 (ssadd ss_pre_filter_set_xx_ename_ new_S2S4))
          ;add on option
            ;new_blk_entlast object
              (setq newblk_ename (entlast))
              (setq newblk_obj_ (vlax-ename->vla-object newblk_ename))
              ; (LM:vl-setattributevalue newblk_obj_ "name" "L1-2")
              (TA:move_polar_insertionpoint newblk_obj_ "x" -300)
            ;
          ;
        )
      )
      
      (setq ss_pre_filter_set_xx_i (+ ss_pre_filter_set_xx_i 1))
    )
  ;
  (command "pselect"  new_S2S4 "" )
  (command "pselect"  ss_pre_filter_set_xx_ "" )
  (TA:ss-erase ss_pre_filter_set_xx_)
  
)


(defun c:temp_ss1 ()
  ;selection_set_for_fillter_blk_name
    (if  ;pre_select_ssget_or_post_select_ssget
      (=
        (setq ss_pre_filter_set_temp_ (ssget "i"
            (list
              (cons 0 "INSERT") ;type of object
              ; (cons 8 "000 - GRID")   ;kind of layer
              ; (cons 2 "000-GRID_LINE_DYN")       ;kind of nameblock
              ; (cons 62 1)           ;kind of color call sign with color code index
            )
          )
        )
        nil
      )
      (progn
        (setq ss_pre_filter_set_temp_ (ssget
            (list
              ; (cons 0 "mtext") ;type of object
              (cons 8 "A-ANNO-NOTE")   ;kind of layer
              ; (cons 2 "000-GRID_LINE_DYN")       ;kind of nameblock
              (cons 62 8)           ;kind of color call sign with color code index
            )
          )
        )
        (sslength ss_pre_filter_set_temp_)
      )
    )
  ;
  (command "pselect"  ss_pre_filter_set_temp_ "" )
)

(defun c:temp_insdif ()
  ;selection_set_for_fillter_blk_name
    (if  ;pre_select_ssget_or_post_select_ssget
      (=
        (setq ss_pre_filter_set_xx_ (ssget "i"
                                          (list
                                            (cons 0 "INSERT,mtext") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,mtext") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq new_S2S4 (ssadd))
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      
      
      (if (and 
            ; ( =  (wcmatch (LM:effectivename ss_pre_filter_set_xx_obj_ ) "*U12*" ) T)
            (= (vla-get-objectname ss_pre_filter_set_xx_obj_) "AcDbBlockReference")
            (= 1 1)
            ; ( =  (wcmatch (LM:effectivename ss_pre_filter_set_xx_obj_ ) "*Slot_Supply_*" ) T)
          )
        (progn
          (setq ss_pre_filter_set_xx_obj_ins_ (vlax-safearray->list (vlax-variant-value (vla-get-insertionpoint ss_pre_filter_set_xx_obj_))))
          (setq ss_pre_filter_set_xx_obj_ro_ (vla-get-rotation ss_pre_filter_set_xx_obj_))
          (TA:vla-insertblock
            "ACM_Linear Slot_Supply_Side Connected _1590x200x450_ - 1590x200-21133948-CONCOURSE LEVEL CB CEILING PLAN"
            ; "000 - CSKT_ACESSORIES_FLUORESCENT_FIXTURE_BOTTOM_VIEW"
            ; "L6 - Ceiling Recessed Modular LED Tube - 1195L x 595W x 85H - 36W"
            ss_pre_filter_set_xx_obj_ins_
            1
            ss_pre_filter_set_xx_obj_ro_
          )
          (setq new_S2S4 (ssadd ss_pre_filter_set_xx_ename_ new_S2S4))
          ;add on option
            ;new_blk_entlast object
              (setq newblk_ename (entlast))
              (setq newblk_obj_ (vlax-ename->vla-object newblk_ename))
              ; (LM:vl-setattributevalue newblk_obj_ "name" "L1-2")
              (TA:move_polar_insertionpoint newblk_obj_ "x" 0)
            ;
          ;
        )
      )
      
      (setq ss_pre_filter_set_xx_i (+ ss_pre_filter_set_xx_i 1))
    )
  ;
  (command "pselect"  new_S2S4 "" )
  (command "pselect"  ss_pre_filter_set_xx_ "" )
  (TA:ss-erase ss_pre_filter_set_xx_)
  
)
    

(defun c:as1 ()
  ;selection_set_for_fillter_blk_name
    (if  ;pre_select_ssget_or_post_select_ssget
      (=
        (setq ss_pre_filter_set_as_ (ssget "i"
            (list
              ; (cons 0 "INSERT") ;type of object
              ; (cons 8 "001 - ASCESSORIES")   ;kind of layer
              ; (cons 2 "000-GRID_LINE_DYN")       ;kind of nameblock
              ; (cons 62 1)           ;kind of color call sign with color code index
            )
          )
        )
        nil
      )
      (progn
        (setq ss_pre_filter_set_as_ (ssget
            (list
              ; (cons 0 "INSERT") ;type of object
              ; (cons 8 "001 - ASCESSORIES")   ;kind of layer
              ; (cons 2 "000-GRID_LINE_DYN")       ;kind of nameblock
              ; (cons 62 1)           ;kind of color call sign with color code index
            )
          )
        )
        (sslength ss_pre_filter_set_as_)
      )
    )
  ;
  ;preloop_and_while
    (setq ss_pre_filter_set_as_i 0)
    (while (< ss_pre_filter_set_as_i (sslength ss_pre_filter_set_as_))
      (setq ss_pre_filter_set_as_ename_ (ssname   ss_pre_filter_set_as_ ss_pre_filter_set_as_i))
      (setq ss_pre_filter_set_as_obj_ (vlax-ename->vla-object  ss_pre_filter_set_as_ename_))
      (cond
        (;_case_
            (and
              (= (vla-get-color ss_pre_filter_set_as_obj_ ) 5)
            )
            (progn
              (vla-put-layer ss_pre_filter_set_as_obj_ "000_PPLINE_CKST_SMOKE_BARRIER_SUB_COLOR_1" )
              (vla-put-color ss_pre_filter_set_as_obj_ 256 )
            ;  (princ "_case_1")
            )
        )
        (;_case_2
            (and
              (= (vla-get-color ss_pre_filter_set_as_obj_ ) 2)
            )
            (progn
              (vla-put-layer ss_pre_filter_set_as_obj_ "000_PPLINE_CKST_SMOKE_GLASS_FIN_MAIN_COLOR" )
              (vla-put-color ss_pre_filter_set_as_obj_ 256 )
            ;  (princ "_case_2")
            )
        )
        (;_case_2
            (and
              (= (vla-get-color ss_pre_filter_set_as_obj_ ) 8)
            )
            (progn
              (vla-put-layer ss_pre_filter_set_as_obj_ "000_PPLINE_CKST_SMOKE_ACESSORIES_MAIN_COLOR" )
              (vla-put-color ss_pre_filter_set_as_obj_ 256 )
            ;  (princ "_case_2")
            )
        )
        (;_case_2
            (and
              (= (vla-get-objectname ss_pre_filter_set_as_obj_ ) "AcDbHatch")
            )
            (progn
              (vla-put-layer ss_pre_filter_set_as_obj_ "000_PPLINE_CKST_SMOKE_BARRIER_HATCH" )
              (vla-put-color ss_pre_filter_set_as_obj_ 256 )
            ;  (princ "_case_2")
            )
        )
      )
      
      (setq ss_pre_filter_set_as_i (+ ss_pre_filter_set_as_i 1))
    )
  ;)
  (command "pselect"  ss_pre_filter_set_as_ "" )
)
(defun c:temp_selko1 ()
  ;selection_set_for_fillter_blk_name
    (if  ;pre_select_ssget_or_post_select_ssget
      (=
        (setq ss_pre_filter_set_as_ (ssget "i"
                                          (list
                                            (cons 0 "INSERT,hatch,line,lwpolyline,arc") ;type of object
                                            (cons 8 "0,IEL-Shadeheavy,hatch,screw")   ;kind of layer
                                            ; (cons 2 "000-GRID_LINE_DYN")       ;kind of nameblock
                                            '(-4 . "<OR")
                                              (cons 62 2)
                                              (cons 62 5)
                                              (cons 62 8)
                                              (cons 62 256)
                                            '(-4 . "OR>")
                                          )
                                    )
        )
        nil
      )
      (progn
        (setq ss_pre_filter_set_as_ (ssget
                                          (list
                                            (cons 0 "INSERT,hatch,line,lwpolyline,arc") ;type of object
                                            (cons 8 "0,IEL-Shadeheavy,hatch,screw")   ;kind of layer
                                            ; (cons 2 "000-GRID_LINE_DYN")       ;kind of nameblock
                                            '(-4 . "<OR")
                                              (cons 62 2)
                                              (cons 62 5)
                                              (cons 62 8)
                                              (cons 62 256)
                                            '(-4 . "OR>")
                                          )
                                    )
        )
      )
      (sslength ss_pre_filter_set_as_)
    )
  ;
  (command "pselect"  ss_pre_filter_set_as_ "" )
)
(defun c:temp_selko2 ()
  ;selection_set_for_fillter_blk_name
    (if  ;pre_select_ssget_or_post_select_ssget
      (=
        (setq ss_pre_filter_set_as_ (ssget "i"
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_as_ (ssget
                                          (list
                                            ; (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_as_)
    )
  ;
  ;preloop_and_while
    (setq ss_pre_filter_set_as_i 0)
    (while (< ss_pre_filter_set_as_i (sslength ss_pre_filter_set_as_))
      (setq ss_pre_filter_set_as_ename_ (ssname   ss_pre_filter_set_as_ ss_pre_filter_set_as_i))
      (setq ss_pre_filter_set_as_obj_ (vlax-ename->vla-object  ss_pre_filter_set_as_ename_))
      (cond
        (;_case_
            (and
              (= (vla-get-color ss_pre_filter_set_as_obj_ ) 5)
            )
            (progn
              (vla-put-layer ss_pre_filter_set_as_obj_ "000_PPLINE_CKST_SMOKE_BARRIER_SUB_COLOR_1" )
              (vla-put-color ss_pre_filter_set_as_obj_ 256 )
            ;  (princ "_case_1")
            )
        )
        (;_case_2
            (and
              (= (vla-get-color ss_pre_filter_set_as_obj_ ) 2)
            )
            (progn
              (vla-put-layer ss_pre_filter_set_as_obj_ "000_PPLINE_CKST_SMOKE_GLASS_FIN_MAIN_COLOR" )
              (vla-put-color ss_pre_filter_set_as_obj_ 256 )
            ;  (princ "_case_2")
            )
        )
        (;_case_2
            (and
              (= (vla-get-color ss_pre_filter_set_as_obj_ ) 8)
            )
            (progn
              (vla-put-layer ss_pre_filter_set_as_obj_ "000_PPLINE_CKST_SMOKE_ACESSORIES_MAIN_COLOR" )
              (vla-put-color ss_pre_filter_set_as_obj_ 256 )
            ;  (princ "_case_2")
            )
        )
        (;_case_2
            (and
              (= (vla-get-objectname ss_pre_filter_set_as_obj_ ) "AcDbHatch")
            )
            (progn
              (vla-put-layer ss_pre_filter_set_as_obj_ "000_PPLINE_CKST_SMOKE_BARRIER_HATCH" )
              (vla-put-color ss_pre_filter_set_as_obj_ 256 )
            ;  (princ "_case_2")
            )
        )
        (;_case_2
            (and
              (= (vla-get-objectname ss_pre_filter_set_as_obj_ ) "AcDbPolyline")
              (= (vla-get-layer ss_pre_filter_set_as_obj_) "0")
              (= (vla-get-color ss_pre_filter_set_as_obj_) 256)
            )
            (progn
              (vla-put-layer ss_pre_filter_set_as_obj_ "000_PPLINE_CKST_SMOKE_BARRIER_HATCH" )
              (vla-put-color ss_pre_filter_set_as_obj_ 256 )
            ;  (princ "_case_2")
            )
        )
      )
      
      (setq ss_pre_filter_set_as_i (+ ss_pre_filter_set_as_i 1))
    )
  ;)
  
)

(defun c:w1 ()
  
  (setq target_ename_ (car (nentselp "specify Object")))
  (setq target_obj_ (vlax-ename->vla-object target_ename_))
  (vl-princ-to-string (vlax-dump-object target_obj_) )
  (print (vla-get-objectname target_obj_))
  (print (vla-get-layer target_obj_))
  (print (vla-get-color target_obj_))
  (setq Er-msg_ (vl-catch-all-apply (function (lambda () (print (vla-get-TagString  target_obj_)) ) ) ) )
  
)

(defun c:change_layer_color-rgb_set_ ()
  (setq doc (vla-get-ActiveDocument (vlax-get-acad-object)))
  (setq layer_list_ (list 
                      (list "000 - SYMBOL CON_ASBUILT_WALL_MAIN_COLOR_1" (list 255 0 0) )                  
                      (list "000 - SYMBOL CON_ASBUILT_WALL_MAIN_COLOR_2" (list 255 135 0) )                  
                      (list "000 - SYMBOL CON_ASBUILT_WALL_SUB_COLOR_1" (list 0 255 0) )      
                    
                      (list "000_AREA_C06_MAIN_COLOR_1" (list 150 250 0) )                  
                      (list "000_AREA_C06_HATCH_" (list 150 250 0) ) 
                      (list "000_AREA_C07_MAIN_COLOR_1" (list 150 250 0) )                  
                      (list "000_AREA_C07_HATCH_" (list 150 250 0) ) 
                      
                      (list "000_AREA_C02_MAIN_COLOR_1" (list 5 230 200) )                  
                      (list "000_AREA_C02_HATCH_" (list 5 230 200) )                  
                      (list "000_AREA_C03_MAIN_COLOR_1" (list 250 0 150) )                  
                      (list "000_AREA_C03_HATCH_" (list 250 0 150) )         
                      
                      (list "000_AREA_C04_MAIN_COLOR_1" (list 0 127 0) )                  
                      (list "000_AREA_C04_HATCH_" (list 0 127 0) )  
                      
                      (list "000_AREA_C05_MAIN_COLOR_1" (list 255 135 0) )                  
                      (list "000_AREA_C05_HATCH_" (list 255 135 0) )     
                      
                      (list "000_AREA_C08_MAIN_COLOR_1" (list 255 0 191) )        
                      (list "000_AREA_C08_HATCH_" (list 255 0 191) )         
                      
                      (list "000_AREA_C09_MAIN_COLOR_1" (list 170 50 170) )                  
                      (list "000_AREA_C09_HATCH_" (list 170 50 170) )   
                      
                      (list "000_AREA_C09_MAIN_COLOR_1" (list 0 255 0) )                  
                      (list "000_AREA_C09_HATCH_" (list 0 255 0) )        
                      
                      (list "000_AREA_C10_MAIN_COLOR_1" (list 127 0 255) )                  
                      (list "000_AREA_C10_HATCH_" (list 127 0 0) )    
                      
                      (list "000_AREA_C10_MAIN_COLOR_1" (list 255 0 0) )                  
                      (list "000_AREA_C10_HATCH_" (list 255 0 0) )                  
                    )
  )
  ;preloop_and_while
    (setq layer_list_i 0)
    (while (< layer_list_i (length layer_list_))
      (if (= (length (nth  layer_list_i layer_list_) ) 2 )
        (progn
          (setq layer_list_name_ (car (nth  layer_list_i layer_list_)))
          (setq layer_list_color_ (cadr (nth  layer_list_i layer_list_)))
          
          (if (and 
                (= (length layer_list_color_ ) 3)
                (=
                  (type 
                    (setq ERR_layObj
                      (vl-catch-all-apply
                        (function
                          (lambda ()
                            (setq layObj (vla-Item 
                                          (vla-get-Layers doc)
                                          layer_list_name_ ; ← ชื่อ Layer
                                        )
                            )
                          )
                        )
                      )
                    )
                  )
                'VLA-OBJECT
                )

              )
            (progn
              (TA:put-rgb layObj (car layer_list_color_) (cadr layer_list_color_) (caddr layer_list_color_))
            )
          )
        )
        
      )

      (setq layer_list_i (+ layer_list_i 1))
    )
  ;
  

) 





(defun TA:nested_data_block_ (blk_obj_ data_mode propertie_name_list_)
  ; (setq blockname "L2-2 - Surface Mounted LED Tube - 1223L x 170W x 93H - 36W-V1-CONCOURSE LEVEL_LIGHTING Copy 1")
  ; (setq data_mode 4)
  ; (setq propertie_name_list_ (list 
  ;                              "HANDLE"
  ;                              "Layer"
  ;                            )
  ; )
  ; (setq line_color 256)
  ; (setq layer_name "008 - E&M_ACESSORIES_MAIN_COLOR_1")
  ; (setq layer_name "008 - E&M_ACESSORIES_MAIN_COLOR_1")
  (setq target_ '())
  (setq result_data_ ())
  
  ; (setq blkdef (tblobjname "BLOCK" blockname))
  ; (setq ent (entnext blkdef))
  (if (= (vla-get-objectname blk_obj_) "AcDbBlockReference")
    (progn
      (setq blkname (cdr (assoc 2 (entget (vlax-vla-object->ename blk_obj_)))))
      (setq bdef (tblobjname "BLOCK" blkname))
      (setq ent (entnext bdef))
      (while ent
        (setq ed (entget ent))
        (cond
          ( (and 
                (= data_mode 1)
                (= (cdr (assoc 0 ed)) "HATCH")
              )
            (progn
              ; (setq target_ (cons ent target_))
              ;main idea of code keep or delete don't affect with core code
                (setq target_obj_ (vlax-ename->vla-object (cdr (assoc -1 ed))))
                (setq target_data_ (vlax-get-property target_obj_ propertie_name_))
                (setq result_data_ (cons target_data_ result_data_))
              ;
            )
          )
          ( (and 
                (= data_mode 2)
                (= (cdr (assoc 0 ed)) "ARC")
                (= (type propertie_name_list_ ) 'list)
              )
            (progn
              ; (setq target_ (cons ent target_))
              ;main idea of code keep or delete don't affect with core code
                (setq target_obj_ (vlax-ename->vla-object (cdr (assoc -1 ed))))
                (vlax-dump-object target_obj_)
                (setq target_data_ (vlax-get-property target_obj_ propertie_name_))
                (setq result_data_ (cons target_data_ result_data_))
              ;
            )
          )
          ( (and 
                (= data_mode 3)
                (= (cdr (assoc 0 ed)) "LINE")
              )
            (progn
              ; (setq target_ (cons ent target_))
              ;main idea of code keep or delete don't affect with core code
                (setq target_obj_ (vlax-ename->vla-object (cdr (assoc -1 ed))))
                (setq target_data_ (vlax-get-property target_obj_ propertie_name_))
                (setq result_data_ (cons target_data_ result_data_))
              ;
            )
          )
          ( (and 
                (= data_mode 4)
                (= (cdr (assoc 0 ed)) "LWPOLYLINE")
              )
            (progn
              ; (setq target_ (cons ent target_))
              ;main idea of code keep or delete don't affect with core code
                (setq target_obj_ (vlax-ename->vla-object (cdr (assoc -1 ed))))
                ;preloop_and_while
                  (setq propertie_name_list_i 0)
                  (setq propertie_name_list_sum_ ())
                  (while (< propertie_name_list_i (length propertie_name_list_))
                    (setq propertie_name_list_val_ (nth  propertie_name_list_i propertie_name_list_))
                    (setq propertie_name_list_val_val_ (vlax-get-property target_obj_ propertie_name_list_val_))
                    (setq propertie_name_list_sum_ (cons propertie_name_list_val_val_ propertie_name_list_sum_ ))
                    (setq propertie_name_list_i (+ propertie_name_list_i 1))
                  )
                ;
                (setq result_data_ (cons (reverse propertie_name_list_sum_) result_data_))
              ;
            )
          )
          ( (and 
                (= data_mode 1)
                (= (cdr (assoc 0 ed)) "SPLINE")
              )
            (progn
              ; (setq target_ (cons ent target_))
              ;main idea of code keep or delete don't affect with core code
                (setq target_obj_ (vlax-ename->vla-object (cdr (assoc -1 ed))))
                (setq target_data_ (vlax-get-property target_obj_ propertie_name_))
                (setq result_data_ (cons target_data_ result_data_))
              ;
            )
          )
          ( (and 
                (= data_mode 1)
                (= (cdr (assoc 0 ed)) "ELLIPSE")
              )
            (progn
              ; (setq target_ (cons ent target_))
              ;main idea of code keep or delete don't affect with core code
                (setq target_obj_ (vlax-ename->vla-object (cdr (assoc -1 ed))))
                (setq target_data_ (vlax-get-property target_obj_ propertie_name_))
                (setq result_data_ (cons target_data_ result_data_))
              ;
            )
          )
          ( (and 
                (= data_mode 1)
                (= (cdr (assoc 0 ed)) "CIRCLE")
              )
            (progn
              ; (setq target_ (cons ent target_))
              ;main idea of code keep or delete don't affect with core code
                (setq target_obj_ (vlax-ename->vla-object (cdr (assoc -1 ed))))
                (setq target_data_ (vlax-get-property target_obj_ propertie_name_))
                (setq result_data_ (cons target_data_ result_data_))
              ;
            )
          )
        )
        (setq ent (entnext ent))
      )
    )
  )

  (reverse result_data_)
)
(defun TA:Assembly_block_ (blk_obj_ )
  ; (setq blk_ename_ (car (entsel "specify Object")))
  ; (setq blk_obj_ (vlax-ename->vla-object blk_ename_))
  (setq blk_list_ ())
  (if (= (vla-get-objectname blk_obj_) "AcDbBlockReference")
    (progn
      (setq blkname (cdr (assoc 2 (entget (vlax-vla-object->ename blk_obj_)))))
      (setq bdef (tblobjname "BLOCK" blkname))
      (if (= (vl-prin1-to-string (type bdef)) "ENAME")
        (progn
          (setq nested (entnext bdef))
          
          (while 
            (and nested 
                (/= (cdr (assoc 0 (entget nested))) "ENDBLK")
            )
            (if (= (cdr (assoc 0 (entget nested))) "INSERT")
              (progn 


                (setq nested_obj_ (vlax-ename->vla-object nested))
                
                (if (= (vla-get-visible nested_obj_) :vlax-true)
                  (progn
                    (princ (strcat "\n  └─ Nested block: " (LM:effectivename nested_obj_)) )
                    (setq blk_list_ (cons (LM:effectivename nested_obj_) blk_list_))
                  )
                )
                
              )
            )
            (setq nested (entnext nested))
          )
        )
      )
    )
  )
  (TA:Count_item_in_list_ blk_list_ )
  


)
(defun c:mat1()
  ;selection_set_for_fillter_blk_name
    (if  ;pre_select_ssget_or_post_select_ssget
      (=
        (setq ss_pre_filter_set_xx_pre (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_pre (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_pre)
    )
  ;
  (setq ss_pre_filter_set_xx_main (TA:EF_Filter_ss_set_V2_ ss_pre_filter_set_xx_pre (list "000 - FAMELINE-CKST_AL.CELING_PANEL_300HK_@400mm_BOTTOM_VIEW")))
  (setq ss_pre_filter_set_xx_ (TA:EF_Filter_ss_set_V2_ ss_pre_filter_set_xx_pre (list "000 - FAMELINE-CKST_CODE_PANEL_DATA")))
  (setq ss_pre_filter_set_xx_ (TA:standard_list_croodinate_sorting ss_pre_filter_set_xx_ "X"))
  (setq panel_obj_ (vlax-ename->vla-object (ssname ss_pre_filter_set_xx_main 0)))
  (if (and 
         (= (sslength ss_pre_filter_set_xx_main ) 1)
         (= (LM:effectivename (setq panel_obj_ (vlax-ename->vla-object (ssname ss_pre_filter_set_xx_main 0 ))) ) "000 - FAMELINE-CKST_AL.CELING_PANEL_300HK_@400mm_BOTTOM_VIEW")
       )
    (progn
      (setq station_val (TA:rightstr (substr (getvar 'dwgname ) 1 8) 4))
      (setq level_val 
        (cond
          ((and 
             (or 
               (= station_val "PP18")
               (= station_val "PP19")
               (= station_val "PP20")
             )
             (= (TA:rightstr (substr (getvar 'dwgname) 1 16) 4) "4130")
           ) 
            (progn "Multi-perpose Level")
          )
          ((and 
             (or 
               (= station_val "PP17")
               (= station_val "PP18")
               (= station_val "PP19")
               (= station_val "PP20")
             )
             (= (TA:rightstr (substr (getvar 'dwgname) 1 16) 4) "4150")
           )
           (progn "Concourse Level")
          )
          ((and 
             (or 
               (= station_val "PP17")
               (= station_val "PP20")
             )
             (= (TA:rightstr (substr (getvar 'dwgname) 1 16) 4) "4180")
           ) 
            (progn "Platform Level")
          )
          ((and 
             (or 
               (= station_val "PP18")
               (= station_val "PP19")
             )
             (= (TA:rightstr (substr (getvar 'dwgname) 1 16) 4) "4160")
           ) 
            (progn ("Upper Platform Level"))
          )
          ((and 
             (or 
               (= station_val "PP18")
               (= station_val "PP19")
             )
             (= (TA:rightstr (substr (getvar 'dwgname) 1 16) 4) "4180")
           ) 
            (progn ("Lower Platform Level"))
          )
        )
      )
      (setq PANEL-TYPE_val (LM:getdynpropvalue panel_obj_ "PANEL-TYPE"))
      (setq panel_width_val_ (rtos (LM:getdynpropvalue panel_obj_ "panel_width") 2 0) )
      (setq panel_length_val "300")
    )
  )
  ;preloop_and_while
    (setq ss_pre_filter_set_xx_i 0)
    (while (< ss_pre_filter_set_xx_i (length ss_pre_filter_set_xx_))
      (setq ss_pre_filter_set_xx_ename_ (car (nth  ss_pre_filter_set_xx_i  ss_pre_filter_set_xx_ )))
      (setq ss_pre_filter_set_xx_obj_ (vlax-ename->vla-object  ss_pre_filter_set_xx_ename_))
      (LM:vl-setattributevalue ss_pre_filter_set_xx_obj_ "STATION_" (strcat station_val " " level_val ) )
      (LM:vl-setattributevalue ss_pre_filter_set_xx_obj_ "PANEL-TYPE" (strcat  panel_length_val "x" panel_width_val_ "mm." ) )
      (LM:vl-setattributevalue ss_pre_filter_set_xx_obj_ "name" "300HK" )
      
      
      (setq ss_pre_filter_set_xx_i (+ ss_pre_filter_set_xx_i 1))
    )
  ;
  


)

(defun TA:round-number (n step)
  ;(round-number 1898 1750) = 1750
  (* step (LM:round (/ n step)))
)
(defun round-300 (n / step)
  (setq step 300)
  (* step (LM:round (/ n step)))
)
(defun round-1750 (n / step)
  (setq step 1750.0)
  (* step (LM:round (/ n step)))
)


(defun round-1500 (n / step)
  (setq step 1500.0)
  (* step (LM:round (/ n step)))
)



  
(defun TA:editblock_asas (blockname line_color layer_name)
  ; (setq blockname "L2-2 - Surface Mounted LED Tube - 1223L x 170W x 93H - 36W-V1-CONCOURSE LEVEL_LIGHTING Copy 1")
  (setq line_color 256)
  ; (setq layer_name "008 - E&M_ACESSORIES_MAIN_COLOR_1")
  (setq blockname (LM:effectivename (vlax-ename->vla-object (car (entsel)))))
  (setq target_ '())
  (setq blkdef (tblobjname "BLOCK" blockname))
  (setq ent (entnext blkdef))
  (while ent
    (setq ed (entget ent))
    (if (= (cdr (assoc 0 ed)) "HATCH")
      (progn
        (setq target_ (cons ent target_))
        ;main idea of code keep or delete don't affect with core code
          (setq target_obj_ (vlax-ename->vla-object (cdr (assoc -1 ed))))
          (vla-put-color target_obj_  line_color)
          (vla-put-patternscale target_obj_  25)
          (vlax-dump-object target_obj_)
          ; (vla-put-EntityTransparency target_obj_ 80 )
        ;
      )
    )

    (setq ent (entnext ent))
  )
  (reverse target)
)

(defun c:temp1 ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i)) 
      (setq ss_pre_filter_set_xx_obj_ (vlax-ename->vla-object  ss_pre_filter_set_xx_ename_))
      (if (= (wcmatch (strcase (LM:effectivename ss_pre_filter_set_xx_obj_)) "*SIGN*") T)
        (progn
          (TA:editblock_ (LM:effectivename ss_pre_filter_set_xx_obj_) 256 "008 - E&M_SIGNAGE_MAIN_COLOR_1") 
        )
      )
      (setq ss_pre_filter_set_xx_i (+ ss_pre_filter_set_xx_i 1))
    )
  ;
)
(defun c:temp2 ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i)) 
      (setq ss_pre_filter_set_xx_obj_ (vlax-ename->vla-object  ss_pre_filter_set_xx_ename_))
      (if (and 
            ; (= (wcmatch (strcase (LM:effectivename ss_pre_filter_set_xx_obj_)) "*SIGN*") T)
            (= "kwai" "kwai")
          )
        (progn
          (TA:editblock_ (LM:effectivename ss_pre_filter_set_xx_obj_) 256 "008 - E&M_ACESSORIES_MAIN_COLOR_1") 
        )
      )
      (setq ss_pre_filter_set_xx_i (+ ss_pre_filter_set_xx_i 1))
    )
  ;
)


;summary_panel
  (defun c:300CU ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000 - DYNAMIC_ARRAY+COMBINE+VIEW_ASSCESSORIES_FAMELINE_AL.CELL_CELING_PANEL_300HK_@400mm_COMBINE_SET" ) ))
    
    ;preloop_and_while
      (setq ss_pre_filter_set_xx_i 0)
      (setq ss_pre_filter_set_xx_obj_total_panel_TL_ 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_total_panel (/ (LM:getdynpropvalue ss_pre_filter_set_xx_obj_ "array_panel_length") 400))
        
        (setq ss_pre_filter_set_xx_obj_total_panel_TL_ (+ ss_pre_filter_set_xx_obj_total_panel_TL_ ss_pre_filter_set_xx_obj_total_panel))
        (setq ss_pre_filter_set_xx_i (+ ss_pre_filter_set_xx_i 1))
      )
    ;
    ;
      (create-text-vla (vlax-3d-point (getpoint "insert point for text")) (strcat "300HK = " (rtos ss_pre_filter_set_xx_obj_total_panel_TL_ 2 0 ) "pc."   ) 5000 0 )
    
    (command "pselect"  ss_pre_filter_set_xx_ "" )
  )
  (defun c:310CU ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000 - DYNAMIC_ARRAY+COMBINE+VIEW_ASSCESSORIES_FAMELINE_AL.CELL_CELING_PANEL_300HK_@310mm_COMBINE_SET" ) ))
    
    ;preloop_and_while
      (setq ss_pre_filter_set_xx_i 0)
      (setq ss_pre_filter_set_xx_obj_total_panel_TL_ 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_total_panel (/ (LM:getdynpropvalue ss_pre_filter_set_xx_obj_ "array_panel_length") 310))
        
        (setq ss_pre_filter_set_xx_obj_total_panel_TL_ (+ ss_pre_filter_set_xx_obj_total_panel_TL_ ss_pre_filter_set_xx_obj_total_panel))
        (setq ss_pre_filter_set_xx_i (+ ss_pre_filter_set_xx_i 1))
      )
    ;
    ;
      (create-text-vla (vlax-3d-point (getpoint "insert point for text")) (strcat "300HK (C10) = " (rtos ss_pre_filter_set_xx_obj_total_panel_TL_ 2 0 ) "pc."   ) 5000 0 )
    (command "pselect"  ss_pre_filter_set_xx_ "" )
  )
  (defun c:360CU ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ 
                                  ss_pre_filter_set_xx_
                                  (list "000 - DYNAMIC_ARRAY+COMBINE+VIEW_ASSCESSORIES_FAMELINE_AL.CELL_CELING_PANEL_300HK_@310mm_COMBINE_SET" 
                                        "000 - DYNAMIC_ARRAY+COMBINE+VIEW_ASSCESSORIES_FAMELINE_AL.CELL_CELING_PANEL_360HK_@372mm_COMBINE_SET"
                                  )
                                )
    )
    
    ;preloop_and_while
      (setq ss_pre_filter_set_xx_i 0)
      (setq ss_pre_filter_set_xx_obj_total_panel_TL_ 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_total_panel (/ (LM:getdynpropvalue ss_pre_filter_set_xx_obj_ "array_panel_length") 372))
        
        (setq ss_pre_filter_set_xx_obj_total_panel_TL_ (+ ss_pre_filter_set_xx_obj_total_panel_TL_ ss_pre_filter_set_xx_obj_total_panel))
        (setq ss_pre_filter_set_xx_i (+ ss_pre_filter_set_xx_i 1))
      )
    ;
    ;
      (create-text-vla (vlax-3d-point (getpoint "insert point for text")) (strcat "360HK = " (rtos ss_pre_filter_set_xx_obj_total_panel_TL_ 2 0 ) "pc."   ) 5000 0 )
    (command "pselect"  ss_pre_filter_set_xx_ "" )
  )
  (defun c:3617CU ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ 
                                  ss_pre_filter_set_xx_
                                  (list "000 - DYNAMIC_ARRAY+COMBINE+VIEW_ASSCESSORIES_FAMELINE_AL.CELL_CELING_PANEL_300HK_@310mm_COMBINE_SET" 
                                  )
                                )
    )
    
    ;preloop_and_while
      (setq ss_pre_filter_set_xx_i 0)
      (setq ss_pre_filter_set_xx_obj_total_panel_TL_ 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_total_panel (/ (LM:getdynpropvalue ss_pre_filter_set_xx_obj_ "array_panel_length") 310))
        
        (setq ss_pre_filter_set_xx_obj_total_panel_TL_ (+ ss_pre_filter_set_xx_obj_total_panel_TL_ ss_pre_filter_set_xx_obj_total_panel))
        (setq ss_pre_filter_set_xx_i (+ ss_pre_filter_set_xx_i 1))
      )
    ;
    ;
      (create-text-vla (vlax-3d-point (getpoint "insert point for text")) (strcat "360HK = " (rtos ss_pre_filter_set_xx_obj_total_panel_TL_ 2 0 ) "pc."   ) 5000 0 )
    (command "pselect"  ss_pre_filter_set_xx_ "" )
  )
  (defun c:300VACU ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ 
                                  ss_pre_filter_set_xx_
                                  (list "A$Cf2bb5ec2"
                                      "000 - DYNAMIC_ARRAY_ASSCESSORIES_FAMELINE_AL.CELL_CELING_PANEL_300HK-VA_@400mm_BOTTOM_VIEW" 
                                  )
                                )
    )
    
    ;preloop_and_while
      (setq ss_pre_filter_set_xx_i 0)
      (setq ss_pre_filter_set_xx_obj_total_panel_TL_ 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        ; (setq ss_pre_filter_set_xx_obj_total_panel (/ (LM:getdynpropvalue ss_pre_filter_set_xx_obj_ "array_panel_length") 400))
        
        ; (setq ss_pre_filter_set_xx_obj_total_panel_TL_ (+ ss_pre_filter_set_xx_obj_total_panel_TL_ ss_pre_filter_set_xx_obj_total_panel))
        (setq ss_pre_filter_set_xx_i (+ ss_pre_filter_set_xx_i 1))
      )
    ;
    ;
      (create-text-vla (vlax-3d-point (getpoint "insert point for text")) (strcat "300VARIES = " (rtos (sslength ss_pre_filter_set_xx_) 2 0 ) "pc. (block)"   ) 5000 0 )
    (command "pselect"  ss_pre_filter_set_xx_ "" )
  )
  (defun c:tckgreen ()
    ;selection_set_for_fillter_blk_name
      (if  ;pre_select_ssget_or_post_select_ssget
        (=
          (setq ss_pre_filter_set_xx_ (ssget "i"
                                            (list
                                              (cons 0 "lwpolyline") ;type of object
                                              ; (cons 8 "000 - GRID")   ;kind of layer
                                              ; (cons 2 "000-GRID_LINE_DYN")       ;kind of nameblock
                                              (cons 62 3)           ;kind of color call sign with color code index
                                            )
                                      )
          )
          nil
        )
        (progn
          (setq ss_pre_filter_set_xx_ (ssget
                                            (list
                                              (cons 0 "lwpolyline") ;type of object
                                              ; (cons 8 "000 - GRID")   ;kind of layer
                                              ; (cons 2 "000-GRID_LINE_DYN")       ;kind of nameblock
                                              (cons 62 3)           ;kind of color call sign with color code index
                                            )
                                      )
          )
        )
        (sslength ss_pre_filter_set_xx_)
      )
    ;
    (create-text-vla (vlax-3d-point (getpoint "insert point for text")) (strcat "300VARIES = " (rtos (sslength ss_pre_filter_set_xx_) 2 0 ) "pc. (pline)"   ) 5000 0 )
    (command "pselect"  ss_pre_filter_set_xx_ "" )
  )
;


(defun TA:filter_select_ (ss_finder_ wildcard_val_)

  ;preloop_and_while
    (setq ss_finder_i 0)
    (setq ss_finder_newss_ (ssadd))
    (while (< ss_finder_i (sslength ss_finder_))
      (setq ss_finder_ename_ (ssname ss_finder_ ss_finder_i))
      (setq ss_finder_obj_ (vlax-ename->vla-object  ss_finder_ename_))
      (if (= (wcmatch (strcase (LM:effectivename ss_finder_obj_)) (strcase wildcard_val_) ) T)
        (progn
          (setq ss_finder_newss_ (ssadd ss_finder_ename_ ss_finder_newss_ ))
        )
      )
      (setq ss_finder_i (+ ss_finder_i 1))
    )
  ;
  (command "pselect"  ss_finder_newss_ "" )
)

(defun asasdasdsdasdasd ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;

  (TA:filter_select_ ss_pre_filter_set_xx_ "*sign*")
)



(defun c:pacu ()
  ;presetting
    (setvar "osmode" 0)
  ;
  ;estimate as-built panel 
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;filtering block name object 
      (setq ss_pre_filter_set_xx_ (TA:EF_Filter_ss_set_V2_ ss_pre_filter_set_xx_ (list "000 - FAMELINE-CKST_AL.CELING_PANEL_300HK_@400mm_BOTTOM_VIEW")))
    ;
    ;preloop_and_while
      (setq ss_pre_filter_set_xx_i 0)
      (setq final_new_ss_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_)) 
        (setq main_border_list_val_1 (TA:assembly_coordinate_coner (setq main_border_ (cdr (TA:ename+vla-getboundingbox ss_pre_filter_set_xx_obj_)))))
        (setq total_panel_ (/ (LM:getdynpropvalue ss_pre_filter_set_xx_obj_ "array_length") 400))
        (setq width_panel (LM:getdynpropvalue ss_pre_filter_set_xx_obj_ "panel_width"))
        ;frist pline box
          (create-plines 
            (list 
              (nth 0 main_border_list_val_1)
              (nth 1 main_border_list_val_1)
              (nth 2 main_border_list_val_1)
              (nth 3 main_border_list_val_1)
            )
            "close"
          )
          ;new_blk_entlast object
            (setq newpline_set_1_ename (entlast))
            (setq newpline_set_1_obj (vlax-ename->vla-object newpline_set_1_ename))
            (setq final_new_ss_ (ssadd newpline_set_1_ename final_new_ss_ ))
            (vla-put-layer newpline_set_1_obj "000 - SYMBOL CON_ASBUILT_WALL_SYMBOL_")
          ;
        ;
        ;sencond cross pline box
          (create-pline 
            (list 
              (nth 0 main_border_list_val_1)
              (nth 2 main_border_list_val_1)
            )
          )
          ;new_blk_entlast object
            (setq newpline_set_2_ename (entlast))
            (setq newpline_set_2_obj (vlax-ename->vla-object newpline_set_2_ename))
            (setq final_new_ss_ (ssadd newpline_set_2_ename final_new_ss_ ))
            (vla-put-layer newpline_set_2_obj "000 - SYMBOL CON_ASBUILT_WALL_SYMBOL_" )
          ;
          (create-pline 
            (list 
              (nth 3 main_border_list_val_1)
              (nth 1 main_border_list_val_1)
            )
          )
          ;new_blk_entlast object
            (setq newpline_set_3_ename (entlast))
            (setq newpline_set_3_obj (vlax-ename->vla-object newpline_set_3_ename))
            (setq final_new_ss_ (ssadd newpline_set_3_ename final_new_ss_ ))
            (vla-put-layer newpline_set_3_obj "000 - SYMBOL CON_ASBUILT_WALL_SYMBOL_")
          ; 
        ;
        (create-text-vla
          (vlax-3d-point (car (LM:intersections newpline_set_2_obj newpline_set_3_obj acextendnone)))
          (strcat "HK 300x" (rtos width_panel 2 0) "mm. " "total_panel_ = " (rtos total_panel_ 2 0) "pc"  )
          5
          0
        )
        ;new_blk_entlast object
          (setq newtext_ename (entlast)) 
          (setq newtext_obj (vlax-ename->vla-object newtext_ename))
          (setq newtext_obj (vlax-ename->vla-object newtext_ename))
          (vla-put-layer newtext_obj "000 - SYMBOL CON_ASBUILT_WALL_TEXT")
          (setq final_new_ss_ (ssadd newtext_ename final_new_ss_ ))
          (vla-put-height newtext_obj 400)
          (setq newtext_obj_ins_ (vlax-safearray->list (vlax-variant-value (vla-get-insertionpoint newtext_obj))))
          (vla-put-alignment newtext_obj  4)
          (vla-put-textalignmentpoint newtext_obj (vlax-3d-point newtext_obj_ins_))
        ;
    
        (setq ss_pre_filter_set_xx_i (+ ss_pre_filter_set_xx_i 1))
      )
    ;

  ;
  ;return
    (setvar "osmode" 1215)
  ;
  (command "pselect"  final_new_ss_ "" )
)


(defun c:text2list_t2l ()
  ;selection_set_for_fillter_blk_name
    (if  ;pre_select_ssget_or_post_select_ssget
      (=
        (setq ss_pre_filter_set_xx_ (ssget "i"
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (setq ss_pre_filter_set_xx_txt_list_val_ ())
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_text_val_ (vla-get-textstring ss_pre_filter_set_xx_obj_))
      (setq ss_pre_filter_set_xx_txt_list_val_ (cons (list ss_pre_filter_set_xx_obj_text_val_) ss_pre_filter_set_xx_txt_list_val_ ))
      (setq ss_pre_filter_set_xx_i (+ ss_pre_filter_set_xx_i 1))
    )
    (length ss_pre_filter_set_xx_txt_list_val_)
  ;
  (setq ss_pre_filter_set_xx_txt_list_val_ ss_pre_filter_set_xx_txt_list_val_)
  (length ss_pre_filter_set_xx_txt_list_val_)
  (foreach item ss_pre_filter_set_xx_txt_list_val_
    (princ (strcat "\n" (car item)))
  )
  
)


(defun c:ptext_ptx ()
  (setq prefix_text_ename_ (car (entsel "specify Object")))
  (setq prefix_text_obj_ (vlax-ename->vla-object prefix_text_ename_))
  (setq prefix_text_val_ ;Get-string by keep previous value
      (if
        (or
          (/= (setq prefix_text_val_val (getstring (strcat "\nSpecify Pattern name <" (if prefix_text_val_ prefix_text_val_ "") ">: ") ) ) "" )
        )
          (progn
            (setq prefix_text_val_ prefix_text_val_val)
            (setq prefix_text_val_keep_val_ prefix_text_val_val)
          )
        (setq prefix_text_val_val prefix_text_val_keep_val_)
      )
  )
  (vla-put-textstring prefix_text_obj_ (strcat  prefix_text_val_ " " (vla-get-textstring prefix_text_obj_ )))
)

(defun c:mergetxt ()
  ;selection_set_for_fillter_blk_name
    (if  ;pre_select_ssget_or_post_select_ssget
      (=
        (setq ss_pre_filter_set_xx_ (ssget "i"
                                          (list
                                            (cons 0 "INSERT,text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,text") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_for_insert_block_ (TA:EF_Filter_ss_set_v2_ ss_pre_filter_set_xx_ (list "000 - FAMELINE-CKST_AL.CELING_PANEL_300HK_@400mm_BOTTOM_VIEW")))
  (setq ss_pre_filter_set_xx_for_text__ (vla-get-textstring (vlax-ename->vla-object (ssname (TA:Prop_Filter_ss_set_ ss_pre_filter_set_xx_ 'ObjectName "AcDbText" ) 0))))
  
  (LM:vl-setattributevalue (vlax-ename->vla-object (ssname ss_pre_filter_set_xx_for_insert_block_ 0)) "panel-type" ss_pre_filter_set_xx_for_text__)
  (command "pselect"   "" )

)



(defun c:tt5 ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  
  
  (setq 1st_pt_ (getpoint "specify conner"))
  (setq cen_pt_ (getcorner 1st_pt_ "specify conner"))
  (TA:midpoint 1st_pt_ cen_pt_)
  (vla-put-insertionpoint (vlax-ename->vla-object (ssname ss_pre_filter_set_xx_ 0)) (vlax-3d-point (TA:midpoint 1st_pt_ cen_pt_)))
)




(defun c:Hstart_ ()
  ; (command "ucs" "w")
  ; (setq hatch_ename_ (car (entsel "specify Object")))
  ; (setq hatch_obj_ (vlax-ename->vla-object hatch_ename_))
  ; (setq hatch_obj_ins_ (vlax-safearray->list (vlax-variant-value (vla-get-origin  hatch_obj_))))
  ; (command "point"  hatch_obj_ins_  )
  ; (setq ob (entlast))
  ; (command "ucs" "ob" hatch_ename_ )
  ; (command "ucs" "z"  270 )
  
  (command "ucs" "w")
  (setvar "snapmode" 0)
  ; (setq hatch_ename_ (car (entsel "specify Object")))
  (command "ucs" "ob"  )
  ; (command "ucs" "z"  270 )
  (setvar "snapmode" 1)   
  (setvar "osmode" 1027)
)

(defun c:point_to_block_pt2blk ()
  ;selection_set_for_fillter_blk_name
    (if  ;pre_select_ssget_or_post_select_ssget
      (=
        (setq ss_pre_filter_set_xx_ (ssget "i"
                                          (list
                                            (cons 0 "point") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "point") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_center (vlax-safearray->list (vlax-variant-value (vla-get-coordinates ss_pre_filter_set_xx_obj_))))
      
      (TA:vla-insertblock
        ; "000 - FAMELINE-CKST_AS-BUILT_POINT_REV03"
        "000 - FAMELINE-CKST_AS-BUILT_POINT_REV01"
        ss_pre_filter_set_xx_obj_center
        5
        (deg-to-rad 45)
        
      )
      (setq ss_pre_filter_set_xx_i (+ ss_pre_filter_set_xx_i 1))
    )
  ;

)

(defun c:temo_lowy ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_V2_ ss_pre_filter_set_xx_ (list "000 - FAMELINE-CKST_AS-BUILT_POINT_REV01")))
  (setq low_y (car (car (TA:standard_list_croodinate_sorting ss_pre_filter_set_xx_ "Y"))))
  (command "pselect"  low_y "" )
)
(defun c:temo_highy ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_V2_ ss_pre_filter_set_xx_ (list "000 - FAMELINE-CKST_AS-BUILT_POINT_REV01")))
  (setq high_y (car (reverse (TA:standard_list_croodinate_sorting ss_pre_filter_set_xx_ "Y"))))
  (command "pselect"  high_y "" )
  
)




    



  
    
  
  (defun TA:dynamic_joint_ ()
    (setq 1st_J_ename_ (car (entsel "specify Object")))
    (setq 1st_J_obj_   (vlax-ename->vla-object 1st_J_ename_))
    (setq 1st_J_obj_ins_ (vlax-safearray->list (vlax-variant-value (vla-get-insertionpoint 1st_J_obj_))))
    (setq 1st_J_obj_ro_top (TA:ModifyRotation (rad-to-deg (vla-get-rotation 1st_J_obj_)) +90))
    (setq 1st_J_obj_ro_bot (TA:ModifyRotation (rad-to-deg (vla-get-rotation 1st_J_obj_)) +270))
    (setq 1st_J_top_point_ (polar 1st_J_obj_ins_ (deg-to-rad 1st_J_obj_ro_top) 12.5 ))
    (setq 1st_J_bot_point_ (polar 1st_J_obj_ins_ (deg-to-rad 1st_J_obj_ro_bot) 12.5 ))
    
    (setq 2nd_J_ename_ (car (entsel "specify Object")))
    (setq 2nd_J_obj_   (vlax-ename->vla-object 2nd_J_ename_))
    (setq 2nd_J_obj_ins_ (vlax-safearray->list (vlax-variant-value (vla-get-insertionpoint 2nd_J_obj_))))
    (setq 2nd_J_obj_ro_top (TA:ModifyRotation (rad-to-deg (vla-get-rotation 2nd_J_obj_)) +90))
    (setq 2nd_J_obj_ro_bot (TA:ModifyRotation (rad-to-deg (vla-get-rotation 2nd_J_obj_)) +270))
    (setq 2nd_J_top_point_ (polar 2nd_J_obj_ins_ (deg-to-rad 2nd_J_obj_ro_top) 12.5 ))
    (setq 2nd_J_top_point_length_ 
           (polar 2nd_J_top_point_ 
                  
                  (deg-to-rad 2nd_J_obj_ro_top) 
                  12.5 
           )
    )
    (setq 2nd_J_bot_point_ (polar 2nd_J_obj_ins_ (deg-to-rad 2nd_J_obj_ro_bot) 12.5 ))

    
    ;
  )

  

  (defun c:dynjoint ()
    ;
      (setq 1st_J_ename_ (car (entsel "specify Object")))
      (setq 1st_J_obj_   (vlax-ename->vla-object 1st_J_ename_))
      (setq 1st_J_obj_ins_ (vlax-safearray->list (vlax-variant-value (vla-get-insertionpoint 1st_J_obj_))))
      (setq 1st_J_obj_ro_top (TA:ModifyRotation (rad-to-deg (vla-get-rotation 1st_J_obj_)) +90))
      (setq 1st_J_obj_ro_bot (TA:ModifyRotation (rad-to-deg (vla-get-rotation 1st_J_obj_)) +270))
      (setq 1st_J_top_point_ (polar 1st_J_obj_ins_ (deg-to-rad 1st_J_obj_ro_top) 12.5 ))
      (setq 1st_J_bot_point_ (polar 1st_J_obj_ins_ (deg-to-rad 1st_J_obj_ro_bot) 12.5 ))
      (setq 1st_J_top_point_length (polar 1st_J_top_point_ 
                                          (if 
                                            (>= (vla-get-xscalefactor 1st_J_obj_) 1)
                                            (progn (vla-get-rotation 1st_J_obj_))
                                            (deg-to-rad (- (rad-to-deg (vla-get-rotation 1st_J_obj_)) 180))
                                          )
                                          50000
                                  )
      )
      (setq 1st_J_bot_point_length (polar 1st_J_bot_point_ 
                                          (if 
                                            (>= (vla-get-xscalefactor 1st_J_obj_) 1)
                                            (progn (vla-get-rotation 1st_J_obj_))
                                            (deg-to-rad (- (rad-to-deg (vla-get-rotation 1st_J_obj_)) 180))
                                          )
                                          50000
                                  )
      )
    ;
    ;
      (setq 2nd_J_ename_ (car (entsel "specify Object")))
      (setq 2nd_J_obj_   (vlax-ename->vla-object 2nd_J_ename_))
      (setq 2nd_J_obj_ins_ (vlax-safearray->list (vlax-variant-value (vla-get-insertionpoint 2nd_J_obj_))))
      (setq 2nd_J_obj_ro_top (TA:ModifyRotation (rad-to-deg (vla-get-rotation 2nd_J_obj_)) +90))
      (setq 2nd_J_obj_ro_bot (TA:ModifyRotation (rad-to-deg (vla-get-rotation 2nd_J_obj_)) +270))
      (setq 2nd_J_top_point_ (polar 2nd_J_obj_ins_ (deg-to-rad 2nd_J_obj_ro_top) 12.5 ))
      (setq 2nd_J_bot_point_ (polar 2nd_J_obj_ins_ (deg-to-rad 2nd_J_obj_ro_bot) 12.5 ))
      (setq 2nd_J_top_point_length (polar 2nd_J_top_point_ 
                                          (if 
                                            (>= (vla-get-xscalefactor 2nd_J_obj_) 1)
                                            (progn (vla-get-rotation 2nd_J_obj_))
                                            (deg-to-rad (- (rad-to-deg (vla-get-rotation 2nd_J_obj_)) 180))
                                          )
                                          50000
                                  )
      )
      (setq 2nd_J_bot_point_length (polar 2nd_J_bot_point_ 
                                          (if 
                                            (>= (vla-get-xscalefactor 2nd_J_obj_) 1)
                                            (progn (vla-get-rotation 2nd_J_obj_))
                                            (deg-to-rad (- (rad-to-deg (vla-get-rotation 2nd_J_obj_)) 180))
                                          )
                                          50000
                                  )
      )
    ;
    ;joint left process
      (LM:setdynpropvalue 
        1st_J_obj_
        "distance1"
        (distance 1st_J_top_point_ 
                  (inters 1st_J_top_point_ 
                          1st_J_top_point_length
                          2nd_J_top_point_
                          2nd_J_top_point_length
                  )
        )
      )
      (LM:setdynpropvalue 
        2nd_J_obj_
        "distance1"
        (distance 2nd_J_top_point_ 
                  (inters 1st_J_top_point_ 
                          1st_J_top_point_length
                          2nd_J_top_point_
                          2nd_J_top_point_length
                  )
        )
      )
    ;joint left process
    ;joint right process
      (LM:setdynpropvalue 
        1st_J_obj_
        "distance2"
        (distance 1st_J_bot_point_ 
                  (inters 1st_J_bot_point_ 
                          1st_J_bot_point_length
                          2nd_J_bot_point_
                          2nd_J_bot_point_length
                  )
        )
      )
      (LM:setdynpropvalue 
        2nd_J_obj_
        "distance2"
        (distance 2nd_J_bot_point_ 
                  (inters 1st_J_bot_point_ 
                          1st_J_bot_point_length
                          2nd_J_bot_point_
                          2nd_J_bot_point_length
                  )
        )
      )
    ;
  )
 
  (defun c:mkwdline_ss1 ()
    ;selection_set_for_fillter_blk_name
      (if  ;pre_select_ssget_or_post_select_ssget
        (=
          (setq ss_pre_filter_set_mkwdline_ (ssget "i"
              (list
                (cons 0 "line,lwpolyline") ;type of object
                (cons 8 "009 - AHP_06_FRAMING_MAIN_COLOR_2,009 - AHP_06_FRAMING_MAIN_COLOR_1")   ;kind of layer
                ; (cons 2 "000-GRID_LINE_DYN")       ;kind of nameblock
                ; (cons 62 1)           ;kind of color call sign with color code index
              )
            )
          )
          nil
        )
        (progn
          (setq ss_pre_filter_set_mkwdline_ (ssget
              (list
                (cons 0 "line,lwpolyline") ;type of object
                (cons 8 "009 - AHP_06_FRAMING_MAIN_COLOR_2,009 - AHP_06_FRAMING_MAIN_COLOR_1")   ;kind of layer
                ; (cons 2 "000-GRID_LINE_DYN")       ;kind of nameblock
                ; (cons 62 1)           ;kind of color call sign with color code index
              )
            )
          )
          (sslength ss_pre_filter_set_mkwdline_)
        )
      )
    ;
    (setq ss_pre_filter_set_mkwd_line_wd_ (TA:Prop_Filter_ss_set_ ss_pre_filter_set_mkwdline_ 'ObjectName "AcDbLine" ))
    ; (command "pselect"  ss_pre_filter_set_mkwd_line_wd_ "" )
    (setq newtron_ss_ (TA:combine_selection_set_ ss_pre_filter_set_mkwd_line_wd_ ss_pre_filter_set_mkwdline_ ))
    (command "pedit" "m" newtron_ss_ "" "y" "w" 25  )
  )

  (defun c:tempcall ()
    (c:createC06layout)
    (setq Er-msg_1 (vl-catch-all-apply (function (lambda () (load "C:/Users/tawan.t/Documents/GitHub/TA_COMPELETE/000 - FOR_CREATE_LAYER_.lsp") ) ) ) )
    (c:crelayAHP06)
    (c:crelayHIDEOBJ_)
    
    (command "-LAYER" "filter" "new" "group"  
                         "PPLINE-FAMELINE"
                         "*001 - ASCESSORIES*" ;(add layer name to filter, Can use wildcard for adding)
                         "PPLINE-FAMELINE_ASCESSORIES_" 
                         "" 
    )
    (command "-LAYER" "filter" "new" "group"  
                         "PPLINE-FAMELINE"
                         "" ;(add layer name to filter, Can use wildcard for adding)
                         "PPLINE-FAMELINE_PANEL" 
                         "" 
    )
    (command "-layer"
            "filter"
            "edit"
            "PPLINE-FAMELINE_PANEL" ; (Filter name must be sensitibe case)
            "add"
            "A04_TUBE SERIES" ;(add layer name to filter, Can use wildcard for adding)
             "add"
            "A11_ALU.SOLID SHEET"  ;(add layer name to filter, Can use wildcard for adding)
            "x" ""
    )
    (command "mspace")
    (c:PPLINE_CKST_viewport_layer_CKST-VPC06)
  )


  (defun c:STAHP ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    
    (setq target_obj_ (vlax-ename->vla-object (ssname ss_pre_filter_set_xx_ 0)))
    (if (= (getvar "worlducs") 0)
      (progn
        (setq target_obj_ins_ (trans (vlax-safearray->list (vlax-variant-value (vla-get-insertionpoint target_obj_))) 0 1))
        (setq target_obj_ins_nextpt (getpoint target_obj_ins_ ) )
        (setq target_obj_ins_dist_ (distance target_obj_ins_ target_obj_ins_nextpt ) )
      )
    )
    (if (= (getvar "worlducs") 1)
      (progn
        (setq target_obj_ins_ (vlax-safearray->list (vlax-variant-value (vla-get-insertionpoint target_obj_))))
        (setq target_obj_ins_nextpt (getpoint target_obj_ins_ ) )
        (setq target_obj_ins_dist_ (distance target_obj_ins_ target_obj_ins_nextpt )   )
      )
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (LM:setdynpropvalue ss_pre_filter_set_xx_obj_ "AHP_length" (- (LM:round  target_obj_ins_dist_) 50))
        (setq ss_pre_filter_set_xx_i (+ ss_pre_filter_set_xx_i 1))
      )
    ;
    
    
    
  )
  (defun c:offlayer ()
    (setq layeroff_ename_ (car (nentsel "specify Object")))
    (setq layeroff_obj_ (vlax-ename->vla-object layeroff_ename_))
    (command "-layer" "off" (vla-get-layer layeroff_obj_) "")
  )

  (defun c:multi_viewportclip_mulvpc ()
    (setq vpc_ename_ (car (entsel "specify Object")))
    (setq vpc_obj_ (vlax-ename->vla-object vpc_ename_))
    (setq vpc_ss_ (ssadd))
    (setq vpc_ss_ (ssadd vpc_ename_ vpc_ss_))
    (if  ;pre_select_ssget_or_post_select_ssget
      (=
        (setq ss_pre_filter_set_xx_ (ssget "i"
                                          (list
                                            (cons 0 "LWPOLYLINE") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "LWPOLYLINE") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    ;preloop_and_while
      (setq ss_i 0)
      (while (< ss_i (- (sslength ss_pre_filter_set_xx_) 1))
        ;new_blk_entlast object
          (vla-copy vpc_obj_)
          (setq ss_ename (entlast))
          (setq ss_obj (vlax-ename->vla-object ss_ename))
          (setq vpc_ss_ (ssadd ss_ename vpc_ss_))
        ;
    
        (setq ss_i (+ ss_i 1))
      )
    ;
    (vla-copy vpc_obj_)
    

    ;selection_set_for_fillter_blk_name
      ;preloop_and_while
        (setq ss_pre_filter_set_xx_i 0)
        (while (< ss_pre_filter_set_xx_i (sslength ss_pre_filter_set_xx_))
          (setq ss_pre_filter_set_xx_ename_ (ssname ss_pre_filter_set_xx_ ss_pre_filter_set_xx_i))
          (setq vpc_ss_ename (ssname  vpc_ss_ ss_pre_filter_set_xx_i))
          (command "vpclip" vpc_ss_ename ss_pre_filter_set_xx_ename_)
      
          (setq ss_pre_filter_set_xx_i (+ ss_pre_filter_set_xx_i 1))
        )
      ;
  )
  (defun c:c:multi_viewportclipdelete_vcdel ()
    ;selection_set_for_fillter_blk_name
      (if  ;pre_select_ssget_or_post_select_ssget
        (=
          (setq ss_pre_filter_set_xx_ (ssget "i"
                                            (list
                                              (cons 0 "LWPOLYLINE") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "LWPOLYLINE") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (command "vpclip" ss_pre_filter_set_xx_ename_ "d"  )
        (setq ss_pre_filter_set_xx_i (+ ss_pre_filter_set_xx_i 1))
      )
    ;

  )



;CKST-FAMELINE_ASPG_FUNC_
  (defun c:tempPG ()
    (setq input_height (cond ( (getint (strcat "\nspecify get heigth \n<" (rtos (setq input_height (cond (input_height) (1.0) ) ) ) "> : " ) ) ) (input_height) ) )
    (setq frame_ename_ (car (entsel "specify Object")))
    (setq frame_obj_ (vlax-ename->vla-object frame_ename_))
    
    (setq cop_length_ (/ (float input_height) (LM:roundup (/ (float input_height) 1500) 1)))
    (setq cop_i_ (- (LM:roundup (/ (float input_height) 1500) 1) 1) )
    (LM:setdynpropvalue frame_obj_ "FRAME_HEIGHT" cop_length_ )
    ;preloop_and_while
      (setq new_i 0)
      (while (< new_i cop_i_)
        (vla-copy (setq frame_obj_ (vlax-ename->vla-object frame_ename_)))
        ;new_blk_entlast object
          (setq newmove__ename (entlast))
          (setq newmove__obj (vlax-ename->vla-object newmove__ename))
          (if (= (LM:getdynpropvalue newmove__obj "view" ) "VisibilityState0")
            (progn
              (LM:setdynpropvalue newmove__obj "view" "1_cut_view")
            )
          )
          (if (= (LM:getdynpropvalue newmove__obj "view" ) "4_side_L_view")
            (progn
              (LM:setdynpropvalue newmove__obj "view" "4_side_R_view")
            )
          )
        ;
        (TA:move_axis_insertionpoint newmove__obj "Y" (* cop_length_ (+ new_i 1)))
        (setq new_i (+ new_i 1))
      )
    ;
  )
  (defun c:tempgr ()
    ; (setq input_height (cond ( (getint (strcat "\nspecify get heigth \n<" (rtos (setq input_height (cond (input_height) (1.0) ) ) ) "> : " ) ) ) (input_height) ) )
    (setq refdim_ename_ (car (entsel "specify dim Object")))
    (setq refdim_obj_ (vlax-ename->vla-object refdim_ename_))
    (setq input_height (LM:round (vla-get-measurement refdim_obj_)) )
    (setq frame_ename_ (car (entsel "specify Object")))
    (setq frame_obj_ (vlax-ename->vla-object frame_ename_))
    
    (setq cop_length_ (/ (/ (float input_height) (LM:roundup (/ (float input_height) 1500) 1)) 50))
    (setq cop_i_ (- (LM:roundup (/ (float input_height) 1500) 1) 1) )
    
    ;preloop_and_while
      (setq new_i 0)
      (setq grid_ss_ (ssadd))
      (while (< new_i cop_i_)
        (vla-copy (setq frame_obj_ (vlax-ename->vla-object frame_ename_)))
        ;new_blk_entlast object
          (setq newmove__ename (entlast))
          (setq newmove__obj (vlax-ename->vla-object newmove__ename))
          (setq grid_ss_ (ssadd newmove__ename grid_ss_))
          
        ;
        (TA:move_axis_insertionpoint newmove__obj "Y" (* cop_length_ (+ new_i 1)))
        (setq new_i (+ new_i 1))
      )
    ;
    (command "pselect"  grid_ss_ "" )
  )
  (defun c:putHframe ()
    (defun TAS:000_ASPG_TYP_FILES_LOUVER_WITH_C-C_FRAME_DYN_VIEW_PUT_HEIGHT_BLOCK (frame_obj_ all_height)
      ; (setq frame_ename_ (car (entsel "specify input_height Object")))
      ; (setq frame_obj_ (vlax-ename->vla-object frame_ename_))
      (setq cop_length_ (/ (float input_height) (LM:roundup (/ (float input_height) 1500) 1)))
      (setq cop_i_ (- (LM:roundup (/ (float input_height) 1500) 1) 1) )
      (LM:setdynpropvalue frame_obj_ "FRAME_HEIGHT" cop_length_ )
      (if (or 
            (= (LM:getdynpropvalue frame_obj_ "view" ) "4_side_R_view")
            (= (LM:getdynpropvalue frame_obj_ "view" ) "4_side_L_view")
          )
        (progn
          (LM:setdynpropvalue frame_obj_ "view" "4_side_L_view")
          (LM:setdynpropvalue frame_obj_  "PANEL_HEIGHT" all_height)
        )
      )
      (if (or 
            (= (LM:getdynpropvalue frame_obj_ "view" ) "1_cut_view")
            (= (LM:getdynpropvalue frame_obj_ "view" ) "VisibilityState0" )
          )
        (progn
          (LM:setdynpropvalue frame_obj_ "view" "VisibilityState0")
          (LM:setdynpropvalue frame_obj_  "PANEL_HEIGHT" all_height)
        )
      )
      ;preloop_and_while
        (setq new_i 0)
        (while (< new_i cop_i_)
          (vla-copy frame_obj_)
          ;new_blk_entlast object
            (setq newmove__ename (entlast))
            (setq newmove__obj (vlax-ename->vla-object newmove__ename))
            (if (= (LM:getdynpropvalue newmove__obj "view" ) "VisibilityState0")
              (progn
                (LM:setdynpropvalue newmove__obj "view" "1_cut_view")
                (LM:setdynpropvalue newmove__obj "PANEL_HEIGHT" all_height)
              )
            )
            (if (= (LM:getdynpropvalue newmove__obj "view" ) "4_side_L_view")
              (progn
                (LM:setdynpropvalue newmove__obj "view" "4_side_R_view")
                (LM:setdynpropvalue newmove__obj  "PANEL_HEIGHT" all_height)
              )
            )
          ;
          (TA:move_axis_insertionpoint newmove__obj "Y" (* cop_length_ (+ new_i 1)))
          (setq new_i (+ new_i 1))
        )
      ;
    )
    ;
      (setq Er-msg_ 
        (vl-catch-all-apply 
          (function 
            (lambda () 
              (setvar "selectionpreview" 3)
              (setq get_height_ename_ (car (entsel "specify reference panel Object")))
              (setq get_height_obj_ (vlax-ename->vla-object get_height_ename_))
              (setq input_height (LM:getdynpropvalue get_height_obj_ "distance2"  ))
              (setvar "selectionpreview" 0)
            )
          )
        )
      )
      (if (and
            (= (vl-catch-all-error-p Er-msg_) T)
          )
        (progn
          (setq input_height (cond ( (getint (strcat "\nspecify get heigth \n<" (rtos (setq input_height (cond (input_height) (1.0) ) ) ) "> : " ) ) ) (input_height) ) )
        )
      )
    ;
    ;while selection process
      (setq ERR_ nil)
      (setq all_height input_height)
      (while ;for keep insertion point and dist. fix length one side
        (and
          (= (vl-catch-all-error-p ERR_) nil)
        )
        (setq ERR_
          (vl-catch-all-apply
            (function
              (lambda ()
                ;sslection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)
                  )
                  (setq ss_pre_filter_set_xx_ (TA:EF_Filter_ss_set_V2_ ss_pre_filter_set_xx_ (list "000_ASPG_TYP_FILES_LOUVER_WITH_C-C_TRIM_FRONT_VIEW" "000_ASPG_TYP_FILES_LOUVER_WITH_C-C_FRAME_DYN_VIEW" "000_ASPG_TYP_FILES_LOUVER_WITH_C-C_FRAME_DYN_VIEW_SUB")))
                ;
                ;preloop_and_while
                  (setq ss_pre_filter_set_xx_i 0)
                  (while (< ss_pre_filter_set_xx_i (sslength ss_pre_filter_set_xx_))
                    (setq ss_pre_filter_set_xx_ename_ (ssname ss_pre_filter_set_xx_ ss_pre_filter_set_xx_i))
                    (setq ss_pre_filter_set_xx_obj_ (vlax-ename->vla-object  ss_pre_filter_set_xx_ename_))
                    (TAS:000_ASPG_TYP_FILES_LOUVER_WITH_C-C_FRAME_DYN_VIEW_PUT_HEIGHT_BLOCK ss_pre_filter_set_xx_obj_ all_height)
                    (setq ss_pre_filter_set_xx_i (+ ss_pre_filter_set_xx_i 1))
                  )
                ;
              )
            )
          )
        )
      )
    ;
  )
  (defun TA:insert-trim_ASPGTRarea (trim-area_obj_)
    ; (setq trim-area_ename_ (car (entsel "specify Object")))
    ; (setq trim-area_obj_ (vlax-ename->vla-object trim-area_ename_))
    (setq trim-area_obj_ins_ (vlax-safearray->list (vlax-variant-value (vla-get-insertionpoint trim-area_obj_))))
    
    (if (= (getvar "worlducs") 0)(progn (setq trim-area_obj_ins_ (trans trim-area_obj_ins_ 1 1))) trim-area_obj_ins_ )
    (TA:vla-insertblock 
      "000_AREA_ASPG_AREA-BOX"
      trim-area_obj_ins_
      1
      (vla-get-rotation trim-area_obj_)
    )
    ;new_blk_entlast object
      (setq new-insert_ename (entlast))
      (setq new-insert_obj (vlax-ename->vla-object new-insert_ename))
      
      (if (or 
            (= (LM:effectivename trim-area_obj_ )"000_ASPG_TYP_FILES_LOUVER_WITH_C-C_TRIM_FRONT_VIEW")
            (= (LM:effectivename trim-area_obj_) "000_ASPG_TYP_FILES_LOUVER_WITH_C-E_TRIM_FRONT_VIEW" )
            (= (LM:effectivename trim-area_obj_) "000_ASPG_TYP_FILES_FRAMING_EXTR_BREAKLINE_FRONT_VIEW"  )
            (= (LM:effectivename trim-area_obj_) "000_ASPG_TYP_FILES_LOUVER_WITH_C-E_TRIM_FRONT_VIEW_SUB"  )
            (= (LM:effectivename trim-area_obj_) "000_ASPG_TYP_FILES_LOUVER_WITH_C-C_TRIM_FRONT_VIEW_SUB"  )
          )
        (progn
          
          (LM:setdynpropvalue new-insert_obj "trim-length" (LM:getdynpropvalue trim-area_obj_ "distance2"  ))
          (LM:setdynpropvalue new-insert_obj "trim-width" 120)
        )
      )
      (if (or 
            (= (LM:effectivename trim-area_obj_ ) "000_ASPG_TYP_FILES_FRAMING_EXTR_BREAKLINE_FRONT_VIEW")
          )
        (progn
          (vla-put-rotation new-insert_obj (deg-to-rad (TA:ModifyRotation (rad-to-deg (vla-get-rotation new-insert_obj) ) -90 )))
          (LM:setdynpropvalue new-insert_obj "trim-length" (+
                                                             (LM:getdynpropvalue trim-area_obj_ "distance1"  )
                                                             (LM:getdynpropvalue trim-area_obj_ "distance2"  )
                                                           )
          )
          (LM:setdynpropvalue new-insert_obj "trim-width" 120)
        )
      )
    ;
  )
  (defun c:sstrimarea ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_V2_ ss_pre_filter_set_xx_ (list "000_ASPG_TYP_FILES_LOUVER_WITH_C-C_TRIM_FRONT_VIEW" 
                                                                                     "000_ASPG_TYP_FILES_FRAMING_EXTR_BREAKLINE_FRONT_VIEW"
                                                                                     "000_ASPG_TYP_FILES_LOUVER_WITH_C-E_TRIM_FRONT_VIEW"
                                                                                     "000_ASPG_TYP_FILES_LOUVER_WITH_C-E_TRIM_FRONT_VIEW"
                                                                                     "000_ASPG_TYP_FILES_LOUVER_WITH_C-E_TRIM_FRONT_VIEW_SUB"
                                                                                     "000_ASPG_TYP_FILES_LOUVER_WITH_C-C_TRIM_FRONT_VIEW_SUB" 
                                                                               )))
    ;preloop_and_while
      (setq ss_pre_filter_set_xx_i 0)
      (setq ss-insert-new (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (TA:insert-trim_ASPGTRarea ss_pre_filter_set_xx_obj_)
        (setq ss-insert-new (ssadd (entlast) ss-insert-new ))
        (setq ss_pre_filter_set_xx_i (+ ss_pre_filter_set_xx_i 1))
      )
      (command "pselect"  ss-insert-new "" )
    ;
  )
  (defun c:ASPG_OFFSET_FRAME ()
    (_StartUndo DOC)
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_ ss_pre_filter_set_xx_ "000_ASPG_TYP_FILES_LOUVER_WITH_C-C_FRAME_DYN_VIEW"))
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (TA:move_polar_insertionpoint ss_pre_filter_set_xx_obj_ "X" 10)
        (LM:setdynpropvalue ss_pre_filter_set_xx_obj_ "frame_width" (- (LM:getdynpropvalue ss_pre_filter_set_xx_obj_ "frame_width" ) 20))
        (setq ss_pre_filter_set_xx_i (+ ss_pre_filter_set_xx_i 1))
      )
    ;
    (_EndUndo DOC)
  )
  (defun c:tempust ()
    (setq s1 (getpoint))
    (setq s2 (getpoint s1))
    (TA:vla-insertblock 
      "000_CKST_FAMELINE_U-PROFILE_TOP_VIEW__STEELFAME"
      s1
      1
      (angle s1 s2)
    )
    ;new_blk_entlast object
      (setq ss_ename (entlast))
      (setq ss_obj (vlax-ename->vla-object ss_ename))
      (LM:setdynpropvalue ss_obj "distance1" (distance s1 s2))
    ;
  )
  (defun c:coplevelName_COPLV ()
    ;selection_set_for_fillter_blk_name
      (if  ;pre_select_ssget_or_post_select_ssget
        (=
          (setq ss_pre_filter_set_xx_ (ssget "i"
                                            (list
                                              (cons 0 "TEXT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "TEXT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;get_data_process_for_fillter_blk_name
      ;preloop_and_while
        (setq ss_pre_filter_set_xx_i 0)
        (setq new_list_for_sorting_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_textstr_ (vla-get-textstring ss_pre_filter_set_xx_obj_))
          (setq sum_ (list 
                       ss_pre_filter_set_xx_obj_ins_
                       ss_pre_filter_set_xx_obj_textstr_
                     )
          )
          (setq new_list_for_sorting_ (cons sum_ new_list_for_sorting_ ))
          
          
          (setq ss_pre_filter_set_xx_i (+ ss_pre_filter_set_xx_i 1))
        )
      ;
      ;TA:stanndard_lambda_sorting
        (setq new_list_for_sorting_sorted_ (vl-sort new_list_for_sorting_  ;bigest open indent list
                                                  (function 
                                                    (lambda (a b) 
                                                      (> (nth 1 (car a)) (nth 1 (car b)))
                                                    )
                                                  )
                              ) ;bigest close indent list
        )
      ;
      ;input_att_process
        (setq level_str_ename_ (car (entsel "specify Object")))
        (setq level_str_obj_ (vlax-ename->vla-object level_str_ename_))
        (LM:vl-setattributevalue level_str_obj_ "LV_NAME_1" "" )
        (LM:vl-setattributevalue level_str_obj_ "LV_NAME_2" "" )
        (LM:vl-setattributevalue level_str_obj_ "LV_NAME_3" "" )
        
        
        (cond
          (;_case_1
             (and
                (= (length new_list_for_sorting_sorted_ ) 2)
             )
             (progn 
               (LM:vl-setattributevalue 
                 level_str_obj_
                 "LV_NAME_2"
                 (cadr (nth 0 new_list_for_sorting_sorted_))
               )
               (LM:vl-setattributevalue 
                 level_str_obj_
                 "LV_NAME_3"
                 (cadr (nth 1 new_list_for_sorting_sorted_))
               )
               (princ "_case_1")
             )
          )
          (;_case_1
             (and
                (= (length new_list_for_sorting_sorted_ ) 3)
             )
             (progn 
               (LM:vl-setattributevalue 
                 level_str_obj_
                 "LV_NAME_1"
                 (cadr (nth 0 new_list_for_sorting_sorted_))
               )
               (LM:vl-setattributevalue 
                 level_str_obj_
                 "LV_NAME_2"
                 (cadr (nth 1 new_list_for_sorting_sorted_))
               )
               (LM:vl-setattributevalue 
                 level_str_obj_
                 "LV_NAME_3"
                 (cadr (nth 2 new_list_for_sorting_sorted_))
               )
               (princ "_case_1")
             )
          )
          
          
          
        )
        

      ;
    ;
  )
  (defun c:copTTL ()
    ;selection_set_for_fillter_blk_name
      (if  ;pre_select_ssget_or_post_select_ssget
        (=
          (setq ss_pre_filter_set_xx_ (ssget "i"
                                            (list
                                              (cons 0 "TEXT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "TEXT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;get_data_process_for_fillter_blk_name
      ;preloop_and_while
        (setq ss_pre_filter_set_xx_i 0)
        (setq new_list_for_sorting_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_textstr_ (vla-get-textstring ss_pre_filter_set_xx_obj_))
          (setq sum_ (list 
                       ss_pre_filter_set_xx_obj_ins_
                       ss_pre_filter_set_xx_obj_textstr_
                     )
          )
          (setq new_list_for_sorting_ (cons sum_ new_list_for_sorting_ ))
          
          
          (setq ss_pre_filter_set_xx_i (+ ss_pre_filter_set_xx_i 1))
        )
      ;
      ;TA:stanndard_lambda_sorting
        (setq new_list_for_sorting_sorted_ (vl-sort new_list_for_sorting_  ;bigest open indent list
                                                  (function 
                                                    (lambda (a b) 
                                                      (> (nth 1 (car a)) (nth 1 (car b)))
                                                    )
                                                  )
                              ) ;bigest close indent list
        )
      ;
      ;input_att_process
        (setq level_str_ename_ (car (entsel "specify Object")))
        (setq level_str_obj_ (vlax-ename->vla-object level_str_ename_))
        (LM:vl-setattributevalue level_str_obj_ "TITLE_1_val" (cadr (nth 0 new_list_for_sorting_sorted_)))
        (LM:vl-setattributevalue level_str_obj_ "TITLE_2_val" (cadr (nth 1 new_list_for_sorting_sorted_)))
        
        (LM:vl-setattributevalue level_str_obj_ "DRAWING_NO_val" (cadr (nth 2 new_list_for_sorting_sorted_)))
      ;
    ;
  )
  (defun c:copTx ()
    ;selection_set_for_fillter_blk_name
      (if  ;pre_select_ssget_or_post_select_ssget
        (=
          (setq ss_pre_filter_set_xx_ (ssget "i"
                                            (list
                                              (cons 0 "TEXT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "TEXT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;get_data_process_for_fillter_blk_name
      ;preloop_and_while
        (setq ss_pre_filter_set_xx_i 0)
        (setq new_list_for_sorting_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_ins_ (vlax-safearray->list (vlax-variant-value (vla-get-insertionpoint ss_pre_filter_set_xx_obj_))))
          (setq ss_pre_filter_set_xx_obj_textstr_ (vla-get-textstring ss_pre_filter_set_xx_obj_))
          (setq sum_ (list 
                       ss_pre_filter_set_xx_obj_ins_
                       ss_pre_filter_set_xx_obj_textstr_
                     )
          )
          (setq new_list_for_sorting_ (cons sum_ new_list_for_sorting_ ))
          
          
          (setq ss_pre_filter_set_xx_i (+ ss_pre_filter_set_xx_i 1))
        )
      ;
      ;TA:stanndard_lambda_sorting
        (setq new_list_for_sorting_sorted_ (vl-sort new_list_for_sorting_  ;bigest open indent list
                                                  (function 
                                                    (lambda (a b) 
                                                      (< (nth 0 (car a)) (nth 0 (car b)))
                                                    )
                                                  )
                              ) ;bigest close indent list
        )
      ;
      ;input_att_process
        (setq level_str_ename_ (car (entsel "specify Object")))
        (setq level_str_obj_ (vlax-ename->vla-object level_str_ename_))
        (LM:vl-setattributevalue level_str_obj_ "NUMBER" (cadr (nth 0 new_list_for_sorting_sorted_)))
        (LM:vl-setattributevalue level_str_obj_ "INDICATOR_NAME_1" (cadr (nth 1 new_list_for_sorting_sorted_)))
        
        ; (LM:vl-setattributevalue level_str_obj_ "DRAWING_NO_val" (cadr (nth 2 new_list_for_sorting_sorted_)))
      ;
    ;
    (command "erase" ss_pre_filter_set_xx_ename_ "")
  )
  (defun c:ASPG_estimate_sort_box_estsort ()
    (_startundo DOC)
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "A$Cd3cf6656"))
    (setq ss_pre_filter_set_xx_ (TA:standard_list_croodinate_sorting ss_pre_filter_set_xx_ "X"))
    (setq subfix_text_ ;Get-string by keep previous value
        (if
          (or
            (/= (setq subfix_text_val (getstring (strcat "\nSpecify Pattern name <" (if subfix_text_ subfix_text_ "") ">: ") ) ) "" )
          )
            (progn
              (setq subfix_text_ subfix_text_val)
              (setq subfix_text_keep_val_ subfix_text_val)
            )
          (setq subfix_text_val subfix_text_keep_val_)
        )
    )
    (setq start_number (cond ( (getint (strcat "\nspecify start_number \n<" (rtos (setq start_number (cond (start_number) (1.0) ) ) ) "> : " ) ) ) (start_number) ) )
    ;preloop_and_while
      (setq ss_pre_filter_set_xx_i 0)
      (while (< ss_pre_filter_set_xx_i (length ss_pre_filter_set_xx_))
        (setq ss_pre_filter_set_xx_ename_ (car (nth  ss_pre_filter_set_xx_i ss_pre_filter_set_xx_))) 
        
        (setq ss_pre_filter_set_xx_obj_ (vlax-ename->vla-object  ss_pre_filter_set_xx_ename_))

        (LM:vl-setattributevalue 
          ss_pre_filter_set_xx_obj_
          "LV_TYPE_VAL"
          (if 
            (= (wcmatch (LM:vl-getattributevalue ss_pre_filter_set_xx_obj_ "LV_TYPE_VAL") "*SINGLE*" ) T)
            (progn 
              (LM:vl-setattributevalue ss_pre_filter_set_xx_obj_ "LV_TYPE_VAL" "SINGLE BLANK" )
            )
            (LM:vl-setattributevalue ss_pre_filter_set_xx_obj_ "LV_TYPE_VAL" "DOUBLE BLANK" )
          )
        ) 
        (if (= ss_pre_filter_set_xx_i 0)
          (progn
            (setq start_number (- start_number 1))
          )
        )
        (LM:vl-setattributevalue ss_pre_filter_set_xx_obj_ "LV_TYPE_VAL" (strcat  subfix_text_ "_PL_" (TA:prefix_value_00 (+ start_number 1  ) ) "_" (LM:vl-getattributevalue ss_pre_filter_set_xx_obj_ "LV_TYPE_VAL") ) ) 
        (setq start_number (+ start_number 1))
        (setq ss_pre_filter_set_xx_i (+ ss_pre_filter_set_xx_i 1))
      )
      (setq start_number (+ start_number 1))
    ;
    (_endUndo DOC)
  )
  (defun c:ASPG_Estimate_panel_estpanel ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_ ss_pre_filter_set_xx_ "000_ASPG_TYP_FILES_LOUVER_WITH_C-C_FRAME_DYN_VIEW"))

    ;preloop_and_while
      (setq ss_pre_filter_set_xx_i 0)
      (setq total_frame_set 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (= (LM:getdynpropvalue ss_pre_filter_set_xx_obj_ "view") "7_dynamic_length_view")
          (progn
            (setq ss_pre_filter_set_xx_obj_width_ (LM:getdynpropvalue ss_pre_filter_set_xx_obj_ "frame_width"))
            (setq ss_pre_filter_set_xx_obj_height_ (LM:getdynpropvalue ss_pre_filter_set_xx_obj_ "frame_height"))
            (setq ss_pre_filter_set_xx_obj_panel_H_ (LM:setdynpropvalue ss_pre_filter_set_xx_obj_ "panel_height" (/ ss_pre_filter_set_xx_obj_height_ 2)))
            (setq total_frame_set (+ total_frame_set 1))
          )
        )
        (setq ss_pre_filter_set_xx_i (+ ss_pre_filter_set_xx_i 1))
      )
      (setq ss_pre_filter_set_xx_bol_ (TA:ss_vla-getboundingbox ss_pre_filter_set_xx_ ) )
      (setq ss_pre_filter_set_xx_bol_assembly_list (TA:assembly_coordinate_coner ss_pre_filter_set_xx_bol_))
    ;
    ;insert-process
      (TA:vla-insertblock 
        "A$Cd3cf6656"
        (nth 4 ss_pre_filter_set_xx_bol_assembly_list )
        1
        (deg-to-rad 90)
      )
      ;new_blk_entlast object
        (setq newent_ename (entlast))
        (setq newent_obj_ (vlax-ename->vla-object newent_ename))
        (setq lv-type_ (TA:choose_list_ (list "SINGLE BLANK" "DOUBLE BLANK" ) ))
        (if (= lv-type_ "DOUBLE BLANK") 
          (progn 
            (setq double_blank_set (getint "Enter DOUBLE BLANK set value: "))
            (setq double_blank_height-per-set_ (* (- ss_pre_filter_set_xx_obj_height_ 50) double_blank_set))
          )
        )
        
        
        (LM:vl-setattributevalue newent_obj_ "LV_TYPE_VAL" lv-type_)
        (LM:vl-setattributevalue newent_obj_ "LV_SIN-H_VAL" (strcat (rtos (* ss_pre_filter_set_xx_obj_height_ total_frame_set) 2 0) " mm. " ))
        (LM:vl-setattributevalue newent_obj_ "LV_DOU-H_VAL" (if (= lv-type_ "DOUBLE BLANK") (progn (strcat (rtos double_blank_height-per-set_ 2 0) " mm. " "(" (rtos double_blank_set 2 0) " set)" ) ) "-")  )
        (LM:vl-setattributevalue newent_obj_ "V-TRIM_VAL" (strcat (rtos (* ss_pre_filter_set_xx_obj_height_ total_frame_set) 2 0) " mm."))
        (LM:vl-setattributevalue newent_obj_ "FRAME_VAL" (strcat (rtos ss_pre_filter_set_xx_obj_width_ 2 2) "mm. x " (rtos ss_pre_filter_set_xx_obj_height_ 2 2) "mm." ) )
        (LM:vl-setattributevalue newent_obj_ "FRAME_SET" (strcat (rtos total_frame_set 2 0) " set") )
      ;
    ;
    (command "pselect"   "" )
  )
  (defun c:ASPG_Create_flashing_length_ASPG_FSAR1 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;user-input
      (setq length-increment (cond ( (getreal (strcat "\nspecify louver_width_<" (rtos (setq length-increment (cond (length-increment) (10) ) ) ) "> : " ) ) ) (length-increment) ) )
      (setq length-increment- (- length-increment) )
      (setq length-increment+ length-increment )
      (setq length-increment++ 0 )
      (setq length-increment-- 0 )
    ;
    ;while selection process
      (setq ERR_ nil)
      (setq ss_pre_filter_set_xx_i 0)
      (setq increment-time 1)
      (while ;for keep insertion point and dist. fix length one side
        (and
          (= (vl-catch-all-error-p ERR_) nil)
        )
        (setq ERR_
          (vl-catch-all-apply
            (function
              (lambda ()
                (setq symbol-input ;Get-string by keep previous value
                    (if
                      (or
                        (/= (setq symbol-inputval (getstring (strcat "\nSpecify + / - name <" (if symbol-input symbol-input "") ">: ") ) ) "" )
                      )
                        (progn
                          (setq symbol-input symbol-inputval)
                          (setq symbol-inputkeep_val_ symbol-inputval)
                        )
                      (setq symbol-inputval symbol-inputkeep_val_)
                    )
                )
                (setq ss_pre_filter_set_xx_obj (vlax-ename->vla-object (ssname  ss_pre_filter_set_xx_ ss_pre_filter_set_xx_i )))
                ;new_blk_entlast object
                  (vla-copy ss_pre_filter_set_xx_obj)
                  (setq new-copy_ename (entlast))
                  (setq new-copy_obj (vlax-ename->vla-object new-copy_ename))
                ;)
                (if (= symbol-input "+")
                  (progn
                    (TA:move_polar_insertionpoint new-copy_obj "Y" (setq length-increment++ (+ length-increment++ length-increment+)))
                  )
                  (TA:move_polar_insertionpoint new-copy_obj "Y" (setq length-increment-- (+ length-increment-- length-increment-)))
                )
                
                (setq increment-time (+ 1 increment-time ))
              )
            )
          )
        )
      )
    ;
  )
  (defun c:ASPG_SWFLASHING ()
    (setq flasing_ename_ (car (entsel "specify Object")))
    (setq flasing_obj_ (vlax-ename->vla-object flasing_ename_))
    (setq flasing_obj_dist-1_ (LM:getdynpropvalue flasing_obj_ "distance1"))
    (setq flasing_obj_dist-2_ (LM:getdynpropvalue flasing_obj_ "distance2"))
    (setq flasing_obj_dist-3_ (LM:getdynpropvalue flasing_obj_ "distance4"))
    
    ;while selection process
      (setq ERR_ nil)
      (while ;for keep insertion point and dist. fix length one side
        (and
          (= (vl-catch-all-error-p ERR_) nil)
        )
        (setq ERR_
          (vl-catch-all-apply
            (function
              (lambda ()
                (getstring "\nHit \nHit \nHit [ENTER] to switch flasing shape...")
                (LM:Setdynpropvalue flasing_obj_ "mid-point x" (- flasing_obj_dist-1_ flasing_obj_dist-2_) ) 
                (LM:Setdynpropvalue flasing_obj_ "edge-point x" (- 
                                                                  (- (- flasing_obj_dist-1_ flasing_obj_dist-2_) (- flasing_obj_dist-3_ 4)  )
                                                                  0
                                                                ) 
                ) 
                (getstring "\nHit \nHit \nHit [ENTER] to switch flasing shape...")
                (LM:Setdynpropvalue flasing_obj_ "mid-point x" flasing_obj_dist-1_ ) 
                (LM:Setdynpropvalue flasing_obj_ "edge-point x" flasing_obj_dist-1_ ) 
                (getstring "\nHit \nHit \nHit [ENTER] to switch flasing shape...")
                (LM:Setdynpropvalue flasing_obj_ "mid-point x" (+ flasing_obj_dist-1_ flasing_obj_dist-2_) ) 
                (LM:Setdynpropvalue flasing_obj_ "edge-point x" (+ 
                                                                  (+ (+ flasing_obj_dist-1_ flasing_obj_dist-2_) (- flasing_obj_dist-3_ 4)  )
                                                                  0
                                                                ) 
                ) 
              )
            )
          )
        )
      )
    ;

  )
  (defun c:ASPGScleancombine ()
    ;presetting_
    ; 
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        
        ; (setq ss_pre_filter_set_xx_obj_ (vlax-ename->vla-object  (car (entsel "specify Object"))))
        (setq ss_pre_filter_set_xx_obj_ (vlax-ename->vla-object  ss_pre_filter_set_xx_ename_))
        
        
        (if (and ;dimension obj
              (= (vla-get-objectname ss_pre_filter_set_xx_obj_ ) "AcDbRotatedDimension")
            )
          (progn
            (vla-put-layer ss_pre_filter_set_xx_obj_ "COMBINE_DIMS_DEF_SUB")
          )
        )
        (if (and ;dimension line layer 
              (= (vla-get-objectname ss_pre_filter_set_xx_obj_ ) "AcDbLine")
              (or 
                (= (vla-get-layer ss_pre_filter_set_xx_obj_ ) "DIMENSION")
                (= (vla-get-layer ss_pre_filter_set_xx_obj_ ) "MULLION")
              )
              (/= (vla-get-color ss_pre_filter_set_xx_obj_ ) 3)
            )
          (progn
            (vla-put-layer ss_pre_filter_set_xx_obj_ "COMBINE_DIMS_DEF_SUB")
          )
        )
        (if (and ;fastern
              (= (vla-get-objectname ss_pre_filter_set_xx_obj_ ) "AcDbBlockReference")
              (or 
                (= (LM:EffectiveName ss_pre_filter_set_xx_obj_ ) "PZG35")
                (= (LM:EffectiveName ss_pre_filter_set_xx_obj_ ) "BOLT PLAN VIEW")
              )
            )
          (progn
            (vla-put-layer ss_pre_filter_set_xx_obj_ "COMBINE_FASTERN_MAIN_COLOR_1")
          )
        )
        (if (and ;bracket aspg
              (= (vla-get-objectname ss_pre_filter_set_xx_obj_ ) "AcDbRegion")
              (= (vla-get-color ss_pre_filter_set_xx_obj_ ) 1)
            )
          (progn
            (vla-put-layer ss_pre_filter_set_xx_obj_ "COMBINE_BRAKCET_MAIN_COLOR_1")
          )
        )
        (if (and ;double-blade aspg
              (= (vla-get-objectname ss_pre_filter_set_xx_obj_ ) "AcDbPolyline")
              (= (vla-get-color ss_pre_filter_set_xx_obj_ ) 2)
            )
          (progn
            (vla-put-layer ss_pre_filter_set_xx_obj_ "COMBINE_DOUBLE-BLADE_MAIN_COLOR_2")
          )
        )
        (if (and ;single-blade aspg
              (= (vla-get-objectname ss_pre_filter_set_xx_obj_ ) "AcDbRegion")
              (= (vla-get-color ss_pre_filter_set_xx_obj_ ) 6)
            )
          (progn
            (vla-put-layer ss_pre_filter_set_xx_obj_ "COMBINE_SINGLE-BLADE_MAIN_COLOR_2")
          )
        )
        (if (and ;extr-framing aspg
              (or 
                (= (vla-get-objectname ss_pre_filter_set_xx_obj_ ) "AcDbLine")
                (= (vla-get-objectname ss_pre_filter_set_xx_obj_ ) "AcDbPolyline")
              )
              (= (vla-get-color ss_pre_filter_set_xx_obj_ ) 3)
            )
          (progn
            (vla-put-layer ss_pre_filter_set_xx_obj_ "COMBINE_SINGLE-BLADE_MAIN_COLOR_3")
          )
        )
        (if (and ;bracket-L-profile aspg
              (or 
                (= (vla-get-objectname ss_pre_filter_set_xx_obj_ ) "AcDbLine")
                (= (vla-get-objectname ss_pre_filter_set_xx_obj_ ) "AcDbPolyline")
              )
              (= (vla-get-color ss_pre_filter_set_xx_obj_ ) 0)
            )
          (progn
            (vla-put-layer ss_pre_filter_set_xx_obj_ "COMBINE_BRAKCET_MAIN_COLOR_1")
          )
        )
        (if (and ;basepoint 
              (= (vla-get-objectname ss_pre_filter_set_xx_obj_ ) "AcDbBlockReference")
              (= (LM:EffectiveName ss_pre_filter_set_xx_obj_ ) "COMBINE_ORI_BSpoint_")
            )
          (progn
            (setq ss_pre_filter_set_xx_obj_ins_ (vlax-safearray->list (vlax-variant-value (vla-get-insertionpoint ss_pre_filter_set_xx_obj_))))
            (setq ss_pre_filter_set_xx_obj_getboundingbox (vla-getboundingbox ss_pre_filter_set_xx_obj_ 'min_ 'max_)) 
            (setq ss_pre_filter_set_xx_min_ (vlax-safearray->list min_)) 
            (setq ss_pre_filter_set_xx_max_ (vlax-safearray->list max_)) 
            (setq ss_pre_filter_set_xx_obj_ggb (nth 4 (TA:assembly_coordinate_coner (list ss_pre_filter_set_xx_min_ ss_pre_filter_set_xx_max_ ) )))
            (command "point"  ss_pre_filter_set_xx_obj_ggb "" )
          )
        )
        (if (and ;MTEXT
              (or 
                (= (vla-get-objectname ss_pre_filter_set_xx_obj_ ) "AcDbMText")
                (= (vla-get-objectname ss_pre_filter_set_xx_obj_ ) "AcDbText")
              )
            )
          (progn
            (vla-put-layer ss_pre_filter_set_xx_obj_ "COMBINE_TEXT_DEF_SUB")
            (setq textstring_ (vla-get-textstring ss_pre_filter_set_xx_obj_ ))
          )
        )
        (vla-put-color ss_pre_filter_set_xx_obj_ 256)
        (setq ss_pre_filter_set_xx_i (+ ss_pre_filter_set_xx_i 1))
      )
  )
  (defun c:ASPGSCOMBINE ()
    ;presetting_
    ; 
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        
        ; (setq ss_pre_filter_set_xx_obj_ (vlax-ename->vla-object  (car (entsel "specify Object"))))
        (setq ss_pre_filter_set_xx_obj_ (vlax-ename->vla-object  ss_pre_filter_set_xx_ename_))
        
        
        (if (and ;dimension obj
              (= (vla-get-objectname ss_pre_filter_set_xx_obj_ ) "AcDbRotatedDimension")
            )
          (progn
            (vla-put-layer ss_pre_filter_set_xx_obj_ "COMBINE_DIMS_DEF_SUB")
          )
        )
        (if (and ;dimension line layer 
              (= (vla-get-objectname ss_pre_filter_set_xx_obj_ ) "AcDbLine")
              (or 
                (= (vla-get-layer ss_pre_filter_set_xx_obj_ ) "DIMENSION")
                (= (vla-get-layer ss_pre_filter_set_xx_obj_ ) "MULLION")
              )
              (/= (vla-get-color ss_pre_filter_set_xx_obj_ ) 3)
            )
          (progn
            (vla-put-layer ss_pre_filter_set_xx_obj_ "COMBINE_DIMS_DEF_SUB")
          )
        )
        (if (and ;fastern
              (= (vla-get-objectname ss_pre_filter_set_xx_obj_ ) "AcDbBlockReference")
              (or 
                (= (LM:EffectiveName ss_pre_filter_set_xx_obj_ ) "PZG35")
                (= (LM:EffectiveName ss_pre_filter_set_xx_obj_ ) "BOLT PLAN VIEW")
              )
            )
          (progn
            (vla-put-layer ss_pre_filter_set_xx_obj_ "COMBINE_FASTERN_MAIN_COLOR_1")
          )
        )
        (if (and ;bracket aspg
              (= (vla-get-objectname ss_pre_filter_set_xx_obj_ ) "AcDbRegion")
              (= (vla-get-color ss_pre_filter_set_xx_obj_ ) 1)
            )
          (progn
            (vla-put-layer ss_pre_filter_set_xx_obj_ "COMBINE_BRAKCET_MAIN_COLOR_1")
          )
        )
        (if (and ;double-blade aspg
              (= (vla-get-objectname ss_pre_filter_set_xx_obj_ ) "AcDbPolyline")
              (= (vla-get-color ss_pre_filter_set_xx_obj_ ) 2)
            )
          (progn
            (vla-put-layer ss_pre_filter_set_xx_obj_ "COMBINE_DOUBLE-BLADE_MAIN_COLOR_2")
          )
        )
        (if (and ;single-blade aspg
              (= (vla-get-objectname ss_pre_filter_set_xx_obj_ ) "AcDbRegion")
              (= (vla-get-color ss_pre_filter_set_xx_obj_ ) 6)
            )
          (progn
            (vla-put-layer ss_pre_filter_set_xx_obj_ "COMBINE_SINGLE-BLADE_MAIN_COLOR_2")
          )
        )
        (if (and ;extr-framing aspg
              (or 
                (= (vla-get-objectname ss_pre_filter_set_xx_obj_ ) "AcDbLine")
                (= (vla-get-objectname ss_pre_filter_set_xx_obj_ ) "AcDbPolyline")
              )
              (= (vla-get-color ss_pre_filter_set_xx_obj_ ) 3)
            )
          (progn
            (vla-put-layer ss_pre_filter_set_xx_obj_ "COMBINE_SINGLE-BLADE_MAIN_COLOR_3")
          )
        )
        (if (and ;bracket-L-profile aspg
              (or 
                (= (vla-get-objectname ss_pre_filter_set_xx_obj_ ) "AcDbLine")
                (= (vla-get-objectname ss_pre_filter_set_xx_obj_ ) "AcDbPolyline")
              )
              (= (vla-get-color ss_pre_filter_set_xx_obj_ ) 0)
            )
          (progn
            (vla-put-layer ss_pre_filter_set_xx_obj_ "COMBINE_BRAKCET_MAIN_COLOR_1")
          )
        )
        (if (and ;basepoint 
              (= (vla-get-objectname ss_pre_filter_set_xx_obj_ ) "AcDbBlockReference")
              (= (LM:EffectiveName ss_pre_filter_set_xx_obj_ ) "COMBINE_ORI_BSpoint_")
            )
          (progn
            (setq ss_pre_filter_set_xx_obj_ins_ (vlax-safearray->list (vlax-variant-value (vla-get-insertionpoint ss_pre_filter_set_xx_obj_))))
            (setq ss_pre_filter_set_xx_obj_getboundingbox (vla-getboundingbox ss_pre_filter_set_xx_obj_ 'min_ 'max_)) 
            (setq ss_pre_filter_set_xx_min_ (vlax-safearray->list min_)) 
            (setq ss_pre_filter_set_xx_max_ (vlax-safearray->list max_)) 
            (setq ss_pre_filter_set_xx_obj_ggb (nth 4 (TA:assembly_coordinate_coner (list ss_pre_filter_set_xx_min_ ss_pre_filter_set_xx_max_ ) )))
            (command "point"  ss_pre_filter_set_xx_obj_ggb "" )
          )
        )
        (if (and ;MTEXT
              (or 
                (= (vla-get-objectname ss_pre_filter_set_xx_obj_ ) "AcDbMText")
                (= (vla-get-objectname ss_pre_filter_set_xx_obj_ ) "AcDbText")
              )
            )
          (progn
            (vla-put-layer ss_pre_filter_set_xx_obj_ "COMBINE_TEXT_DEF_SUB")
            (setq textstring_ (vla-get-textstring ss_pre_filter_set_xx_obj_ ))
          )
        )
        (vla-put-color ss_pre_filter_set_xx_obj_ 256)
        (setq ss_pre_filter_set_xx_i (+ ss_pre_filter_set_xx_i 1))
      )
      (setq doc (vla-get-ActiveDocument (vlax-get-acad-object)))
      (setq blocks (vla-get-Blocks doc))
      (setvar "osmode" 0)
      (command "_block" (strcat "[ASPG-COMBINE]_" textstring_ "_[SINGLE-BLADE]") ss_pre_filter_set_xx_obj_ggb ss_pre_filter_set_xx_ "" )
      (TA:vla-insertblock 
        (strcat "[ASPG-COMBINE]_" textstring_ "_[SINGLE-BLADE]")
        ss_pre_filter_set_xx_obj_ggb
        1
        0
      )
      (setvar "osmode" 1215)
    ;
  )
  (defun c:ASPGDCOMBINE ()
    ;presetting_
    ; 
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        
        (setq ss_pre_filter_set_xx_obj_ (vlax-ename->vla-object  (car (entsel "specify Object"))))
        (setq ss_pre_filter_set_xx_obj_ (vlax-ename->vla-object  ss_pre_filter_set_xx_ename_))
        
        (if (and ;dimension obj
              (= (vla-get-objectname ss_pre_filter_set_xx_obj_ ) "AcDbRotatedDimension")
            )
          (progn
            (vla-put-layer ss_pre_filter_set_xx_obj_ "COMBINE_DIMS_DEF_SUB")
          )
        )
        (if (and ;dimension line layer 
              (= (vla-get-objectname ss_pre_filter_set_xx_obj_ ) "AcDbLine")
              (or 
                (= (vla-get-layer ss_pre_filter_set_xx_obj_ ) "DIMENSION")
                (= (vla-get-layer ss_pre_filter_set_xx_obj_ ) "MULLION")
              )
              (/= (vla-get-color ss_pre_filter_set_xx_obj_ ) 3)
            )
          (progn
            (vla-put-layer ss_pre_filter_set_xx_obj_ "COMBINE_DIMS_DEF_SUB")
          )
        )
        (if (and ;fastern
              (= (vla-get-objectname ss_pre_filter_set_xx_obj_ ) "AcDbBlockReference")
              (or 
                (= (LM:EffectiveName ss_pre_filter_set_xx_obj_ ) "PZG35")
                (= (LM:EffectiveName ss_pre_filter_set_xx_obj_ ) "BOLT PLAN VIEW")
              )
            )
          (progn
            (vla-put-layer ss_pre_filter_set_xx_obj_ "COMBINE_FASTERN_MAIN_COLOR_1")
          )
        )
        (if (and ;bracket aspg
              (= (vla-get-objectname ss_pre_filter_set_xx_obj_ ) "AcDbRegion")
              (= (vla-get-color ss_pre_filter_set_xx_obj_ ) 1)
            )
          (progn
            (vla-put-layer ss_pre_filter_set_xx_obj_ "COMBINE_BRAKCET_MAIN_COLOR_1")
          )
        )
        (if (and ;double-blade aspg
              (= (vla-get-objectname ss_pre_filter_set_xx_obj_ ) "AcDbPolyline")
              (= (vla-get-color ss_pre_filter_set_xx_obj_ ) 2)
            )
          (progn
            (vla-put-layer ss_pre_filter_set_xx_obj_ "COMBINE_DOUBLE-BLADE_MAIN_COLOR_2")
          )
        )e
        (if (and ;single-blade aspg
              (= (vla-get-objectname ss_pre_filter_set_xx_obj_ ) "AcDbRegion")
              (= (vla-get-color ss_pre_filter_set_xx_obj_ ) 6)
            )
          (progn
            (vla-put-layer ss_pre_filter_set_xx_obj_ "COMBINE_SINGLE-BLADE_MAIN_COLOR_2")
          )
        )
        (if (and ;extr-framing aspg
              (or 
                (= (vla-get-objectname ss_pre_filter_set_xx_obj_ ) "AcDbLine")
                (= (vla-get-objectname ss_pre_filter_set_xx_obj_ ) "AcDbPolyline")
              )
              (= (vla-get-color ss_pre_filter_set_xx_obj_ ) 3)
            )
          (progn
            (vla-put-layer ss_pre_filter_set_xx_obj_ "COMBINE_SINGLE-BLADE_MAIN_COLOR_3")
          )
        )
        (if (and ;bracket-L-profile aspg
              (or 
                (= (vla-get-objectname ss_pre_filter_set_xx_obj_ ) "AcDbLine")
                (= (vla-get-objectname ss_pre_filter_set_xx_obj_ ) "AcDbPolyline")
              )
              (= (vla-get-color ss_pre_filter_set_xx_obj_ ) 0)
            )
          (progn
            (vla-put-layer ss_pre_filter_set_xx_obj_ "COMBINE_BRAKCET_MAIN_COLOR_1")
          )
        )
        (if (and ;basepoint 
              (= (vla-get-objectname ss_pre_filter_set_xx_obj_ ) "AcDbBlockReference")
              (= (LM:EffectiveName ss_pre_filter_set_xx_obj_ ) "COMBINE_ORI_BSpoint_")
            )
          (progn
            (setq ss_pre_filter_set_xx_obj_ins_ (vlax-safearray->list (vlax-variant-value (vla-get-insertionpoint ss_pre_filter_set_xx_obj_))))
            (setq ss_pre_filter_set_xx_obj_getboundingbox (vla-getboundingbox ss_pre_filter_set_xx_obj_ 'min_ 'max_)) 
            (setq ss_pre_filter_set_xx_min_ (vlax-safearray->list min_)) 
            (setq ss_pre_filter_set_xx_max_ (vlax-safearray->list max_)) 
            (setq ss_pre_filter_set_xx_obj_ggb (nth 4 (TA:assembly_coordinate_coner (list ss_pre_filter_set_xx_min_ ss_pre_filter_set_xx_max_ ) )))
            (command "point"  ss_pre_filter_set_xx_obj_ggb "" )
          )
        )
        (if (and ;MTEXT
              (or 
                (= (vla-get-objectname ss_pre_filter_set_xx_obj_ ) "AcDbMText")
                (= (vla-get-objectname ss_pre_filter_set_xx_obj_ ) "AcDbText")
              )
            )
          (progn
            (vla-put-layer ss_pre_filter_set_xx_obj_ "COMBINE_TEXT_DEF_SUB")
            (setq textstring_ (vla-get-textstring ss_pre_filter_set_xx_obj_ ))
          )
        )
        (vla-put-color ss_pre_filter_set_xx_obj_ 256)
        (setq ss_pre_filter_set_xx_i (+ ss_pre_filter_set_xx_i 1))
      )
      (setq doc (vla-get-ActiveDocument (vlax-get-acad-object)))
      (setq blocks (vla-get-Blocks doc))
      (setvar "osmode" 0)
      (command "_block" (strcat "[ASPG-COMBINE]_" textstring_ "_[DOUBLE-BLADE]") ss_pre_filter_set_xx_obj_ggb ss_pre_filter_set_xx_ "" )
      (TA:vla-insertblock 
        (strcat "[ASPG-COMBINE]_" textstring_ "[DOUBLE-BLADE]")
        ss_pre_filter_set_xx_obj_ggb
        1
        0
      )
      (setvar "osmode" 1215)
    ;
  )
  (defun c:t33_temp_aspg_ ()
    ;selection_set_for_fillter_blk_name
      (if  ;pre_select_ssget_or_post_select_ssget
        (=
          (setq ss_pre_filter_set_xx_ (ssget "i"
                                            (list
                                              (cons 0 "lwpolyline") ;type of object
                                              (cons 8 "DIMENSION,COMBINE_SINGLE-BLADE_MAIN_COLOR_3")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "lwpolyline") ;type of object
                                              (cons 8 "DIMENSION,COMBINE_SINGLE-BLADE_MAIN_COLOR_3")   ;kind of layer
                                              ; (cons 2 "000-GRID_LINE_DYN")       ;kind of nameblock
                                              ; (cons 62 1)           ;kind of color call sign with color code index
                                            )
                                      )
          )
        )
        (sslength ss_pre_filter_set_xx_)
      )
    ;
    (setq sssset_ins_1_ (nth 0 (TA:assembly_coordinate_coner (TA:ss_vla-getboundingbox ss_pre_filter_set_xx_))))
    (command "pselect"  ss_pre_filter_set_xx_ "" )
    (TA:vla-insertblock
      "COMBINE_ORI_BSpoint_"
      sssset_ins_1_
      1
      0
    )
    (TA:vla-insertblock
      "INSERT-ATT"
      sssset_ins_1_
      1
      0
    )
    ;new_blk_entlast object
      (setq ss_ename (entlast))
      (setq ss_obj (vlax-ename->vla-object ss_ename))
      (vla-explode ss_obj)
    ;
  )
;




(defun c:test ()
  (setq line_ename_ (car (entsel "specify Object")))
  (setq line_obj_ (vlax-ename->vla-object line_ename_))
  (setq line_obj_start_end_pt_ (list
                                  (setq line_obj_startpt_ (vlax-safearray->list
                                                             (vlax-variant-value ( vla-get-startpoint line_obj_ ))
                                                           )
                                  )
                                  (setq line_obj_endpt_ (vlax-safearray->list
                                                            (vlax-variant-value ( vla-get-endpoint line_obj_ ))
                                                         )
                                  )
                                )
  )
  (setq div_soc (cond ( (getint (strcat "\nspecify get color \n<" (rtos (setq div_soc (cond (div_soc) (1.0) ) ) ) "> : " ) ) ) (div_soc) ) )
  ;preloop_and_while
    (if (= div_soc 2)
      (progn
        (setq div_all_ 2)
      )
    )
    (if (= div_soc 3)
      (progn
        (setq div_all_ 3)
      )
    )
    (if (= div_soc 4)
      (progn
        (setq div_all_ 4)
      )
    )
    (setq div_i 1)
    (setq list_divpt_ ())
    (setq list_divpt_ (cons line_obj_startpt_ list_divpt_))
    ; (setq list_divpt_ (cons line_obj_endpt_ list_divpt_))
    (setq 1st_trans ())
    (setq line_obj_all_length_ (vla-get-length line_obj_))
    (while (< div_i (+ div_all_ 1))
      (setq line_obj_div_ (/ line_obj_all_length_ div_all_  ))
      (setq summary_div_ (vlax-curve-getPointAtDist line_obj_ (* line_obj_div_ div_i)))
      (if (= (getvar "worlducs") 0)
        (progn
          (setq 1st_trans (list 
                            (car (trans summary_div_ 1 1) )
                            (cadr (trans summary_div_ 1 1) )
                            0
                          )
          )  
        )
        
      )
      (if (= (getvar "worlducs") 1)
        (progn
          (setq 1st_trans (list 
                            (car summary_div_ )
                            (cadr summary_div_ )
                            0
                          )
          )  
        )
        
      )
      (setq list_divpt_ (cons 1st_trans list_divpt_ ))
      (setq div_i (+ div_i 1))
    )
  ;
  ; (setq newblk_obj_efname_ (LM:Effectivename (vlax-ename->vla-object (car (entsel "specify block to insert")))))
  (foreach i list_divpt_ 
    (TA:vla-insertblock 
      "000 - CKST_DOWNLIGHT_SYMBOL"
      i
      1
      0
    )
  )
)

(defun c:ll1 ()
  
  (setq ss_bol_ (TA:ss_vla-getboundingbox (ssget "i")))
  (setq ss_bol_ (TA:assembly_coordinate_coner ss_bol_))
  (setq ss_bol_mid_ (nth 4 ss_bol_))
  (setq ss_bol_width_ (nth 5 ss_bol_))
  (setq ss_bol_height_ (nth 6 ss_bol_))
  (TA:vla-insertblock 
    "000_CSKT_FAMELINE_THAISHINRYO_LIGHTING__20260324-084403_LIGHT_EM-4"
    ss_bol_mid_
    1
    (deg-to-rad 0)
  )
  ;new_blk_entlast object
    (setq new-insert-col_ename (entlast))
    (setq new-insert-col_obj (vlax-ename->vla-object new-insert-col_ename))
    (LM:setdynpropvalue new-insert-col_obj "distance1" ss_bol_width_)
    (LM:setdynpropvalue new-insert-col_obj "distance2" ss_bol_height_)
  ;
  (command "pselect"   "" )
  
)
(defun c:tt1 ()
  
  (setq ss_bol_ (TA:ss_vla-getboundingbox (ssget "i")))
  (setq ss_bol_ (TA:assembly_coordinate_coner ss_bol_))
  (setq ss_bol_Lbot_ (nth 0 ss_bol_))
  (setq ss_bol_Rbot_ (nth 1 ss_bol_))
  (setq ss_bol_mid_ (nth 4 ss_bol_))
  (setq ss_bol_width_ (nth 5 ss_bol_))
  (setq ss_bol_height_ (nth 6 ss_bol_))
  (setq ss_bol_angle_ (angle ss_bol_Lbot_ ss_bol_Rbot_ ))
  (setq blocktype (cond 
                    ((getint 
                       (strcat "\nspecify get block name\n1 = 000_CKST_FAMELINE_RC-PRECAST_TOP_VIEW\n2 = 000_CKST_FAMELINE_GENERAL-WALL_TOP_VIEW\n3 = 000_CKST_FAMELINE_RC-COLUMN_TOP_VIEW \n<" 
                               (rtos (setq blocktype (cond (blocktype) (1.0))))
                               "> : "
                       )
                     )
                    )
                    (blocktype)
                  )
  )
  (cond
    (;_case_1
       (and
          (= blocktype 1)
       )
       (progn
         (setq insblk_  "000_CKST_FAMELINE_RC-PRECAST_TOP_VIEW")
         (princ "_case_1")
       )
    )
    (;_case_2
       (and
          (= blocktype 2)
       )
       (progn
         (setq insblk_    "000_CKST_FAMELINE_GENERAL-WALL_TOP_VIEW")
         (princ "_case_2")
       )
    )
    (;_case_3
       (and
          (= blocktype 3)
       )
       (progn
         (setq insblk_ "000_CKST_FAMELINE_RC-COLUMN_TOP_VIEW")
         (princ "_case_3")
       )
    )
  )
  (TA:vla-insertblock 
    insblk_
    ss_bol_mid_
    1
    ss_bol_angle_
  )
  ;new_blk_entlast object
    (setq new-insert-col_ename (entlast))
    (setq new-insert-col_obj (vlax-ename->vla-object new-insert-col_ename))
    (LM:setdynpropvalue new-insert-col_obj "distance2" ss_bol_height_)
    (LM:setdynpropvalue new-insert-col_obj "distance1" ss_bol_width_)
  ;
  (command "pselect"   "" )
  
)
(defun c:insert_alu-tray_tr1 ()
  (setq pt-1_ (getpoint "specify point 1"))
  (setq pt-2_ (getpoint pt-1_  "specify point 2"))
  (setq pt-1_ANG_ pt-1_)
  (setq pt-2_ANG_ pt-2_)
  (setq pt-length_ (LM:round (distance (list (car pt-1_) (cadr pt-1_) (caddr pt-1_)) (list (car pt-2_) (cadr pt-1_) (caddr pt-2_)) ) ) )
  (if (= (getvar "worlducs") 0)(progn (setq pt-1_ (trans pt-1_ 1 0))) pt-1_ )
  (TA:vla-insertblock 
    "010 - ALU_TRAY_PANEL_START-END_STANDARD-SHAPE_BOTTOM-VIEW"
    pt-1_
    1
    0
  )
  ;new_blk_entlast object
    (setq entlast_ename (entlast))
    (setq entlast_obj (vlax-ename->vla-object entlast_ename))
    (LM:setdynpropvalue entlast_obj "sub_length" pt-length_)
    (if (and 
          (> (rad-to-deg (angle pt-1_ANG_ pt-2_ANG_) ) 0)
          (< (rad-to-deg (angle pt-1_ANG_ pt-2_ANG_) ) 90)
        )
      (progn
        (LM:setdynpropvalue entlast_obj "flip state1" 1)
      )
    )
  ;
)
(defun c:insert_alu-tray_tr22 ()
  (setq pt-1_ (getpoint "specify point 1"))
  (setq pt-2_ (getpoint pt-1_  "specify point 2"))
  (setq pt-1_ANG_ pt-1_)
  (setq pt-2_ANG_ pt-2_)
  (setq pt-length_ (LM:round (distance (list (car pt-1_) (cadr pt-1_) (caddr pt-1_)) (list (car pt-1_) (cadr pt-2_) (caddr pt-2_)) ) ) )
  (if (= (getvar "worlducs") 0)(progn (setq pt-1_ (trans pt-1_ 1 0))) pt-1_ )
  (TA:vla-insertblock 
    "010 - ALU_TRAY_PANEL_START-END_STANDARD-SHAPE_BOTTOM-VIEW"
    pt-1_
    1
    (deg-to-rad 90)
  )
  ;new_blk_entlast object
    (setq entlast_ename (entlast))
    (setq entlast_obj (vlax-ename->vla-object entlast_ename))
    (LM:setdynpropvalue entlast_obj "sub_length" pt-length_)
    (if (and 
          (>= (rad-to-deg (angle pt-1_ANG_ pt-2_ANG_) ) 90)
          (<= (rad-to-deg (angle pt-1_ANG_ pt-2_ANG_) ) 180)
        )
      (progn
        (LM:setdynpropvalue entlast_obj "flip state1" 1)
      )
    )
  ;
)
(defun c:setazone ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
    (setq ss_pre_filter_set_xx_ (TA:EF_Filter_ss_set_V2_ 
                                  ss_pre_filter_set_xx_
                                  (list 
                                        "010 - ALU_TRAY_PANEL_FOR_AIR_GRILLE_STANDARD-SHAPE_BOTTOM-VIEW" 
                                        "010 - ALU_TRAY_PANEL_FOR_BLANK-RECESSED-LIGHT_STANDARD-SHAPE_BOTTOM-VIEW" 
                                        "010 - ALU_TRAY_PANEL_FOR_RECESSED-LIGHT_STANDARD-SHAPE_BOTTOM-VIEW" 
                                        "010 - ALU_TRAY_PANEL_FOR_RECESSED-LIGHT_START-END_VARIES-SHAPE_BOTTOM-VIEW" 
                                        "010 - ALU_TRAY_PANEL_START-END_STANDARD-SHAPE_BOTTOM-VIEW" 
                                        "010 - ALU_TRAY_PANEL_START-END_TZP-SHAPE_BOTTOM-VIEW"
                                  )
                                )
    )
    ;1
      (setq zoneprefix_ ;Get-string by keep previous value
          (if
            (or
              (/= (setq zoneprefix_val (getstring (strcat "\nSpecify zoneprefix_ name <" (if zoneprefix_ zoneprefix_ "") ">: ") ) ) "" )
            )
              (progn
                (setq zoneprefix_ zoneprefix_val)
                (setq zoneprefix_keep_val_ zoneprefix_val)
              )
            (setq zoneprefix_val zoneprefix_keep_val_)
          )
      )
      (setq zone_number_ (cond ( (getint (strcat "\nspecify get NUMBER\n<" (rtos (setq zone_number_ (cond (zone_number_) (1.0) ) ) ) "> : " ) ) ) (zone_number_) ) )
      
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (LM:vl-setattributevalue ss_pre_filter_set_xx_obj_ "panel_zone"  (strcat "ZONE" "_" zoneprefix_ "_" (TA:prefix_value_000 zone_number_)))
        (setq ss_pre_filter_set_xx_i (+ ss_pre_filter_set_xx_i 1))
      )
      (setq zone_number_ (+ zone_number_ 1))
    ;
  
  
)
(defun c:ttpre ()
  
  (setq ss_bol_ (TA:ss_vla-getboundingbox (ssget "i")))
  (setq ss_bol_ (TA:assembly_coordinate_coner ss_bol_))
  (setq ss_bol_Lbot_ (nth 0 ss_bol_))
  (setq ss_bol_Rbot_ (nth 1 ss_bol_))
  (setq ss_bol_mid_ (nth 4 ss_bol_))
  (setq ss_bol_width_ (nth 5 ss_bol_))
  (setq ss_bol_height_ (nth 6 ss_bol_))
  (setq ss_bol_angle_ (angle ss_bol_Lbot_ ss_bol_Rbot_ ))
  (TA:vla-insertblock 
    "000_CKST_FAMELINE_RC-PRECAST_TOP_VIEW"
    ss_bol_mid_
    1
    ss_bol_angle_
  )
  ;new_blk_entlast object
    (setq new-insert-col_ename (entlast))
    (setq new-insert-col_obj (vlax-ename->vla-object new-insert-col_ename))
    (LM:setdynpropvalue new-insert-col_obj "distance2" ss_bol_height_)
    (LM:setdynpropvalue new-insert-col_obj "distance1" ss_bol_width_)
  ;
  (command "pselect"   "" )
  
)

(defun c:tt2_ ()
  (defun TAS:editblock_fot_tt2 (blockname line_color layer_name)
    ; (setq blockname "PZG35")
    ; (setq line_color 256)
    ; (setq layer_name "008 - E&M_ACESSORIES_MAIN_COLOR_1")
    (setq target_ '())
    (setq blkdef (tblobjname "BLOCK" blockname))
    (setq ent (entnext blkdef))
    (while ent
      (setq ed (entget ent))
      (if (= (cdr (assoc 0 ed)) "HATCH")
        (progn
          (setq target_ (cons ent target_))
          ;main idea of code keep or delete don't affect with core code
            (setq target_obj_ (vlax-ename->vla-object (cdr (assoc -1 ed))))
            (vla-put-color target_obj_  line_color)
            (vla-put-layer target_obj_  layer_name)
            (vla-put-entitytransparency target_obj_ 80)
            ; (vla-put-EntityTransparency target_obj_ 80 )
          ;
        )
      )
      (setq ent (entnext ent))
    )
    (reverse target)
  )
  (setq ss_all_ (ssget "i"))
  ;preloop_and_while
    (setq ss_all_i 0)
    (while (< ss_all_i (sslength ss_all_))
      (setq ss_all_ename_ (ssname ss_all_ ss_all_i))
      (setq ss_all_obj_ (vlax-ename->vla-object  ss_all_ename_))
      (setq ss_all_obj_efname (LM:Effectivename ss_all_obj_))
      (TAS:editblock_fot_tt2 ss_all_obj_efname 256 "000 - 0_HIDE_OBJ_FRAMING_DEF_SUB")
      (setq ss_all_i (+ ss_all_i 1))
    )
  ;
  
  
  
)
  
(defun c:tt3 ()
  (setq ss_bol_ (TA:ss_vla-getboundingbox (setq sstemp_ (ssget "i"))))
  (setq ss_bol_ (TA:assembly_coordinate_coner ss_bol_))
  (setq ss_bol_second-pt_ (nth 1 ss_bol_))
  (setq ss_bol_mid_ (nth 4 ss_bol_))
  (setq ss_bol_width_ (nth 5 ss_bol_))
  (setq ss_bol_height_ (nth 6 ss_bol_))
  (TA:vla-insertblock 
    "000 - FAMELINE-CKST_AL.CELING_PANEL_300HK_@400mm_BOTTOM_VIEW_FOR_AS-02(L-varies_LOT)"
    ss_bol_second-pt_
    1
    0
  )
  ;new_blk_entlast object
    (setq new-insert-col_ename (entlast))
    (setq new-insert-col_obj (vlax-ename->vla-object new-insert-col_ename))
    (LM:setdynpropvalue new-insert-col_obj "flip state1" 1)
    (LM:setdynpropvalue new-insert-col_obj "ref_line" 0)
    (LM:setdynpropvalue new-insert-col_obj "panel_width" ss_bol_height_)
    (LM:setdynpropvalue new-insert-col_obj "panel_length" ss_bol_width_ )
  ;
  ;preloop_and_while
    (setq sstemp_i 0)
    (while (< sstemp_i (sslength sstemp_))
      (setq sstemp_ename_ (ssname sstemp_ sstemp_i))
      (setq sstemp_obj_ (vlax-ename->vla-object  sstemp_ename_))
      (vla-delete sstemp_obj_ )
      (setq sstemp_i (+ sstemp_i 1))
    )
  ;
  (command "pselect"   "" )
  
)
(defun c:tt4 ()
  
  (setq ss_bol_ (TA:ss_vla-getboundingbox (setq sstemp_ (ssget "i"))))
  (setq ss_bol_ (TA:assembly_coordinate_coner ss_bol_))
  (setq ss_bol_second-pt_ (nth 1 ss_bol_))
  (setq ss_bol_third-pt_ (nth 2 ss_bol_))
  (setq ss_bol_mid_ (nth 4 ss_bol_))
  (setq ss_bol_width_ (nth 5 ss_bol_))
  (setq ss_bol_height_ (nth 6 ss_bol_))
  (TA:vla-insertblock 
    "ACM_Linear Slot_Supply _1600x175x450_ - 1600x175_300Ø_-15127328-06 MULTIPURPOSE LEVEL CB CEILING PLAN"
    ss_bol_mid_
    1
    (deg-to-rad 180)
  )
  ;preloop_and_while
    (setq sstemp_i 0)
    (while (< sstemp_i (sslength sstemp_))
      (setq sstemp_ename_ (ssname sstemp_ sstemp_i))
      (setq sstemp_obj_ (vlax-ename->vla-object  sstemp_ename_))
      (vla-delete sstemp_obj_ )
      (setq sstemp_i (+ sstemp_i 1))
    )
  ;
  (command "pselect"   "" )
  
)

(defun c:400pol ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_ ss_pre_filter_set_xx_ "000 - FAMELINE-CKST_AL.CELING_PANEL_300HK_@400mm_BOTTOM_VIEW_FOR_AS-02(MULTI-varies_LOT)" ))
  (setq panel_matt_type1_ ;Get-string by keep previous value
      (if
        (or
          (/= (setq panel_matt_type1_val (getstring (strcat "\nSpecify MATT CODE <" (if panel_matt_type1_ panel_matt_type1_ "") ">: ") ) ) "" )
        )
          (progn
            (setq panel_matt_type1_ panel_matt_type1_val)
            (setq panel_matt_type1_keep_val_ panel_matt_type1_val)
          )
        (setq panel_matt_type1_val panel_matt_type1_keep_val_)
      )
  )
  (setq color_code_ ;Get-string by keep previous value
      (if
        (or
          (/= (setq color_code_val (getstring (strcat "\nSpecify color code <" (if color_code_ color_code_ "") ">: ") ) ) "" )
        )
          (progn
            (setq color_code_ color_code_val)
            (setq color_code_keep_val_ color_code_val)
          )
        (setq color_code_val color_code_keep_val_)
      )
  )
  (setq date_create_ ;Get-string by keep previous value
      (if
        (or
          (/= (setq date_create_val (getstring (strcat "\nSpecify date_create_  <" (if date_create_ date_create_ "") ">: ") ) ) "" )
        )
          (progn
            (setq date_create_ date_create_val)
            (setq date_create_keep_val_ date_create_val)
          )
        (setq date_create_val date_create_keep_val_)
      )
  )
  (setq date_create_ "varies_lot" )
  (setq panel_date-create date_create_  )
        
  (setq panel_station 
    (cond
      (;_case_1
        (and
            (= (wcmatch (getvar "dwgname"  ) "*PP17*") T)
        )
        (progn
          "PP17"
        )
      )
      (;_case_2
        (and
            (= (wcmatch (getvar "dwgname"  ) "*PP18*") T)
        )
        (progn
          "PP18"
          
        )
      )
      (;_case_3
        (and
            (= (wcmatch (getvar "dwgname"  ) "*PP19*") T)
        )
        (progn
          "PP19"
          
        )
      )
      (;_case_4
        (and 
          (= (wcmatch (getvar "dwgname"  ) "*PP20*") T )
        )
        (progn
          "PP20"
          
        )
      )
    )
  )
  (setq panel_level 
    (cond
      (;_case_2
        (and
            (= (wcmatch (getvar "dwgname"  ) "*PP17*") T)
            (= (wcmatch (getvar "dwgname"  ) "*AR-4150*") T)
        )
        (progn
          "concourse_level"
        )
      )
      (;_case_3
        (and
            (= (wcmatch (getvar "dwgname"  ) "*PP17*") T)
            (= (wcmatch (getvar "dwgname"  ) "*AR-4180*") T)
        )
        (progn
          "platform_level"
        )
      )
      (;_case_1
        (and
            (= (wcmatch (getvar "dwgname"  ) "*PP18*") T)
            (= (wcmatch (getvar "dwgname"  ) "*AR-4130*") T)
        )
        (progn
          "multi_purpose_level"
        )
      )
      (;_case_2
        (and
            (= (wcmatch (getvar "dwgname"  ) "*PP18*") T)
            (= (wcmatch (getvar "dwgname"  ) "*AR-4150*") T)
        )
        (progn
          "concourse_level"
        )
      )
      (;_case_2
        (and
            (= (wcmatch (getvar "dwgname"  ) "*PP18*") T)
            (= (wcmatch (getvar "dwgname"  ) "*AR-4160*") T)
        )
        (progn
          "upper_platform_level"
        )
      )
      (;_case_2
        (and
            (= (wcmatch (getvar "dwgname"  ) "*PP18*") T )
            (= (wcmatch (getvar "dwgname"  ) "*AR-4180*") T )
        )
        (progn
          "lower_platform_level"
        )
      )
      (;_case_1
        (and
            (= (wcmatch (getvar "dwgname"  ) "*PP19*") T)
            (= (wcmatch (getvar "dwgname"  ) "*AR-4130*") T)
        )
        (progn
          "multi_purpose_level"
        )
      )
      (;_case_2
        (and
            (= (wcmatch (getvar "dwgname"  ) "*PP19*") T)
            (= (wcmatch (getvar "dwgname"  ) "*AR-4150*") T)
        )
        (progn
          "concourse_level"
        )
      )
      (;_case_2
        (and
            (= (wcmatch (getvar "dwgname"  ) "*PP19*") T)
            (= (wcmatch (getvar "dwgname"  ) "*AR-4160*") T)
        )
        (progn
          "upper_platform_level"
        )
      )
      (;_case_2
        (and
            (= (wcmatch (getvar "dwgname"  ) "*PP19*") T)
            (= (wcmatch (getvar "dwgname"  ) "*AR-4180*") T)
        )
        (progn
          "lower_platform_level"
        )
      )
      (;_case_1
        (and
            (= (wcmatch (getvar "dwgname"  ) "*PP20*") T)
            (= (wcmatch (getvar "dwgname"  ) "*AR-4130*") T)
        )
        (progn
          "multi_purpose_level"
        )
      )
      (;_case_2
        (and
            (= (wcmatch (getvar "dwgname"  ) "*PP20*") T )
            (= (wcmatch (getvar "dwgname"  ) "*AR-4150*")  T)
        )
        (progn
          "concourse_level"
        )
      )
      (;_case_2
        (and
            (= (wcmatch (getvar "dwgname"  ) "*PP20*") T)
            (= (wcmatch (getvar "dwgname"  ) "*AR-4180*") T)
        )
        (progn
          "platform_level"
        )
      )
      
    )
  )
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq temp_ss_ (ssadd ))
      (setq temp_ss_ (ssadd ss_pre_filter_set_xx_ename_ temp_ss_))
      (setq panel_name "300HK")
      (setq panel_shape (cond ((or (= 1 1) ) (progn "trapezoids") ) ) )
      (setq ss_bol_ (TA:ss_vla-getboundingbox temp_ss_))
      (setq ss_bol_ (TA:assembly_coordinate_coner ss_bol_))
      (setq ss_bol_frist-pt_ (nth 0 ss_bol_))
      (setq ss_bol_second-pt_ (nth 1 ss_bol_))
      (setq ss_bol_third-pt_ (nth 2 ss_bol_))
      (setq ss_bol_mid_ (nth 4 ss_bol_))
      (setq ss_bol_width_ (nth 5 ss_bol_))
      (setq ss_bol_height_ (LM:round (nth 6 ss_bol_)))
      (TA:vla-insertblock 
        "000_CKST-FAMELINE_CEILING_CODE_PANEL"
        ss_bol_frist-pt_
        1
        0
      )
      ;new_blk_entlast object
        (setq new_box_ename (entlast))
        (setq new_box_obj (vlax-ename->vla-object new_box_ename))
        (vla-put-layer new_box_obj "C0x_300HK_CODE_TEXT")
        (vla-put-color new_box_obj 256)
        (LM:setdynpropvalue new_box_obj "distance1" 300)
        ; (TA:move_polar_insertionpoint new_box_obj "Y" panel_length)
        ;input_first_pc
          (setq ASB_textbox_ename_obj_ (vlax-ename->vla-object new_box_ename))
          (setq panel_code_name1(LM:vl-setattributevalue ASB_textbox_ename_obj_ "panel_code_name" ""))
          (LM:vl-setattributevalue ASB_textbox_ename_obj_ "panel_matt_type" panel_matt_type1_)
          (setq panel_name1 (LM:vl-setattributevalue ASB_textbox_ename_obj_ "panel_name" panel_name))
          (setq panel_no1 (LM:vl-getattributevalue ASB_textbox_ename_obj_ "panel_no1" ))
          (setq panel_length1 (LM:vl-setattributevalue ASB_textbox_ename_obj_ "panel_length" (LM:round ss_bol_width_)))
          (setq panel_width1 (LM:vl-setattributevalue ASB_textbox_ename_obj_ "panel_width" ss_bol_height_))
          (setq panel_color1 (LM:vl-setattributevalue ASB_textbox_ename_obj_ "panel_color" color_code_))
          (setq panel_shape1 (LM:vl-setattributevalue ASB_textbox_ename_obj_ "panel_shape" panel_shape))
          (setq panel_add-on1 (LM:vl-getattributevalue ASB_textbox_ename_obj_ "panel_add-on" ))
          (setq panel_date-create1(LM:vl-setattributevalue ASB_textbox_ename_obj_ "panel_date-create" panel_date-create))
          (setq panel_station1(LM:vl-setattributevalue ASB_textbox_ename_obj_ "panel_station" panel_station))
          (setq panel_level (LM:vl-setattributevalue ASB_textbox_ename_obj_ "panel_level" panel_level ))
          (setq panel_zone1 (LM:vl-getattributevalue ASB_textbox_ename_obj_ "panel_zone" ))
        ;
        ;generate_code_name
          (setq sumsum_ (strcat panel_station "-" (strcase (substr panel_level 1 4 )) "-"
                                panel_matt_type1_ "-" panel_name "-" "\n" 
                                (rtos panel_length1 2 0) "x" (rtos panel_width1 2 0) "mm." "-"
                                panel_color1 "-" "\n"
                                ""
                                (cond
                                  ( (= (wcmatch panel_shape "*standard*") T)
                                    (progn
                                      "STD-SHAPE"
                                    )
                                  )
                                  ( (= (wcmatch panel_shape "*trapezoids*") T)
                                    (progn
                                      "TPZ-SHAPE"
                                    )
                                  )
                                  ( (= (wcmatch panel_shape "varies") T)
                                    (progn
                                      "VA"
                                    )
                                  )
                                )
                                "-" panel_add-on1
                        ) 
          )
          (LM:vl-setattributevalue ASB_textbox_ename_obj_ "panel_code_name" sumsum_)
        ;
      (setq ss_pre_filter_set_xx_i (+ ss_pre_filter_set_xx_i 1))
    )
  ;
  

)












(defun c:sssssw ()
  (setq ang
    (cond
      (
        (getangle
          (strcat
            "\nSpecify angle <"
            (angtos (cond (ang) (0.0)) 0 2)
            "> : "
          )
        )
      )
      (ang)
    )
  )
  (defun c:ff1 (/ pt1 pt2 ang deg)
    (setq pt1 (getpoint "\nStart point: "))
    (setq pt2 (getpoint pt1 "\nSpecify direction: "))
    (setq ang (angle pt1 pt2))
    ; (setq deg (TA:ModifyRotation (rad-to-deg ang)  (rad-to-deg (angle '(0 0 0) (getvar "UCSXDIR")))))
    ; (princ (strcat "\nAngle = " (rtos deg 2 2) "°"))
    ; (princ)
    (command "line" pt1 pt2  )
    ;while selection process
      (setq ERR_ nil)
      (while ;for keep insertion point and dist. fix length one side
        (and
          (= (vl-catch-all-error-p ERR_) nil)
        )
        (setq ERR_
          (vl-catch-all-apply
            (function
              (lambda ()
                (setq pt3 (getpoint pt2 "\nSpecify direction: "))
              )
            )
          )
        )
        (command "line" pt2 pt3 )
        (setq pt2 pt3 )
        
        
      )
    ;
  )
  
  
)

(defun c:foo ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (setq ss_pre_filter_set_xx_ (TA:EF_Filter_ss_set_v2_ 
                                  ss_pre_filter_set_xx_
                                  (list 
                                    "000 - DYNAMIC_COMBINE+VIEW_ASSCESSORIES_FAMELINE_AL.EXTR._C-PROFILE_50x100mm._non-code_COMBINE_VIEW"
                                    "000 - DYNAMIC_COMBINE+VIEW_ASSCESSORIES_FAMELINE_AL.EXTR._REC-PROFILE_50x100mm._non-code_COMBINE_VIEW"
                                  )
                                )
    )
  ;
  ;preloop_and_while
    (setq ss_pre_filter_set_xx_i 0)
    (setq sum_ 0)
    (setq sum_length_ 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq sum_ (atoi (LM:vl-getattributevalue ss_pre_filter_set_xx_obj_ "EXTR.OVL-LENGTH_")))
      
      (setq sum_length_ (+ sum_length_ sum_))
      (setq ss_pre_filter_set_xx_i (+ ss_pre_filter_set_xx_i 1))
    )
  ;
  (setq sum_length_m (/ (float sum_length_) 1000))
  (princ (strcat "\nTotal length = " (rtos sum_length_m 2 2) "m."))
  (TA:copytext->clipboard (strcat "\nTotal length = " (rtos sum_length_m 2 2) "m."))

)
(defun c:foo1 ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (setq ss_pre_filter_set_xx_ (TA:EF_Filter_ss_set_v2_ 
                                  ss_pre_filter_set_xx_
                                  (list 
                                    "000 - DYNAMIC_COMBINE+VIEW_ASSCESSORIES_FAMELINE_AL.EXTR._C-PROFILE_50x100mm._non-code_COMBINE_VIEW"
                                    "000 - DYNAMIC_COMBINE+VIEW_ASSCESSORIES_FAMELINE_AL.EXTR._REC-PROFILE_50x100mm._non-code_COMBINE_VIEW"
                                  )
                                )
    )
  ;
  ;preloop_and_while
    (setq ss_pre_filter_set_xx_i 0)
    (setq new__SSS (ssadd))

    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (if (= (LM:vl-getattributevalue ss_pre_filter_set_xx_obj_ "EXTR.OVL-LENGTH_") "")
        (progn
          (setq new__SSS (ssadd ss_pre_filter_set_xx_ename_ new__SSS))
        )
      )
      
      (setq ss_pre_filter_set_xx_i (+ ss_pre_filter_set_xx_i 1))
    )
  ;
  (command "pselect"  new__SSS "" )

)




(defun c:suma1 ()
  (setq kkk_ename_ (car (entsel "specify Object")))
  (setq kkk_obj_ (vlax-ename->vla-object kkk_ename_))
  (+
  (LM:getdynpropvalue kkk_obj_ "FLASHING_1-1" )
  (LM:getdynpropvalue kkk_obj_ "FLASHING_1-2" )
  (LM:getdynpropvalue kkk_obj_ "FLASHING_2-1" )
  (LM:getdynpropvalue kkk_obj_ "FLASHING_2-2" )
  (LM:getdynpropvalue kkk_obj_ "FLASHING_2-3" )
  (LM:getdynpropvalue kkk_obj_ "FLASHING_2-4" )
  )
)



(defun c:temp_difi ()
  ;selection_set_for_fillter_blk_name
    (if  ;pre_select_ssget_or_post_select_ssget
      (=
        (setq ss_pre_filter_set_xx_name_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_name_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_name_i 0)
    (while (< ss_pre_filter_set_xx_name_i (sslength ss_pre_filter_set_xx_name_))
      (setq ss_pre_filter_set_xx_name_ename_ (ssname ss_pre_filter_set_xx_name_ ss_pre_filter_set_xx_name_i))
      (setq ss_pre_filter_set_xx_name_obj_ (vlax-ename->vla-object  ss_pre_filter_set_xx_name_ename_))
      (setq ss_pre_filter_set_xx_name_obj_ins_ (vlax-safearray->list (vlax-variant-value (vla-get-insertionpoint ss_pre_filter_set_xx_name_obj_))))
      (setq ss_pre_filter_set_xx_name_obj_getboundingbox (vla-getboundingbox ss_pre_filter_set_xx_name_obj_ 'min_ 'max_)) 
      (setq ss_pre_filter_set_xx_name_min_ (vlax-safearray->list min_)) 
      (setq ss_pre_filter_set_xx_name_max_ (vlax-safearray->list max_)) 
      (setq middle_pt_ (nth 4 (TA:assembly_coordinate_coner (list ss_pre_filter_set_xx_name_min_ ss_pre_filter_set_xx_name_max_))))
      
      (setq text_value_ (LM:vl-getattributevalue ss_pre_filter_set_xx_name_obj_ "EXTR.OVL-LENGTH_"))
      
      (create-text-vla (vlax-3d-point middle_pt_) text_value_ 250 0) 
      
      (setq ss_pre_filter_set_xx_name_i (+ ss_pre_filter_set_xx_name_i 1))
    )
  ;
)

(defun c:PPLINE_INSERTION_BRACKET_INSBKK2_ ()
  (setq ins_point_1 (getpoint "specify point 1"))
  (setq ins_point_2 (getpoint ins_point_1 "specify point 2"))
  (if (= (getvar "worlducs") 0)(progn (setq ins_point_1 (trans ins_point_1 1 0))) ins_point_1 )
  (if (= (getvar "worlducs") 0)(progn (setq ins_point_2 (trans ins_point_2 1 0))) ins_point_2 )
  (TA:vla-insertblock
    "000_ASPG_TYP_FILES__ASPG_BK_SET_2"
    ins_point_1
    1
    (angle ins_point_1 ins_point_2)
  )
  (LM:setdynpropvalue (vlax-ename->vla-object (entlast)) "view" "2_top_view_hex")
  (LM:setdynpropvalue (vlax-ename->vla-object (entlast)) "distance1" (distance ins_point_1 ins_point_2))
  (command "pselect" (entlast)  "" )
  (c:quick_mirror_qmi)
)
(defun c:PPLINE_INSERTION_BRACKET_INSBKK3_ ()
  (setq ins_point_1 (getpoint "specify point 1"))
  (setq ins_point_2 (getpoint ins_point_1 "specify point 2"))
  (if (= (getvar "worlducs") 0)(progn (setq ins_point_1 (trans ins_point_1 1 0))) ins_point_1 )
  (if (= (getvar "worlducs") 0)(progn (setq ins_point_2 (trans ins_point_2 1 0))) ins_point_2 )
  (TA:vla-insertblock
    "000_ASPG_TYP_FILES__ASPG_BK_SET_3"
    ins_point_1
    1
    (angle ins_point_1 ins_point_2)
  )
  (LM:setdynpropvalue (vlax-ename->vla-object (entlast)) "view" "2_top_view_hex")
  (LM:setdynpropvalue (vlax-ename->vla-object (entlast)) "distance1" (distance ins_point_1 ins_point_2))
  (command "pselect" (entlast)  "" )
  (c:quick_mirror_qmi)
)
(defun c:PPLINE_INSERTION_silicone_sealant_bkk4 ()
  (setq ins_point_1 (getpoint "specify point 1"))
  (setq ins_point_2 (getpoint ins_point_1 "specify point 2"))
  (if (= (getvar "worlducs") 0)(progn (setq ins_point_1 (trans ins_point_1 1 0))) ins_point_1 )
  (if (= (getvar "worlducs") 0)(progn (setq ins_point_2 (trans ins_point_2 1 0))) ins_point_2 )
  (TA:vla-insertblock
    "A$C5a699cc3"
    ins_point_1
    1
    (angle ins_point_1 ins_point_2)
  )
  
  (command "pselect" (entlast)  "" )
  (c:quick_mirror_qmi)
)


(defun c:textsumlength_tx1 ()
  ;selection_set_for_fillter_blk_name
    (if  ;pre_select_ssget_or_post_select_ssget
      (=
        (setq ss_pre_filter_set_xx_ (ssget "i"
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq total_air_ (getint "total air grille"))
  ;preloop_and_while
    (setq ss_pre_filter_set_xx_i 0)
    (setq sumtext_val 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_textstr_ (vla-get-textstring ss_pre_filter_set_xx_obj_ ))
      (setq sumtext_val (+ sumtext_val (/ (atoi ss_pre_filter_set_xx_obj_textstr_) 1000)))
      (setq ss_pre_filter_set_xx_i (+ ss_pre_filter_set_xx_i 1))
    )
    (create-text-vla (vlax-3d-point (getpoint "specify text for value")) (strcat "ความยาวทั้งหมด " (rtos (- sumtext_val (/ (* total_air_ 1600) 1000) ) 2 0 ) " มม. หักลบจำนวนความกว้างแอร์")  1500 0)
  ;/
)



(defun c:temp_drop_color_set ()
  (setq layer_list_for_drop_set (list 
                                  "008 - AIR_MASK_MAIN_COLOR_1"
                                  "008 - AIR_MASK_MAIN_COLOR_2"
                                  "008 - E&M_ACESSORIES_MAIN_COLOR_1"
                                  "008 - E&M_ACESSORIES_MAIN_COLOR_2"
                                  "008 - LIGHT_DN_MAIN_COLOR_1"
                                  "008 - LIGHT_DN_MAIN_COLOR_1"
                                  "008 - LIGHT_FLUORESCENT_MAIN_COLOR_1"
                                  "008 - LIGHT_FLUORESCENT_MAIN_COLOR_2"
                                  "009 - AHP_06_PANEL_MAIN_COLOR_1"
                                )
  )
  (foreach i layer_list_for_drop_set 
    (setq ERR_ (vl-catch-all-apply 
                 (function 
                   (lambda () 
                      (if (= (TA:if_found_layer_ i) T) 
                        (progn 
                          (command "vplayer" "c" 1 i "c" "")
                        )
                      )
                   )
                 )
               )
    )
  )
  
)


(defun c:po2bo ()
  ;selection_set_for_fillter_blk_name
    (if  ;pre_select_ssget_or_post_select_ssget
      (=
        (setq ss_pre_filter_set_xx_ (ssget "i"
                                          (list
                                            (cons 0 "point") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "point") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_ins (vlax-safearray->list (vlax-variant-value (vla-get-Coordinates ss_pre_filter_set_xx_obj_))))
      (command "boundary" ss_pre_filter_set_xx_obj_ins "")
      (setq ss_pre_filter_set_xx_i (+ ss_pre_filter_set_xx_i 1))
    )
  ;
)


(defun c:foo ()
  (setq ssss_ename_ (car (entsel "specify Object")))
  (setq ssss_obj_ (vlax-ename->vla-object ssss_ename_))
  
  (command "measure" ssss_ename_ "B" "a1" "Y" 5 )
)
(defun c:f2()
  (setq ssss_ename_ (car (entsel "specify Object")))
  (setq ssss_obj_ (vlax-ename->vla-object ssss_ename_))
  
  (command "measure" ssss_ename_ "B" "AAW" "Y" 20 )
)





(defun c:PL2STEEL ()
  (_startundo DOC)
  (defun TA:pl2steel (line_obj_)
    ; (setq line_ename_ (car (entsel "specify Object")))
    ; (setq line_obj_ (vlax-ename->vla-object line_ename_))
    (setq line_obj_start_end_pt_ (list
                                    (setq line_obj_startpt_ (vlax-safearray->list
                                                              (vlax-variant-value ( vla-get-startpoint line_obj_ ))
                                                            )
                                    )
                                    (setq line_obj_endpt_ (vlax-safearray->list
                                                              (vlax-variant-value ( vla-get-endpoint line_obj_ ))
                                                          )
                                    )
                                  )
    )
    (TA:vla-insertblock 
      "009 - AHP_06_FRAMING_TOP-VIEW" 
      (if (= (getvar "worlducs") 0)(progn (trans line_obj_startpt_ 1 1)) line_obj_startpt_ ) 
      1 
      (angle line_obj_startpt_ line_obj_endpt_) 
    )
    ;new_blk_entlast object
      (setq newsteel_ename (entlast))
      (setq newsteel_obj (vlax-ename->vla-object newsteel_ename))
      (LM:setdynpropvalue newsteel_obj "distance1" (fix (distance line_obj_startpt_ line_obj_endpt_)))
    ;
  )
  ;selection_set_for_fillter_blk_name
    (if  ;pre_select_ssget_or_post_select_ssget
      (=
        (setq ss_pre_filter_set_xx_ (ssget "i"
                                          (list
                                            (cons 0 "LINE") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "LINE") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (TA:pl2steel ss_pre_filter_set_xx_obj_)
      (setq ss_pre_filter_set_xx_i (+ ss_pre_filter_set_xx_i 1))
    )
  ;
  (_endundo DOC)
  (command "pselect" ss_pre_filter_set_xx_ "")
)

(defun c:special_explode_sexx ()
  (defun TA:point-to-BBOX (pt r / minpt maxpt)
    (setq minpt (list (- (car pt) r) (- (cadr pt) r) 0.0))
    (setq maxpt (list (+ (car pt) r) (+ (cadr pt) r) 0.0))
    (list minpt maxpt)
  )
  (_startundo DOC)
  (setq target_ename_ (car (entsel "specify Object")))
  (setq target_obj_ (vlax-ename->vla-object target_ename_))
  (setq target_obj_ins_ (vlax-safearray->list (vlax-variant-value (vla-get-insertionpoint target_obj_))))
  (setq target_obj_getboundingbox (vla-getboundingbox target_obj_ 'min_ 'max_)) 
  (setq target_min_ (vlax-safearray->list min_)) 
  (setq target_max_ (vlax-safearray->list max_)) 
  
  (setq target_obj_ins_reucs (if (= (getvar "worlducs") 0)(progn (trans target_obj_ins_ 0 1)) target_obj_ins_ ))
  (setq target_obj_ins_reucsmin (if (= (getvar "worlducs") 0)(progn (trans target_min_ 0 1)) target_min_ ))
  (setq target_obj_ins_reucsmax (if (= (getvar "worlducs") 0)(progn (trans target_max_ 0 1)) target_max_ ))
  (setq temp___ (ssget "_C" target_obj_ins_reucsmin target_obj_ins_reucsmax))
  
  ;get-dynamic data process
    (setq target_obj_dyn_data_ (list
                                  (LM:getdynpropvalue target_obj_ "distance1")
                                  (LM:getdynpropvalue target_obj_ "distance2")
                                )
    )
  ;
  
  (vla-explode target_obj_ )
  (vla-delete target_obj_ )
  ;while selection process
    (setq ERR_ nil)
    (setq sss nil)
    (while ;for keep insertion point and dist. fix length one side
      (and
        (= (vl-catch-all-error-p ERR_) nil)
        (= sss nil)
      )
      (setq ERR_
        (vl-catch-all-apply
          (function
            (lambda ()
              (setq ggg (getstring "sds"))
              (setq temp___ (ssget "_C" target_obj_ins_reucsmin target_obj_ins_reucsmax))
              (command "pselect" temp___  "" )
            )
          )
        )
      )
    )
  ;
  ;preloop_and_while
    (setq temp___i 0)
    (while (< temp___i (sslength temp___))
      (setq assembly_blk_list_ename_ (ssname  temp___ temp___i)) 
      (setq assembly_blk_list_obj_ (vlax-ename->vla-object assembly_blk_list_ename_)) 
      (if (and 
            (= (LM:effectivename assembly_blk_list_obj_) "009 - AHP_06_FRAMING_TOP-VIEW" )
            (= (vla-get-layer assembly_blk_list_obj_) "009 - AHP_06_FRAMING_MAIN_COLOR_1" )
          )
        (progn
          (LM:setdynpropvalue assembly_blk_list_obj_ "distance1" (nth 0 target_obj_dyn_data_))
        )
      )
  
      (setq temp___i (+ temp___i 1))
    )
  ;
)
(defun c:write_c06subfix ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (setq ss_pre_filter_set_xx_ (TA:EF_Filter_ss_set_ ss_pre_filter_set_xx_ "Title Block_Under Ground_C2 v3"))
    (setq ss_pre_filter_set_xx_ (TA:standard_list_croodinate_sorting ss_pre_filter_set_xx_ "X"))
  ;
  ;preloop_and_while
    (setq ss_pre_filter_set_xx_i 0)
    (while (< ss_pre_filter_set_xx_i (length ss_pre_filter_set_xx_))
      (setq ss_pre_filter_set_xx_ename_ (car (nth  ss_pre_filter_set_xx_i ss_pre_filter_set_xx_)))
      (setq ss_pre_filter_set_xx_obj_ (vlax-ename->vla-object  ss_pre_filter_set_xx_ename_))
      (setq xxx-1 (strcat (rtos (+ ss_pre_filter_set_xx_i 1) 2 0) "/" (rtos (length ss_pre_filter_set_xx_) 2 0) ))
      (LM:vl-setattributevalue ss_pre_filter_set_xx_obj_ "TITLE_3_val" (strcat "(C06 PART " xxx-1 ")" ))
      (setq ss_pre_filter_set_xx_i (+ ss_pre_filter_set_xx_i 1))
    )
  ;
  
)






(defun c:lvline_updateH_ ()
  (setq ssss_ename_ (car (entsel "specify Object")))
  (setq ssss_obj_ (vlax-ename->vla-object ssss_ename_))
  (setq ssss_obj_ins_ (vlax-safearray->list (vlax-variant-value (vla-get-insertionpoint ssss_obj_))))
  (setq ssss_obj_ins_ucs (if (= (getvar "worlducs") 0)(progn (trans ssss_obj_ins_ 0 1)) ssss_obj_ins_ ))
  (LM:vl-setattributevalue ssss_obj_ "LV_NAME_3" (strcat "EL +" (rtos (/ (cadr ssss_obj_ins_ucs) 1000) 2 3 ) ""))
  ; (LM:vl-setattributevalue ssss_obj_ "LV_NAME_3" (strcat "FFL +" (rtos (/ (cadr ssss_obj_ins_ucs) 1000) 2 3 ) " m."))
)



(defun c:prefix-subfix_all-block_ ()
  (setq block_all-list_ (TA:get_name_block_in_drawing_to_list_v2))
  (setq prefix "")
  (setq subfix "_SUB" )
  ;preloop_and_while
    (setq block_all-list_i 0)
    (while (< block_all-list_i (length block_all-list_))
      (setq block_all-list_name_ (car (nth  block_all-list_i block_all-list_)))
      (if (and 
            ; (/= (cadr (nth  block_all-list_i block_all-list_)) 0 )
            (= 1 1)            
          )
        (progn
          (command "rename" "b" block_all-list_name_ (strcat prefix block_all-list_name_ subfix))
        )
      )
      (setq block_all-list_i (+ block_all-list_i 1))
    )
  ;
)




(defun c:tempsc ()
  ;selection_set_for_fillter_blk_name
    (if  ;pre_select_ssget_or_post_select_ssget
      (=
        (setq ss_pre_filter_set_xx_ (ssget "i"
                                          (list
                                            (cons 0 "INSERT,mtext") ;type of object
                                            (cons 8 "A-ANNO-IDEN")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT,mtext") ;type of object
                                            (cons 8 "A-ANNO-IDEN")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (if (= (vla-get-objectname ss_pre_filter_set_xx_obj_ ) "AcDbBlockReference")
        
        (progn
          (setq ssbol_vertex_list_ (TA:assembly_coordinate_coner (TA:ss_vla-getboundingbox ss_pre_filter_set_xx_)))
          (setq ss_pre_filter_set_xx_obj_ins_ (vlax-safearray->list (vlax-variant-value (vla-get-insertionpoint ss_pre_filter_set_xx_obj_))))
          ; (if (= (getvar "worlducs") 0)(progn (trans pttarget_torr 1 0)) pttarget_torr )
        )
      )
      (setq ss_pre_filter_set_xx_i (+ ss_pre_filter_set_xx_i 1))
    )
    
  ;
  (command "pselect"   "" )
  (command "scale" ss_pre_filter_set_xx_ "" (nth 4 ssbol_vertex_list_) 0.5 )
)
  

;master cutting length
  (defun c:EXTR-from-Pline () 
    ;selection_set_for_fillter_blk_name
      (if  ;pre_select_ssget_or_post_select_ssget
        (= 
          (setq ss_pre_filter_set_xx_ (ssget "i" 
                                            (list 
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "lwpolyline") ;type of object
                                          ; (cons 8 "000 - GRID")   ;kind of layer
                                          ; (cons 2 "000-GRID_LINE_DYN")       ;kind of nameblock
                                          ; (cons 62 1)           ;kind of color call sign with color code index
                                        )
                                      )
          )
        )
        (sslength ss_pre_filter_set_xx_)
      )
    ;
    ;preloop_and_while
    (setq ss_pre_filter_set_xx_i 0)
    (while (< ss_pre_filter_set_xx_i (sslength ss_pre_filter_set_xx_)) 
      (setq ss_pre_filter_set_xx_ename_ (ssname ss_pre_filter_set_xx_ ss_pre_filter_set_xx_i ) )
      (setq ss_pre_filter_set_xx_obj_ (vlax-ename->vla-object ss_pre_filter_set_xx_ename_))
      (setq ss_pre_filter_set_xx_obj_getboundingbox (vla-getboundingbox ss_pre_filter_set_xx_obj_ 'min_ 'max_ ) )
      (setq ss_pre_filter_set_xx_min_ (vlax-safearray->list min_))
      (setq ss_pre_filter_set_xx_max_ (vlax-safearray->list max_))
      (setq ss_pre_filter_set_xx_obj_xylist_ (TA:assembly_coordinate_coner (list ss_pre_filter_set_xx_min_ ss_pre_filter_set_xx_max_) ) )

      (TA:vla-insertblock 
        "DANAI EXTR H VAL" 
        (TA:midpoint (nth 0 ss_pre_filter_set_xx_obj_xylist_) (nth 1 ss_pre_filter_set_xx_obj_xylist_)) 
        1 
        0
      )
      ;new_blk_entlast object
      (setq sssss_ename (entlast))
      (setq sssss_obj (vlax-ename->vla-object sssss_ename))
      (LM:setdynpropvalue 
        sssss_obj
        "H"
        (distance  (nth 0 ss_pre_filter_set_xx_obj_xylist_) (nth 3 ss_pre_filter_set_xx_obj_xylist_))
      )
      (vla-delete ss_pre_filter_set_xx_obj_)
      ;


      (setq ss_pre_filter_set_xx_i (+ ss_pre_filter_set_xx_i 1))
    )
    ;
  )
  (defun c:EXTR-tag-sort-attribute ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:standard_list_croodinate_sorting ss_pre_filter_set_xx_ "X" ) )
    ;
    (setq danai-att-val_ ;Get-string by keep previous value
        (if
          (or
            (/= (setq danai-att-val_val (getstring (strcat "\nSpecify prefix name 1 <" (if danai-att-val_ danai-att-val_ "") ">: ") ) ) "" )
          )
            (progn
              (setq danai-att-val_ danai-att-val_val)
              (setq danai-att-val_keep_val_ danai-att-val_val)
            )
          (setq danai-att-val_val danai-att-val_keep_val_)
        )
    )
    (setq danai-att-val_LV2 ;Get-string by keep previous value
        (if
          (or
            (/= (setq danai-att-val_LV2val (getstring (strcat "\nSpecify prefix name 2 " (strcat danai-att-val_ )  "<" (if danai-att-val_LV2 danai-att-val_LV2 "") ">: ") ) ) "" )
          )
            (progn
              (setq danai-att-val_LV2 danai-att-val_LV2val)
              (setq danai-att-val_LV2keep_val_ danai-att-val_LV2val)
            )
          (setq danai-att-val_LV2val danai-att-val_LV2keep_val_)
        )
    )
    ;prloop_and_while
      (setq ss_pre_filter_set_xx_i 0)
      (while (< ss_pre_filter_set_xx_i (length ss_pre_filter_set_xx_))
        (setq ss_pre_filter_set_xx_ename_ (car (nth  ss_pre_filter_set_xx_i ss_pre_filter_set_xx_)))
        (setq ss_pre_filter_set_xx_obj_ (vlax-ename->vla-object  ss_pre_filter_set_xx_ename_))
        (setq ss_pre_filter_set_xx_obj_att-val (LM:vl-setattributevalue ss_pre_filter_set_xx_obj_ "DANAI_EXTR_NAME" (strcat danai-att-val_val "-" danai-att-val_LV2 "-" (TA:prefix_value_000 (+ ss_pre_filter_set_xx_i 1)))) )
        (setq ss_pre_filter_set_xx_i (+ ss_pre_filter_set_xx_i 1))
      )
    ;
  )
  (defun c:EXTR-indicate-color ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:standard_list_croodinate_sorting ss_pre_filter_set_xx_ "X" ) )
    ;
    ;prloop_and_while
      (setq ss_pre_filter_set_xx_i 0)
      (while (< ss_pre_filter_set_xx_i (length ss_pre_filter_set_xx_))
        (setq ss_pre_filter_set_xx_ename_ (car (nth  ss_pre_filter_set_xx_i ss_pre_filter_set_xx_)))
        (setq ss_pre_filter_set_xx_obj_ (vlax-ename->vla-object  ss_pre_filter_set_xx_ename_))
        (setq ss_pre_filter_set_xx_obj_att-val (LM:vl-setattributevalue 
                                                 ss_pre_filter_set_xx_obj_
                                                 "DANAI_EXTR_COLOR_FOR_SET"
                                                 (if 
                                                   (= (vla-get-color ss_pre_filter_set_xx_obj_) 0 )
                                                   (progn 
                                                     "000"
                                                   )
                                                   (TA:prefix_value_000 (vla-get-color ss_pre_filter_set_xx_obj_) )
                                                 )
                                               )
        )
        (setq ss_pre_filter_set_xx_i (+ ss_pre_filter_set_xx_i 1))
      )
    ;
  )
  (defun c:EXTR-sum_selection-length ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (setq sum 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq sum (+ sum (LM:getdynpropvalue ss_pre_filter_set_xx_obj_ "H")))
        (setq ss_pre_filter_set_xx_i (+ ss_pre_filter_set_xx_i 1))
      )
    ;\
    (alert (rtos sum 2 2))
  )
  (defun c:EXTR-pairing-length ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      ; (setq ss_pre_filter_set_xx_ (TA:EF_Filter_ss_set_V2_ ss_pre_filter_set_xx_ (list "DANAI EXTR H VAL")))
    ;
    ;preloop_and_while
      (setq color_i 0)
      (setq ss_pre_filter_set_xx_i 0)
      (setq ss_pre_filter_set_xx_ii 0)
      (setq ss_pre_filter_set_xx_list-ename_ ())
      (while (< ss_pre_filter_set_xx_i (sslength ss_pre_filter_set_xx_))
        (setq color_i (+ color_i 1))
        (setq ss_pre_filter_set_xx_ename_ (ssname ss_pre_filter_set_xx_ ss_pre_filter_set_xx_i))
        (setq ss_pre_filter_set_xx_list-ename_ (cons ss_pre_filter_set_xx_ename_  ss_pre_filter_set_xx_list-ename_ ))
        (setq ss_pre_filter_set_xx_obj_ (vlax-ename->vla-object  ss_pre_filter_set_xx_ename_))
        (setq ss_pre_filter_set_xx_obj_cur-L (LM:getdynpropvalue ss_pre_filter_set_xx_obj_ "distance1"))
        ; (vla-put-color ss_pre_filter_set_xx_obj_ color_i)
        ;preloop_and_while
          (setq ss_pre_filter_set_xx_ii 0)
          (while (< ss_pre_filter_set_xx_ii (sslength ss_pre_filter_set_xx_))
            (if (and 
                  (/= (vl-princ-to-string (setq target-match (ssname ss_pre_filter_set_xx_ ss_pre_filter_set_xx_ii))) (vl-princ-to-string ss_pre_filter_set_xx_ename_))
                  (/= (vl-princ-to-string (setq target-match_obj_ (vlax-ename->vla-object  target-match))) (vl-princ-to-string ss_pre_filter_set_xx_obj_))
                  (= (vla-get-color target-match_obj_) 0)
                  (= (vla-get-color target-match_obj_) 0)
                  (= (member target-match ss_pre_filter_set_xx_list-ename_) nil)
                  (or 
                    (< (+ (LM:getdynpropvalue target-match_obj_ "distance1") ss_pre_filter_set_xx_obj_cur-L) 6000)
                  )
                )
              (progn
                (setq ss_pre_filter_set_xx_obj_cur-L (+ (LM:getdynpropvalue target-match_obj_ "distance1") ss_pre_filter_set_xx_obj_cur-L))
                (setq ss_pre_filter_set_xx_list-ename_ (cons target-match  ss_pre_filter_set_xx_list-ename_ ))
                (vla-put-color target-match_obj_ color_i)
                (vla-put-color ss_pre_filter_set_xx_obj_ color_i)
                T
              )
            )
            ; (setq color_i (+ color_i 1))
            (setq ss_pre_filter_set_xx_ii (+ ss_pre_filter_set_xx_ii 1))
          )
        ;
        ;preloop_and_while
          (setq ss_pre_filter_set_xx_list-ename_i 0)
          (while (< ss_pre_filter_set_xx_list-ename_i (length ss_pre_filter_set_xx_list-ename_))
            (setq ss_pre_filter_set_xx_list-ename_ename_ (nth  ss_pre_filter_set_xx_list-ename_i ss_pre_filter_set_xx_list-ename_))
            (ssdel ss_pre_filter_set_xx_list-ename_ename_ ss_pre_filter_set_xx_)
            (sslength ss_pre_filter_set_xx_)
            (setq ss_pre_filter_set_xx_i 0)
            (setq ss_pre_filter_set_xx_list-ename_i (+ ss_pre_filter_set_xx_list-ename_i 1))
          )
        ;
        (setq ss_pre_filter_set_xx_i (+ ss_pre_filter_set_xx_i 1))
      )
    ;
  )
  (defun c:EXTR-runing_color_tag ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:standard_list_croodinate_sorting ss_pre_filter_set_xx_ (strcase(getstring "X or Y")) ) )
    ;
    
    (setq run_no (cond ( (getint (strcat "\nspecify get NUMBER\n<" (rtos (setq run_no (cond (run_no) (1.0) ) ) ) "> : " ) ) ) (run_no) ) )
    ;prloop_and_while
      (setq ss_pre_filter_set_xx_i 0)
      (while (< ss_pre_filter_set_xx_i (length ss_pre_filter_set_xx_))
        (setq ss_pre_filter_set_xx_ename_ (car (nth  ss_pre_filter_set_xx_i ss_pre_filter_set_xx_)))
        (setq ss_pre_filter_set_xx_obj_ (vlax-ename->vla-object  ss_pre_filter_set_xx_ename_))
        (if (and 
              (= 1 1)
              ( = (LM:vl-getattributevalue ss_pre_filter_set_xx_obj_ "DANAI_EXTR_COLOR_FOR_SET") "000")
            )
          (progn
            
            (LM:vl-setattributevalue ss_pre_filter_set_xx_obj_ "DANAI_EXTR_COLOR_FOR_SET" (TA:prefix_value_000 run_no))
            (setq run_no (+ run_no 1))
          )
        )
        (setq ss_pre_filter_set_xx_i (+ ss_pre_filter_set_xx_i 1))
      )
    ;
  )
  (defun c:EXTR-runingC4_color_tag ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:standard_list_croodinate_sorting ss_pre_filter_set_xx_ (strcase(getstring "X or Y")) ) )
    ;
    
    (setq run_no (cond ( (getint (strcat "\nspecify get NUMBER\n<" (rtos (setq run_no (cond (run_no) (1.0) ) ) ) "> : " ) ) ) (run_no) ) )
    ;prloop_and_while
      (setq ss_pre_filter_set_xx_i 0)
      (while (< ss_pre_filter_set_xx_i (length ss_pre_filter_set_xx_))
        (setq ss_pre_filter_set_xx_ename_ (car (nth  ss_pre_filter_set_xx_i ss_pre_filter_set_xx_)))
        (setq ss_pre_filter_set_xx_obj_ (vlax-ename->vla-object  ss_pre_filter_set_xx_ename_))
        (if (and 
              (= 1 1)
              ( = (LM:vl-getattributevalue ss_pre_filter_set_xx_obj_ "DANAI_EXTR_COLOR_FOR_SET") "0000")
            )
          (progn
            
            (LM:vl-setattributevalue ss_pre_filter_set_xx_obj_ "DANAI_EXTR_COLOR_FOR_SET" (TA:prefix_value_000 run_no))
            (setq run_no (+ run_no 1))
          )
        )
        (setq ss_pre_filter_set_xx_i (+ ss_pre_filter_set_xx_i 1))
      )
    ;
  )
  (defun c:EXTR-lineup ()
    ;user-input-
      ;selection_set_for_fillter_blk_name
        (if  ;pre_select_ssget_or_post_select_ssget
          (=
            (setq ss_pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq ss_pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength ss_pre_filter_set_xx_)
        )
      ;
      ;preloop_and_while
        (setq ss_pre_filter_set_xx_i 0)
        (setq extr-tag-len_ ())
        (setq extr-tag-ename_ ())
        (while (< ss_pre_filter_set_xx_i (sslength ss_pre_filter_set_xx_))
          (setq ss_pre_filter_set_xx_ename_ (ssname ss_pre_filter_set_xx_ ss_pre_filter_set_xx_i))
          (setq ss_pre_filter_set_xx_obj_ (vlax-ename->vla-object  ss_pre_filter_set_xx_ename_))
          (setq ss_pre_filter_set_xx_obj_length (LM:getdynpropvalue ss_pre_filter_set_xx_obj_ "distance1"))
          (setq color_tag (LM:vl-getattributevalue ss_pre_filter_set_xx_obj_ "DANAI_EXTR_COLOR_FOR_SET" ))
          (setq tempforsum (list 
                                color_tag
                                ss_pre_filter_set_xx_obj_length
                              )
          )
          (setq tempforename (list 
                                color_tag
                                ss_pre_filter_set_xx_ename_
                                ss_pre_filter_set_xx_obj_length
                              )
          )
          (setq extr-tag-ename_ (cons tempforename extr-tag-ename_ ))
          (setq extr-tag-len_ (cons tempforsum extr-tag-len_ ))
          (setq ss_pre_filter_set_xx_i (+ ss_pre_filter_set_xx_i 1))
        )
      ;\
    ;
    ;result text summary
      (setq result '())

      (foreach item extr-tag-len_
        (setq key (car item))
        (setq val (cadr item))

        (if (assoc key result)
          (setq result
            (subst
              (cons key (+ val (cdr (assoc key result))))
              (assoc key result)
              result
            )
          )
          (setq result (cons (cons key val) result))
        )
      )
      (setq txt "")
      (foreach r (vl-sort result '(lambda (a b) (< (car a) (car b))))
        (setq txt
          (strcat txt
            (car r)
            " = "
            (rtos (cdr r) 2 3)
            "\n"
          )
        )
      )
      (TA:copytext->clipboard txt )
    ;
    ;summary ename for set
      (setq result_ename-lst_ '())
      (foreach pair extr-tag-ename_
        (setq key (car pair))
        (setq ent (cadr pair))

        (if (assoc key result_ename-lst_)
          (setq result_ename-lst_
            (subst
              (cons key (cons ent (cdr (assoc key result_ename-lst_))))
              (assoc key result_ename-lst_)
              result_ename-lst_
            )
          )
          (setq result_ename-lst_ (cons (cons key (list ent)) result_ename-lst_))
        )
      )

      ;; print result_ename-lst_
      (foreach r result_ename-lst_
        (princ (strcat "\nTAG " (car r) " = " (itoa (length (cdr r)))))
      )

      (princ)
    ;
    ;TA:stanndard_lambda_sorting
      (setq result_ename-lst_sorted_ (vl-sort result_ename-lst_  ;bigest open indent list
                                              (function 
                                                (lambda (a b) 
                                                  (< 
                                                    (atoi (car a)) 
                                                    (atoi (car b))
                                                  )
                                                )
                                              )
                                     ) ;bigest close indent list
      )
    ;
    (setq new_pt_ (getpoint "xxxx"))
    ;preloop_and_while
      (setq result_ename-lst_i 0)
      (while (< result_ename-lst_i (length result_ename-lst_))
        (setq H-val 0)
        (setq result_ename-lst_main-set_ (nth  result_ename-lst_i result_ename-lst_))
        ;preloop_and_while for 
          (setq result_ename-lst_main-set_i 1)
          (while (< result_ename-lst_main-set_i (length result_ename-lst_main-set_))
            (setq temp-ss- (TA:list-to-ss result_ename-lst_main-set_ result_ename-lst_main-set_))
            (setq result_ename-lst_main-set_ename_ (nth  result_ename-lst_main-set_i result_ename-lst_main-set_)) 
            
            (setq result_ename-lst_main-set_obj_ (vlax-ename->vla-object  result_ename-lst_main-set_ename_))
            (setq result_ename-lst_main-set_obj_ins_ (vlax-safearray->list (vlax-variant-value (vla-get-insertionpoint result_ename-lst_main-set_obj_))))
            
            (vla-put-insertionpoint
              result_ename-lst_main-set_obj_
              (vlax-3d-point new_pt_ )
            )
            (if (/= result_ename-lst_main-set_i 1)
              (progn
                (setq H-val (+ (+ H-val (LM:getdynpropvalue 
                              (vlax-ename->vla-object (nth  (- result_ename-lst_main-set_i 1)  result_ename-lst_main-set_)) 
                              "distance1"
                            )) 1.5 )
                )
                (TA:move_axis_insertionpoint result_ename-lst_main-set_obj_ "Y" H-val)
              )
            )

            (setq result_ename-lst_main-set_i (+ result_ename-lst_main-set_i 1))
          )
        ;
        (setq new_pt_ (list 
                        (+ (car new_pt_) 500)
                        (+ (cadr new_pt_) 0)
                        0
                      )
        )
        (setq result_ename-lst_i (+ result_ename-lst_i 1))
      )
    ;
    
  )
  (defun TA:EXTR_SPILT_EXTRSLLENGTH (spilt_obj_)
    ;presetting
      (setq STATION "PP20")
      (setq EXTR-TYPE_ "C05" )
      (setq NAME "EXTR jaaaa")
      (setq COLOR-TYPE "RAL 9016")
      (setq DANAI_EXTR_COLOR_FOR_SET "" )
      (setq color-cur_ 1)
    ;
    ;
      ; (setq spilt_ename_ (car (entsel "specify Object")))
      ; (setq spilt_obj_ (vlax-ename->vla-object spilt_ename_))
      (setq spilt_obj_ro (vla-get-rotation spilt_obj_ ))
      (setq spilt_obj_ins_ (vlax-safearray->list (vlax-variant-value (vla-get-insertionpoint spilt_obj_))))
      (setq spilt_obj_ins_ucs (if (= (getvar "worlducs") 0)(progn (trans spilt_obj_ins_ 1 1)) spilt_obj_ins_ ))
      (setq spilt_obj_getboundingbox (vla-getboundingbox spilt_obj_ 'min_ 'max_)) 
      (setq spilt_min_ (vlax-safearray->list min_)) 
      (setq spilt_max_ (vlax-safearray->list max_)) 
      (setq spilt_obj_ins_ucsmin  (if (= (getvar "worlducs") 0)(progn (trans spilt_min_ 0 1)) spilt_min_ ))
      (setq spilt_obj_ins_ucsmax (if (= (getvar "worlducs") 0)(progn (trans spilt_max_ 0 1)) spilt_max_ ))
      
      ; (command "rectangle" spilt_obj_ins_ucsmin spilt_obj_ins_ucsmax )
      ; (setq spilt_asm-xyz (TA:assembly_coordinate_coner (list  spilt_min_ spilt_max_)))
      (setq spilt_asm-xyz (car (TA:get-visible-boundingbox spilt_obj_)) )
      (vla-delete (vlax-ename->vla-object (entlast)))
      (setq spilt_obj_dist1 (atof (LM:vl-getattributevalue spilt_obj_ "EXTR.OVL-LENGTH_")))
      (if (< spilt_obj_dist1 6000) 
        (progn 
          (TA:vla-insertblock "A$Cf6525e95" spilt_obj_ins_ucs 1 spilt_obj_ro)
          ;new_blk_entlast object
            (setq newss-ss-ss_ename (entlast))
            (setq newss-ss-ss_obj (vlax-ename->vla-object newss-ss-ss_ename))
            (LM:vl-setattributevalue newss-ss-ss_obj "EXTR-LENGTH_" spilt_obj_dist1)
            (LM:setdynpropvalue newss-ss-ss_obj "distance1" spilt_obj_dist1 )
          
            (LM:vl-setattributevalue newss-ss-ss_obj "STATION" STATION)
            (LM:vl-setattributevalue newss-ss-ss_obj "EXTR-TYPE_" EXTR-TYPE_)
            (LM:vl-setattributevalue newss-ss-ss_obj "NAME" NAME)
            (LM:vl-setattributevalue newss-ss-ss_obj "COLOR-TYPE" COLOR-TYPE)
            (vla-put-color newss-ss-ss_obj color-cur_)
          ;
        )
      ) ;nom case below 6000mm.
      
      (if (> spilt_obj_dist1 6000)
        (progn
          (TA:vla-insertblock 
            "A$Cf6525e95" 
            (if (or
                  (= (rtos (rad-to-deg spilt_obj_ro ) 2 0) "90")
                  (= (rtos (rad-to-deg spilt_obj_ro ) 2 0) "270")
                )
              (progn
                (TA:midpoint (nth 0 spilt_asm-xyz) (nth 3 spilt_asm-xyz))
              )
              (TA:midpoint (nth 0 spilt_asm-xyz) (nth 1 spilt_asm-xyz))
            )
            1 
            (if (or
                  (= (rtos (rad-to-deg spilt_obj_ro ) 2 0) "90")
                  (= (rtos (rad-to-deg spilt_obj_ro ) 2 0) "270")
                )
              (progn
                (deg-to-rad 270)
              )
              spilt_obj_ro
            )
            
          )
          ;new_blk_entlast object
            (setq iextr 1)
            (setq new-ins-blk_ename (entlast))
            (setq new-ins-blk_obj (vlax-ename->vla-object new-ins-blk_ename))
            (LM:setdynpropvalue new-ins-blk_obj "distance1" 6000 )
              (LM:vl-setattributevalue new-ins-blk_obj "EXTR-LENGTH_" 6000)
              (LM:vl-setattributevalue new-ins-blk_obj "STATION" STATION)
              (LM:vl-setattributevalue new-ins-blk_obj "EXTR-TYPE_" EXTR-TYPE_)
              (LM:vl-setattributevalue new-ins-blk_obj "NAME" NAME)
              (LM:vl-setattributevalue new-ins-blk_obj "COLOR-TYPE" COLOR-TYPE)
              (vla-put-color new-ins-blk_obj color-cur_)          
            (vla-copy new-ins-blk_obj)
            (repeat (- (fix (/ spilt_obj_dist1 6000)) 1) iextr
              
              (setq new-ins-blk_ename (entlast))
              (setq new-ins-blk_obj (vlax-ename->vla-object new-ins-blk_ename))
              (TA:move_polar_insertionpoint new-ins-blk_obj "x" (* 6000 1))
              (LM:vl-setattributevalue new-ins-blk_obj "EXTR-LENGTH_" 6000)
              (LM:vl-setattributevalue new-ins-blk_obj "STATION" STATION)
              (LM:vl-setattributevalue new-ins-blk_obj "EXTR-TYPE_" EXTR-TYPE_)
              (LM:vl-setattributevalue new-ins-blk_obj "NAME" NAME)
              (LM:vl-setattributevalue new-ins-blk_obj "COLOR-TYPE" COLOR-TYPE)
              (vla-put-color new-ins-blk_obj color-cur_)
              (vla-copy new-ins-blk_obj)
              
              (setq iextr (+ iextr 1))
              
            )
            ;last pc
              (TA:move_polar_insertionpoint new-ins-blk_obj "x" (* 6000 1))
              (setq full-size_length (* (fix (/ spilt_obj_dist1 6000)) 6000))
              (setq fragment_length (- spilt_obj_dist1 full-size_length ))
              (LM:setdynpropvalue new-ins-blk_obj "distance1" fragment_length )
              (LM:vl-setattributevalue new-ins-blk_obj "EXTR-LENGTH_" fragment_length)
          
              (LM:vl-setattributevalue new-ins-blk_obj "STATION" STATION)
              (LM:vl-setattributevalue new-ins-blk_obj "EXTR-TYPE_" EXTR-TYPE_)
              (LM:vl-setattributevalue new-ins-blk_obj "NAME" NAME)
              (LM:vl-setattributevalue new-ins-blk_obj "COLOR-TYPE" COLOR-TYPE)
              (vla-put-color new-ins-blk_obj color-cur_)
            ;
          
            (setq iextr (+ iextr 1))
          ;
        )
      )
    ;
  )
  (defun c:SS-SSLLENGTH ()
    ;while selection process
      (setq ERR_ nil)
      (while ;for keep insertion point and dist. fix length one side
        (and
          (= (vl-catch-all-error-p ERR_) nil)
        )
        (setq ERR_
          (vl-catch-all-apply
            (function
              (lambda ()
                ;
                ;selection_set_for_fillter_blk_name
                  (if  ;pre_select_ssget_or_post_select_ssget
                    (=
                      (setq ss_pre_filter_set_xx_ (ssget "i"
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                      nil
                    )
                    (progn
                      (setq ss_pre_filter_set_xx_ (ssget
                                                        (list
                                                          (cons 0 "INSERT") ;type of object
                                                          ; (cons 8 "000 - GRID")   ;kind of layer
                                                          ; (cons 2 "000-GRID_LINE_DYN")       ;kind of nameblock
                                                          ; (cons 62 1)           ;kind of color call sign with color code index
                                                        )
                                                  )
                      )
                    )
                    (sslength ss_pre_filter_set_xx_)
                  )
                ;
                ;preloop_and_while
                  (setq ss_pre_filter_set_xx_i 0)
                    ; (TA:interface_text_ T)
                    (textscr)
                    (getstring "\nHit \nHit \nHit [ENTER] to continue...")
                  (while (< ss_pre_filter_set_xx_i (sslength ss_pre_filter_set_xx_))

                    
                    (setq ss_pre_filter_set_xx_ename_ (ssname ss_pre_filter_set_xx_ ss_pre_filter_set_xx_i))
                    (setq ss_pre_filter_set_xx_obj_ (vlax-ename->vla-object  ss_pre_filter_set_xx_ename_))
                    (TA:EXTR_SPILT_EXTRSLLENGTH ss_pre_filter_set_xx_obj_) 
                    (TA:textscr_process_V2 "\nupdate dynamic" ss_pre_filter_set_xx_i blk-count_list_)
                    (setq ss_pre_filter_set_xx_i (+ ss_pre_filter_set_xx_i 1))
                  )
                ;
              )
            )
          )
        )
      )
    ;
  )
  (defun c:EXTR-C1_stamp-length ()
    (_startundo doc)
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "A$Cf6525e95")))
    ;
    ;preloop_and_while
      (setq ss_pre_filter_set_xx_i 0)
      (while (< ss_pre_filter_set_xx_i (length ss_pre_filter_set_xx_))
        (setq ss_pre_filter_set_xx_ename_ (nth  ss_pre_filter_set_xx_i ss_pre_filter_set_xx_))
        (setq ss_pre_filter_set_xx_obj_ (vlax-ename->vla-object  ss_pre_filter_set_xx_ename_))
        
        (setq ss_pre_filter_set_xx_i (+ ss_pre_filter_set_xx_i 1))
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (LM:vl-setattributevalue ss_pre_filter_set_xx_obj_ "EXTR-LENGTH_" (LM:roundup (LM:getdynpropvalue ss_pre_filter_set_xx_obj_ "distance1") 1))
        (setq ss_pre_filter_set_xx_i (+ ss_pre_filter_set_xx_i 1))
      )
    ;
    (_endundo doc)
  )
  (defun c:EXTR_C2_find_below6000 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (List "A$Cf6525e95")))
    ;
    ;preloop_and_while
      (setq ss_pre_filter_set_xx_i 0)
      (setq temp-ss_ (ssadd))
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (< (LM:getdynpropvalue ss_pre_filter_set_xx_obj_ "distance1") 6000)
          (progn
            (setq temp-ss_ (ssadd ss_pre_filter_set_xx_ename_ temp-ss_ ))
          )
        )
        (setq ss_pre_filter_set_xx_i (+ ss_pre_filter_set_xx_i 1))
      )
    ;
    (command "pselect"  temp-ss_ "" )
  )

  (defun c:t1 ()
    (setq txttemp_1 "SFL")
    (setq txttemp_2 "FFL")
    (setq entatt_ename_ (car (nentsel "specify Object")))
    (setq entatt_obj_ (vlax-ename->vla-object entatt_ename_))
    (vla-put-textstring entatt_obj_ (LM:StringSubst txttemp_2 txttemp_1  (vla-get-textstring entatt_obj_)))
    
  )
  
  (defun c:temp_fix_scx2 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_Filter_set_xx_ (list "000 - CKST_HEADING_VAL")))
    ;
    ;preloop_and_while
      (setq ss_pre_filter_set_xx_i 0)
      (while (< ss_pre_filter_set_xx_i (sslength ss_pre_filter_set_xx_))
        (setq ss_pre_filter_set_xx_ename_ (ssname   ss_pre_filter_set_xx_ ss_pre_filter_set_xx_i))
        (setq ss_pre_filter_set_xx_obj_ (vlax-ename->vla-object  ss_pre_filter_set_xx_ename_))
        (if (and 
              (= (LM:EffectiveName ss_pre_filter_set_xx_obj_ ) "000 - CKST_HEADING_VAL")
              (= (wcmatch (LM:vl-getattributevalue ss_pre_filter_set_xx_obj_ "sc_val" )  "*1:*") T) 
            )
          (progn
            (setq val-X2_ (* (atoi (substr (LM:vl-getattributevalue ss_pre_filter_set_xx_obj_ "sc_val") (+ (vl-string-search ":" (LM:vl-getattributevalue ss_pre_filter_set_xx_obj_ "sc_val" ) 1 ) 2 ) 8 ) ) 2))
            (LM:vl-setattributevalue 
              ss_pre_filter_set_xx_obj_ 
              "sc_val"
              (strcat "SCALE 1:" (rtos val-X2_ 2 0 ))
            )
          )
        )
        (setq ss_pre_filter_set_xx_i (+ ss_pre_filter_set_xx_i 1))
      )
    ;
  )
  (defun c:temp_fix_scd2 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_Filter_set_xx_ (list "000 - CKST_HEADING_VAL")))
    ;
    ;preloop_and_while
      (setq ss_pre_filter_set_xx_i 0)
      (while (< ss_pre_filter_set_xx_i (sslength ss_pre_filter_set_xx_))
        (setq ss_pre_filter_set_xx_ename_ (ssname   ss_pre_filter_set_xx_ ss_pre_filter_set_xx_i))
        (setq ss_pre_filter_set_xx_obj_ (vlax-ename->vla-object  ss_pre_filter_set_xx_ename_))
        (if (and 
              (= (LM:EffectiveName ss_pre_filter_set_xx_obj_ ) "000 - CKST_HEADING_VAL")
              (= (wcmatch (LM:vl-getattributevalue ss_pre_filter_set_xx_obj_ "sc_val" )  "*1:*") T) 
            )
          (progn
            (setq val-X2_ (/ (atoi (substr (LM:vl-getattributevalue ss_pre_filter_set_xx_obj_ "sc_val") (+ (vl-string-search ":" (LM:vl-getattributevalue ss_pre_filter_set_xx_obj_ "sc_val" ) 1 ) 2 ) 8 ) ) 2))
            (LM:vl-setattributevalue 
              ss_pre_filter_set_xx_obj_ 
              "sc_val"
              (strcat "SCALE 1:" (rtos val-X2_ 2 0 ))
            )
          )
        )
        (setq ss_pre_filter_set_xx_i (+ ss_pre_filter_set_xx_i 1))
      )
    ;
  )
  (defun c:temp_fix_sc3 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "Title Block_Under Ground_C1 v3")))
    ;
    ;while selection process
      (setq ERR_ nil)
      (setq stoper 0)
      (while ;for keep insertion point and dist. fix length one side
        (and
          (= (vl-catch-all-error-p ERR_) nil)
          (/= stoper 5)
        )
        (setq ERR_1
          (vl-catch-all-apply
            (function
              (lambda ()
                ;preloop_and_while
                    (setq ss_pre_filter_set_xx_i 0)
                    (setq ERR_ (vl-catch-all-apply (function (lambda () (getstring "\nA1 = 1:5 \nA1 = 1:10 \nHit [ENTER] to continue...") ) ) ) )
                    (while (and (< ss_pre_filter_set_xx_i (sslength ss_pre_filter_set_xx_)) (= (vl-catch-all-error-p ERR_) nil))
                      (setq ss_pre_filter_set_xx_ename_ (ssname ss_pre_filter_set_xx_ ss_pre_filter_set_xx_i))
                      (setq ss_pre_filter_set_xx_obj_ (vlax-ename->vla-object  ss_pre_filter_set_xx_ename_))
                      (LM:vl-setattributevalue ss_pre_filter_set_xx_obj_ "SCALE_FOR_A1_val" "A1 = 1:5")
                      (LM:vl-setattributevalue ss_pre_filter_set_xx_obj_ "DWG_SCALE_val" "A3 = 1:10")
                      (setq ss_pre_filter_set_xx_i (+ ss_pre_filter_set_xx_i 1))
                    )
                    (setq ERR_ (vl-catch-all-apply (function (lambda () (getstring "\nA1 = 1:5 \nA1 = 1:10 \nHit [ENTER] to continue...") ) ) ) )
                    (setq ss_pre_filter_set_xx_i 0)
                    (while (and (< ss_pre_filter_set_xx_i (sslength ss_pre_filter_set_xx_)) (= (vl-catch-all-error-p ERR_) nil))
                      (setq ss_pre_filter_set_xx_ename_ (ssname ss_pre_filter_set_xx_ ss_pre_filter_set_xx_i))
                      (setq ss_pre_filter_set_xx_obj_ (vlax-ename->vla-object  ss_pre_filter_set_xx_ename_))
                      (LM:vl-setattributevalue ss_pre_filter_set_xx_obj_ "SCALE_FOR_A1_val" "A1 = 1:20")
                      (LM:vl-setattributevalue ss_pre_filter_set_xx_obj_ "DWG_SCALE_val" "A3 = 1:40")
                      (setq ss_pre_filter_set_xx_i (+ ss_pre_filter_set_xx_i 1))
                    )
                    (setq ERR_ (vl-catch-all-apply (function (lambda () (getstring "\nA1 = 1:20 \nA1 = 1:40 \nHit [ENTER] to continue...") ) ) ) )
                    (setq ss_pre_filter_set_xx_i 0)
                    (while (and (< ss_pre_filter_set_xx_i (sslength ss_pre_filter_set_xx_)) (= (vl-catch-all-error-p ERR_) nil))
                      (setq ss_pre_filter_set_xx_ename_ (ssname ss_pre_filter_set_xx_ ss_pre_filter_set_xx_i))
                      (setq ss_pre_filter_set_xx_obj_ (vlax-ename->vla-object  ss_pre_filter_set_xx_ename_))
                      (LM:vl-setattributevalue ss_pre_filter_set_xx_obj_ "SCALE_FOR_A1_val" "A1 = 1:25")
                      (LM:vl-setattributevalue ss_pre_filter_set_xx_obj_ "DWG_SCALE_val" "A3 = 1:50")
                      (setq ss_pre_filter_set_xx_i (+ ss_pre_filter_set_xx_i 1))
                    )
                    (setq ERR_ (vl-catch-all-apply (function (lambda () (getstring "\nA1 = 1:25 \nA1 = 1:50 \nHit [ENTER] to continue...") ) ) ) )
                    (setq ss_pre_filter_set_xx_i 0)
                    (while (and (< ss_pre_filter_set_xx_i (sslength ss_pre_filter_set_xx_)) (= (vl-catch-all-error-p ERR_) nil))
                      (setq ss_pre_filter_set_xx_ename_ (ssname ss_pre_filter_set_xx_ ss_pre_filter_set_xx_i))
                      (setq ss_pre_filter_set_xx_obj_ (vlax-ename->vla-object  ss_pre_filter_set_xx_ename_))
                      (LM:vl-setattributevalue ss_pre_filter_set_xx_obj_ "SCALE_FOR_A1_val" "A1 = 1:50")
                      (LM:vl-setattributevalue ss_pre_filter_set_xx_obj_ "DWG_SCALE_val" "A3 = 1:100")
                      (setq ss_pre_filter_set_xx_i (+ ss_pre_filter_set_xx_i 1))
                    )
                    (setq stoper (+ stoper 1))
                ;
              )
            )
          )
        )
      )
    ;
  )
  (defun c:temp_fix_sc4 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ttb_ (TA:EF_Filter_ss_set_V2_ ss_pre_filter_set_xx_ (list "Title Block_Under Ground_C1 v3" )))
      (setq ss_pre_filter_set_xx_hed_ (TA:EF_Filter_ss_set_V2_ ss_pre_filter_set_xx_ (list "000 - CKST_HEADING" )))
    ;
    ;preloop_and_while
      (setq ss_pre_filter_set_xx_hed_i 0)
      (setq ss_pre_filter_set_xx_hed_list_scval ())
      (while (< ss_pre_filter_set_xx_hed_i (sslength ss_pre_filter_set_xx_hed_))
        (setq ss_pre_filter_set_xx_hed_ename_ (ssname ss_pre_filter_set_xx_hed_ ss_pre_filter_set_xx_hed_i))
        (setq ss_pre_filter_set_xx_hed_obj_ (vlax-ename->vla-object  ss_pre_filter_set_xx_hed_ename_))
        (setq ss_pre_filter_set_xx_hed_list_scval (cons (LM:vl-getattributevalue ss_pre_filter_set_xx_hed_obj_ "SCALE_VAL" ) ss_pre_filter_set_xx_hed_list_scval))
        (setq ss_pre_filter_set_xx_hed_i (+ ss_pre_filter_set_xx_hed_i 1))
      )
      (setq ss_pre_filter_set_xx_hed_list_scval (vl-sort ss_pre_filter_set_xx_hed_list_scval '>))
      (setq ss_pre_filter_set_xx_hed_list_scval (LM:CountItems ss_pre_filter_set_xx_hed_list_scval nil))
      (setq SCALE_FOR_A1_val (LM:lst->str ss_pre_filter_set_xx_hed_list_scval ","))
      (setq SCALE_FOR_A3_val (LM:lst->str 
                               (mapcar 
                                 '(lambda (x) (itoa (* (atoi x) 2)))
                                 ss_pre_filter_set_xx_hed_list_scval
                               )
                               ","
                             )
      )
    ;
    (LM:vl-setattributevalue (vlax-ename->vla-object  (ssname ss_pre_filter_set_xx_ttb_ 0)) "SCALE_FOR_A1_val" (strcat "A1 = " SCALE_FOR_A1_val))
    (LM:vl-setattributevalue (vlax-ename->vla-object  (ssname ss_pre_filter_set_xx_ttb_ 0)) "DWG_SCALE_val" (strcat "A3 = " SCALE_FOR_A3_val))
  )
  (defun c:temp_fix_sc5 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ttb_ (TA:EF_Filter_ss_set_V2_ ss_pre_filter_set_xx_ (list "Title Block_Under Ground_C1 v3" )))
      (setq ss_pre_filter_set_xx_hed_ (TA:EF_Filter_ss_set_V2_ ss_pre_filter_set_xx_ (list "000 - CKST_HEADING_VAL" )))
    ;
    ;preloop_and_while
      (setq ss_pre_filter_set_xx_hed_i 0)
      (setq ss_pre_filter_set_xx_hed_list_scval ())
      (while (< ss_pre_filter_set_xx_hed_i (sslength ss_pre_filter_set_xx_hed_))
        (setq ss_pre_filter_set_xx_hed_ename_ (ssname ss_pre_filter_set_xx_hed_ ss_pre_filter_set_xx_hed_i))
        (setq ss_pre_filter_set_xx_hed_obj_ (vlax-ename->vla-object  ss_pre_filter_set_xx_hed_ename_))
        (setq ss_pre_filter_set_xx_hed_list_scval (cons (LM:StringSubst "" "SCALE 1:" (LM:vl-getattributevalue ss_pre_filter_set_xx_hed_obj_ "SC_VAL" )) ss_pre_filter_set_xx_hed_list_scval))
        (setq ss_pre_filter_set_xx_hed_i (+ ss_pre_filter_set_xx_hed_i 1))
      )
      (setq ss_pre_filter_set_xx_hed_list_scval (LM:CountItems ss_pre_filter_set_xx_hed_list_scval nil))
      (setq SCALE_FOR_A1_val (LM:lst->str ss_pre_filter_set_xx_hed_list_scval ","))
      (setq SCALE_FOR_A3_val (LM:lst->str 
                               (mapcar 
                                 '(lambda (x) (itoa (* (atoi x) 2)))
                                 ss_pre_filter_set_xx_hed_list_scval
                               )
                               ","
                             )
      )
    ;
    (LM:vl-setattributevalue (vlax-ename->vla-object  (ssname ss_pre_filter_set_xx_ttb_ 0)) "SCALE_FOR_A1_val" (strcat "A1 = " SCALE_FOR_A1_val))
    (LM:vl-setattributevalue (vlax-ename->vla-object  (ssname ss_pre_filter_set_xx_ttb_ 0)) "DWG_SCALE_val" (strcat "A3 = " SCALE_FOR_A3_val))
  )


  
  

  (defun c:f113 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;while selection process
      (setq ERR_ nil)
      (while ;for keep insertion point and dist. fix length one side
        (and
          (= (vl-catch-all-error-p ERR_) nil)
        )
        (setq ERR_
          (vl-catch-all-apply
            (function
              (lambda ()
                (setq newman_ ;Get-string by keep previous value
                    (if
                      (or
                        (/= (setq newman_val (getstring (strcat "\nSpecify Pattern name <" (if newman_ newman_ "") ">: ") ) ) "" )
                      )
                        (progn
                          (setq newman_ newman_val)
                          (setq newman_keep_val_ newman_val)
                        )
                      (setq newman_val newman_keep_val_)
                    )
                )
              )
            )
          )
        )
        
        ;preloop_and_while
          (setq ss_pre_filter_set_xx_i 0)
          (while (and 
                   (= (vl-catch-all-error-p ERR_) nil)
                   (< ss_pre_filter_set_xx_i (sslength ss_pre_filter_set_xx_))
                 )
            (setq ss_pre_filter_set_xx_ename_ (ssname ss_pre_filter_set_xx_ ss_pre_filter_set_xx_i))
            (setq ss_pre_filter_set_xx_obj_ (vlax-ename->vla-object  ss_pre_filter_set_xx_ename_))
            (if (= (vl-catch-all-error-p ERR_) nil)
              (progn
                  (if (= newman_ "+")
                    (progn
                      (LM:setdynpropvalue ss_pre_filter_set_xx_obj_ "distance3" (+ (LM:getdynpropvalue ss_pre_filter_set_xx_obj_ "distance3" ) 5) ) ;parameter 1
                      (LM:setdynpropvalue ss_pre_filter_set_xx_obj_ "distance4" (+ (LM:getdynpropvalue ss_pre_filter_set_xx_obj_ "distance4" ) 5) ) ;parameter 2
                    )
                    (List 
                      (LM:setdynpropvalue ss_pre_filter_set_xx_obj_ "distance3" (- (LM:getdynpropvalue ss_pre_filter_set_xx_obj_ "distance3" ) 5) ) ;parameter 1
                      (LM:setdynpropvalue ss_pre_filter_set_xx_obj_ "distance4" (- (LM:getdynpropvalue ss_pre_filter_set_xx_obj_ "distance4" ) 5) ) ;parameter 2
                    )
                  )
                )
              )
            
            (setq ss_pre_filter_set_xx_i (+ ss_pre_filter_set_xx_i 1))
          )
        ;
      )
    ;
  )

  (defun c:sortzone ( ) 
    (defun TA:TBsort_ (TBsort_ tol
                       / data xSortIndex xSorted currentColumn columnX
                         item itemX columnSortIndex sortedResult)

      ;; ระยะ X ที่ถือว่าอยู่ในคอลัมน์เดียวกัน
      (if (or (null tol) (<= tol 0.0))
        (setq tol 5.0)
      )

      ;; ถ้าใช้ UCS ให้แปลงจุดจาก WCS เป็น UCS ก่อน
      (if (= (getvar "WORLDUCS") 0)
        (setq data
          (mapcar
            '(lambda (item)
              (list
                (car item)
                (trans (cadr item) 0 1)
              )
            )
            TBsort_
          )
        )
        (setq data TBsort_)
      )

      ;; ขั้นแรกเรียงทุกวัตถุตาม X จากซ้ายไปขวา
      ;; ใช้ vl-sort-i เพื่อไม่ให้ข้อมูลตำแหน่งซ้ำถูกตัดออก
      (setq xSortIndex
        (vl-sort-i
          data
          '(lambda (a b)
            (< (car (cadr a)) (car (cadr b)))
          )
        )
      )
      (setq xSorted
        (mapcar
          '(lambda (index)
            (nth index data)
          )
          xSortIndex
        )
      )

      ;; แบ่งกลุ่มตามคอลัมน์จากซ้ายไปขวา
      (setq currentColumn nil
            columnX       nil
            sortedResult  nil
      )

      (foreach item xSorted
        (setq itemX (car (cadr item)))

        (if (or (null currentColumn)
                (<= (abs (- itemX columnX)) tol)
            )
          (progn
            ;; ค่า X ของสมาชิกแรกเป็นแนวอ้างอิงของคอลัมน์
            (if (null currentColumn)
              (setq columnX itemX)
            )
            (setq currentColumn (cons item currentColumn))
          )
          (progn
            ;; จบคอลัมน์เดิม: เรียงค่า Y จากมากไปน้อย
            (setq columnSortIndex
              (vl-sort-i
                currentColumn
                '(lambda (a b)
                  (> (cadr (cadr a)) (cadr (cadr b)))
                )
              )
            )
            (setq sortedResult
              (append
                sortedResult
                (mapcar
                  '(lambda (index)
                    (nth index currentColumn)
                  )
                  columnSortIndex
                )
              )
            )

            ;; เริ่มคอลัมน์ใหม่ทางขวา
            (setq currentColumn (list item)
                  columnX       itemX
            )
          )
        )
      )

      ;; เรียงและเพิ่มคอลัมน์สุดท้าย
      (if currentColumn
        (progn
          (setq columnSortIndex
            (vl-sort-i
              currentColumn
              '(lambda (a b)
                (> (cadr (cadr a)) (cadr (cadr b)))
              )
            )
          )
          (setq sortedResult
            (append
              sortedResult
              (mapcar
                '(lambda (index)
                  (nth index currentColumn)
                )
                columnSortIndex
              )
            )
          )
        )
      )

      sortedResult
    )
    (defun TA:LRsort_ (LRsort_ tol)
      (defun TA:convert-list-ucs (lst /)
        (mapcar
          '(lambda (a)
            (list
              (car a)
              (trans (cadr a) 0 1)
            )
          )
          lst
        )
      )
      (setq tol 5.0) ; ระยะที่ถือว่าเป็นแถวเดียวกัน (mm)
      (if (= (getvar "worlducs" ) 0 )
        (progn
          (setq LRsort_ (TA:convert-list-ucs LRsort_))
          (setq sorted_
            (vl-sort LRsort_
              '(lambda (a b)

                (setq ya (cadr (cadr a)))
                (setq yb (cadr (cadr b)))

                (setq xa (car (cadr a)))
                (setq xb (car (cadr b)))

                (if (> (abs (- ya yb)) tol)
                  (> ya yb) ; แถวบน -> ล่าง
                  (< xa xb) ; ซ้าย -> ขวา
                )

              )
            )

          )
        )
        (setq sorted_
          (vl-sort LRsort_
            '(lambda (a b)

              (setq ya (cadr (cadr a)))
              (setq yb (cadr (cadr b)))

              (setq xa (car (cadr a)))
              (setq xb (car (cadr b)))

              (if (> (abs (- ya yb)) tol)
                (> ya yb) ; แถวบน -> ล่าง
                (< xa xb) ; ซ้าย -> ขวา
              )

            )
          )
        )
        
      )
    )
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_list_filter_xx_ (TA:standard_list_croodinate_sorting ss_pre_filter_set_xx_ "Y" ))
    ;preloop_and_while
      ;user-input-
      (setq sortinglist_ (list "left to right" "top to below"))
      (setq sorting-finder_mode
        (TA:choose_list_v4
          sortinglist_
          "select sorting mode"
          sorting-finder_mode
        )
      )
      (setq station_number  (cond ( (getint (strcat "\nspecify get station_number \n<" (rtos (setq station_number ( cond (station_number) ( 1.0 ) ) ) ) "> : " ) ) ) (station_number) ) )
      (setq input-zone (cond ( (getint (strcat "\nspecify get input-zone \n<" (rtos (setq input-zone ( cond ( input-zone ) ( 1.0 ) ) ) ) "> : " ) ) ) (input-zone) ) )
      (setq panel_no_  (cond ( (getint (strcat "\nspecify get panel_no_ \n<" (rtos (setq panel_no_ ( cond (panel_no_) ( 1.0 ) ) ) ) "> : " ) ) ) (panel_no_) ) )
      
      (if (= sorting-finder_mode "top to below" )
        (progn
          (setq ss_list_filter_xx_sorted_ (TA:TBsort_ ss_list_filter_xx_ 5 ))
        )
        (setq ss_list_filter_xx_sorted_ (TA:LRsort_ ss_list_filter_xx_ 5 ))
      )
      (setq ss_list_filter_xx_sorted_i 0)
      (while (< ss_list_filter_xx_sorted_i (length ss_list_filter_xx_sorted_))
        (setq ss_list_filter_xx_sorted_ename_ (car (nth  ss_list_filter_xx_sorted_i ss_list_filter_xx_sorted_)))
        (setq ss_list_filter_xx_sorted_obj_ (vlax-ename->vla-object  ss_list_filter_xx_sorted_ename_))
        (if (= (wcmatch (LM:effectivename ss_list_filter_xx_sorted_obj_ ) "*ALU_TRAY_*") T)
          (progn
            ;core att
              (LM:vl-setattributevalue ss_list_filter_xx_sorted_obj_ "panel_zone" 
                (strcat "PP" (rtos station_number 2 0 ) "_" "ZONE" "_" (TA:prefix_value_00 input-zone ))
              )
              (LM:vl-setattributevalue ss_list_filter_xx_sorted_obj_ "panel_no" 
                (strcat "PP" (rtos station_number 2 0 ) "_" "ZONE" "_" (TA:prefix_value_00 input-zone )
                "_"  (TA:prefix_value_000 panel_no_))
              )
              (setq panel_no_ (+ panel_no_ 1))
            ;
          )
        )
        
        
        
        (setq ss_list_filter_xx_sorted_i (+ ss_list_filter_xx_sorted_i 1))
      )
      (if (< ss_list_filter_xx_sorted_i (length ss_list_filter_xx_sorted_))
        (progn
          (setq panel_no_ (+ panel_no_ 1))
        )
      )
    ;
  )   

  (defun c:zoneblank()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_pre_filter_set_xx_obj_ ) "*ALU_TRAY_*") T)
              (= (LM:vl-getattributevalue ss_pre_filter_set_xx_obj_ "panel_no") "")
            )
          (progn
            (setq newss (ssadd ss_pre_filter_set_xx_ename_ newss))
          )
          
        )
        (setq ss_pre_filter_set_xx_i (+ ss_pre_filter_set_xx_i 1))
      )
    ;
    (command "pselect"   newss "" )
  )
  (defun c:colorblank()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_pre_filter_set_xx_obj_ ) "*ALU_TRAY_*") T)
              (= (LM:vl-getattributevalue ss_pre_filter_set_xx_obj_ "panel_color") "")
            )
          (progn
            (setq newss (ssadd ss_pre_filter_set_xx_ename_ newss))
          )
          
        )
        (setq ss_pre_filter_set_xx_i (+ ss_pre_filter_set_xx_i 1))
      )
    ;
    (command "pselect"   newss "" )
  )
  (defun c:std1900()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_pre_filter_set_xx_obj_ ) "*ALU_TRAY_*") T)
                (= (vl-catch-all-apply 
                    (function 
                      (lambda () 
                        (= (wcmatch (LM:getdynpropvalue ss_pre_filter_set_xx_obj_ "lookup1") "*STD-LENGTH_1900*") T)
                      )
                    )
                  ) T)
            )
          (progn
            (setq newss (ssadd ss_pre_filter_set_xx_ename_ newss))
          )
          
        )
        (setq ss_pre_filter_set_xx_i (+ ss_pre_filter_set_xx_i 1))
      )
    ;
    (command "pselect"   newss "" )
  )
  (defun c:std1600()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_pre_filter_set_xx_obj_ ) "*ALU_TRAY_*") T)
                (= (vl-catch-all-apply 
                    (function 
                      (lambda () 
                        (= (wcmatch (LM:getdynpropvalue ss_pre_filter_set_xx_obj_ "lookup1") "*STD-LENGTH_1600*") T)
                      )
                    )
                  ) T)
            )
          (progn
            (setq newss (ssadd ss_pre_filter_set_xx_ename_ newss))
          )
          
        )
        (setq ss_pre_filter_set_xx_i (+ ss_pre_filter_set_xx_i 1))
      )
    ;
    (command "pselect"   newss "" )
  )
  (defun c:std1500()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_pre_filter_set_xx_obj_ ) "*ALU_TRAY_*") T)
                (= (vl-catch-all-apply 
                    (function 
                      (lambda () 
                        (= (wcmatch (LM:getdynpropvalue ss_pre_filter_set_xx_obj_ "lookup1") "*STD-LENGTH_1500*") T)
                      )
                    )
                  ) T)
            )
          (progn
            (setq newss (ssadd ss_pre_filter_set_xx_ename_ newss))
          )
          
        )
        (setq ss_pre_filter_set_xx_i (+ ss_pre_filter_set_xx_i 1))
      )
    ;
    (command "pselect"   newss "" )
  )
  (defun c:std1750()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_pre_filter_set_xx_obj_ ) "*ALU_TRAY_*") T)
                (= (vl-catch-all-apply 
                    (function 
                      (lambda () 
                        (= (wcmatch (LM:getdynpropvalue ss_pre_filter_set_xx_obj_ "lookup1") "*STD-LENGTH_1750*") T)
                      )
                    )
                  ) T)
            )
          (progn
            (setq newss (ssadd ss_pre_filter_set_xx_ename_ newss))
          )
          
        )
        (setq ss_pre_filter_set_xx_i (+ ss_pre_filter_set_xx_i 1))
      )
    ;
    (command "pselect"   newss "" )
  )
  
  (defun c:zoneup(/ newss)
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      
    ;
    ;preloop_and_while
      (setq newss (ssadd))
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (wcmatch (LM:effectivename ss_list_filter_xx_sorted_obj_ ) "*ALU_TRAY_*") T)
              (/= (LM:vl-getattributevalue ss_list_filter_xx_sorted_obj_ "panel_no") "")
            )
          (progn
            
          )
          (setq newss (ssadd ss_pre_filter_set_xx_ename_ newss))
        )
        (setq ss_pre_filter_set_xx_i (+ ss_pre_filter_set_xx_i 1))
      )
    ;
    (command "pselect"   newss "" )
  )
  

  

  (defun c:sumdyn ()
    ;presetting from code
      (setq sum_parameter "distance1")
    ; 
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq sum_val_ 0)
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (and 
              (= (vla-get-isdynamicblock ss_pre_filter_set_xx_obj_  ) :vlax-true )
              (/= (member (strcase sum_parameter) (setq dynamic_property_list_ (mapcar (function (lambda ( property_name_ ) (strcase property_name_) ) ) (LM:getdynprops_nonvalue ss_pre_filter_set_xx_obj_ ) ) )) nil )
              
            )
          (progn
            (setq sum_val_ (+ (LM:getdynpropvalue ss_pre_filter_set_xx_obj_ sum_parameter) sum_val_ ))
          )
        )
        (setq ss_pre_filter_set_xx_i (+ ss_pre_filter_set_xx_i 1))
      )
    ;
    (alert (rtos (/ sum_val_ 1000) 2 2))
    (TA:copytext->clipboard (rtos (/ sum_val_ 1000) 2 2))
  ) 
  (defun c:ar1 ()
    (setq area_ename_ (car (nentsel "specify Object")))
    (setq area_obj_ (vlax-ename->vla-object area_ename_))
    (setq area_obj_area (/ (vla-get-area area_obj_) 1000000))
    (alert (rtos area_obj_area 2 2))
    (TA:copytext->clipboard (rtos area_obj_area 2 2))
  ) 
  
  (defun c:MKpliso ()
    (setvar "SELECTIONPREVIEW" 3)
    (setq pline1_ename_ (car (entsel "specify Object")))
    (setq pline1_obj_ (vlax-ename->vla-object pline1_ename_))
    (setq pline1_obj_vtx_ (TA:Get_Pline_vertext_angle_case1 pline1_ename_))
    (setq pline2_ename_ (car (entsel "specify Object")))
    (setq pline2_obj_ (vlax-ename->vla-object pline2_ename_))
    (setq pline2_obj_vtx_ (TA:Get_Pline_vertext_angle_case2 pline2_ename_))
    
    
    ;preloop_and_while
      (setq pline1_obj_vtx_i 0)
      (while (and 
               (< pline1_obj_vtx_i (length pline1_obj_vtx_))
               (= (length pline1_obj_vtx_ ) (length pline2_obj_vtx_))
               
             )
        (if (or 
              (= 1 1)
              (= pline1_obj_vtx_i 0)
              (= pline1_obj_vtx_i 3)
              (= pline1_obj_vtx_i 5)
              (= pline1_obj_vtx_i 7)
              (= pline1_obj_vtx_i 9)
            )
          (progn
            (command "line" 
                     (if (= (getvar "worlducs") 0)
                       (progn 
                         (trans (car (nth pline1_obj_vtx_i pline1_obj_vtx_)) 0 1)
                       )
                       (car (nth pline1_obj_vtx_i pline1_obj_vtx_)) 
                     )
                     (if (= (getvar "worlducs") 0)
                       (progn 
                         (trans (car (nth pline1_obj_vtx_i pline2_obj_vtx_)) 0 1)
                       )
                       (car (nth pline1_obj_vtx_i pline2_obj_vtx_)) 
                     )

                     ""  
            )
          )
        )
  
        
    
        (setq pline1_obj_vtx_i (+ pline1_obj_vtx_i 1))
      )
    ;
    
    


    (setvar "SELECTIONPREVIEW" 1)
  )



  (defun c:swap ()
    (setq sss_ename_ (car (entsel "specify Object")))
    (setq sss_obj_ (vlax-ename->vla-object sss_ename_))
    (setq sss_obj_ins_ (vlax-safearray->list (vlax-variant-value (vla-get-insertionpoint sss_obj_))))

    (setq ttt_ename_ (car (entsel "specify Object")))
    (setq ttt_obj_ (vlax-ename->vla-object ttt_ename_))
    (setq ttt_obj_ins_ (vlax-safearray->list (vlax-variant-value (vla-get-insertionpoint ttt_obj_))))

    (cond
      (;_case_1 TEXT กับ TEXT
         (and
            (= (vla-get-objectname sss_obj_) "AcDbText")
            (= (vla-get-objectname ttt_obj_) "AcDbText")
         )
         (progn
           (setq sss_text_ (vla-get-textstring sss_obj_))
           (setq ttt_text_ (vla-get-textstring ttt_obj_))
           (vla-put-textstring sss_obj_ ttt_text_)
           (vla-put-textstring ttt_obj_ sss_text_)
           (princ "_case_1")
         )
      )
      (;_case_2 MTEXT กับ MTEXT
         (and
            (= (vla-get-objectname sss_obj_) "AcDbMText")
            (= (vla-get-objectname ttt_obj_) "AcDbMText")
         )
         (progn
           (setq sss_text_ (vla-get-textstring sss_obj_))
           (setq ttt_text_ (vla-get-textstring ttt_obj_))
           (vla-put-textstring sss_obj_ ttt_text_)
           (vla-put-textstring ttt_obj_ sss_text_)
           (princ "_case_2")
         )
      )
      (;_case_3 BLOCK กับ BLOCK
         (and
            (= (vla-get-objectname sss_obj_) "AcDbBlockReference")
            (= (vla-get-objectname ttt_obj_) "AcDbBlockReference")
         )
         (progn
           (vla-put-insertionpoint sss_obj_ (vlax-3d-point ttt_obj_ins_))
           (vla-put-insertionpoint ttt_obj_ (vlax-3d-point sss_obj_ins_))
           (princ "_case_3")
         )
      )
      (;_case_4 วัตถุชนิดอื่น
         (and
            sss_obj_
            ttt_obj_
         )
         (progn
           (vla-put-insertionpoint sss_obj_ (vlax-3d-point ttt_obj_ins_))
           (vla-put-insertionpoint ttt_obj_ (vlax-3d-point sss_obj_ins_))
           (princ "_case_4")
         )
      )
    )
    (princ)
  )
  (defun c:TEMP_MAINtoSUB_ ()
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (= (wcmatch (vla-get-layer ss_pre_filter_set_xx_obj_ ) "*MAIN_COLOR_*") T)
          (progn
            (vla-put-layer
              ss_pre_filter_set_xx_obj_ 
              (LM:StringSubst "SUB" "MAIN" (vla-get-layer ss_pre_filter_set_xx_obj_ ))
            )
          )
        )
        (setq ss_pre_filter_set_xx_i (+ ss_pre_filter_set_xx_i 1))
      )
    ;
  )
  (defun c:TEMP_SUBtoMAIN_ ()
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (= (wcmatch (vla-get-layer ss_pre_filter_set_xx_obj_ ) "*MAIN_COLOR_*") T)
          (progn
            (vla-put-layer
              ss_pre_filter_set_xx_obj_ 
              (LM:StringSubst "SUB" "MAIN" (vla-get-layer ss_pre_filter_set_xx_obj_ ))
            )
          )
        )
        (setq ss_pre_filter_set_xx_i (+ ss_pre_filter_set_xx_i 1))
      )
    ;
  )
  (defun c:TEMP_p2p_ ()
    ;selection_set_for_fillter_blk_name
      (if  ;pre_select_ssget_or_post_select_ssget
        (=
          (setq ss_pre_filter_set_xx_ (ssget "i"
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              ; (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (if (= (wcmatch (vla-get-layer ss_pre_filter_set_xx_obj_ ) "*PANEL_PANEL*") T)
          (progn
            (vla-put-layer
              ss_pre_filter_set_xx_obj_ 
              (LM:StringSubst  "PANEL_BACK-PANEL" "PANEL_PANEL" (vla-get-layer ss_pre_filter_set_xx_obj_ ))
            )
          )
        )
        (setq ss_pre_filter_set_xx_i (+ ss_pre_filter_set_xx_i 1))
      )
    ;
  )
  (defun c:temp_replace_text_t11 ()
    (setq old_text "M10")
    (setq new_text "M5")
    (setq sss_ename_ (car (entsel "specify Object")))
    (setq sss_obj_ (vlax-ename->vla-object sss_ename_))
    (setq sss_obj_text_ (vla-get-textstring sss_obj_))
    (vla-put-textstring sss_obj_ (LM:StringSubst  new_text old_text sss_obj_text_) )
    
  )



  (defun c:RECTANGLE_TO_BLOCK_REC-TO-BLK ()
    ;presetting 
      (_StartUndo doc)
    ; 
    ;selection_set_for_fillter_blk_name
      (if  ;pre_select_ssget_or_post_select_ssget
        (=
          (setq ss_pre_filter_set_xx_ (ssget "i"
                                            (list
                                              (cons 0 "LWPOLYLINE") ;type of object
                                              ; (cons 8 "000 - GRID")   ;kind of layer
                                              ; (cons 2 "000-GRID_LINE_DYN")       ;kind of nameblock
                                              (cons 62 3)           ;kind of color call sign with color code index
                                            )
                                      )
          )
          nil
        )
        (progn
          (setq ss_pre_filter_set_xx_ (ssget
                                            (list
                                              (cons 0 "LWPOLYLINE") ;type of object
                                              ; (cons 8 "000 - GRID")   ;kind of layer
                                              ; (cons 2 "000-GRID_LINE_DYN")       ;kind of nameblock
                                              (cons 62 3)           ;kind of color call sign with color code index
                                            )
                                      )
          )
        )
        (sslength ss_pre_filter_set_xx_)
      )
    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_obj_min_ (vlax-safearray->list min_)) 
        (setq ss_pre_filter_set_xx_obj_max_ (vlax-safearray->list max_)) 
        (setq ss_pre_filter_set_xx_obj_assembly_coord  (nth 4 (TA:assembly_coordinate_coner (list ss_pre_filter_set_xx_obj_min_ ss_pre_filter_set_xx_obj_max_))))
        (TA:vla-insertblock 
          "010 - C10_PANEL_PANEL_GREEN_PLATE_SET-B-BOT-VIEW" 
          ss_pre_filter_set_xx_obj_assembly_coord
          1
          (deg-to-rad 90)
        )
        (setq ss_pre_filter_set_xx_i (+ ss_pre_filter_set_xx_i 1))
      )
    ;
    (_endUndo doc)
  )

  (defun c:temp_t6 ()
    (setq sss_ename_ (car (entsel "specify Object")))
    (setq sss_obj_ (vlax-ename->vla-object sss_ename_))
    (setq sss_obj_getboundingbox (vla-getboundingbox sss_obj_ 'min_ 'max_)) 
    (setq sss_min_ (vlax-safearray->list min_)) 
    (setq sss_max_ (vlax-safearray->list max_)) 
    (setq sss_assembly_coord  (nth 0 (TA:assembly_coordinate_coner (list sss_min_ sss_max_))))
    
    (setq hhh_ename_ (car (entsel "specify Object")))
    (setq hhh_obj_ (vlax-ename->vla-object hhh_ename_))
    (setq hhh_obj_getboundingbox (vla-getboundingbox hhh_obj_ 'min_ 'max_)) 
    (setq hhh_min_ (vlax-safearray->list min_)) 
    (setq hhh_max_ (vlax-safearray->list max_)) 
    (setq hhh_assembly_coord  (nth 3 (TA:assembly_coordinate_coner (list hhh_min_ hhh_max_))))
    
      (vla-move
        hhh_obj_ 
        (vlax-3d-point hhh_assembly_coord)
        (vlax-3d-point sss_assembly_coord)
        
      )
    
    
  )

  (defun c:temp_T7 ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
      (setq ss_pre_filter_set_xx_ (TA:EF_Filter_ss_set_V2_ ss_pre_filter_set_xx_ (list "A$C3cbad0ab")) )
      (setq user-input-point_ (getpoint "input point") )
      (setq user-input-point_(if (= (getvar "worlducs") 0)(progn (trans user-input-point_ 1 1)) user-input-point_ ))

    ;
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_ins_ (vlax-safearray->list (vlax-variant-value (vla-get-insertionpoint ss_pre_filter_set_xx_obj_))))
        (setq ss_pre_filter_set_xx_obj_ins_ (if (= (getvar "worlducs") 0)(progn (trans ss_pre_filter_set_xx_obj_ins_ 0 1)) ss_pre_filter_set_xx_obj_ins_ ))
        
        (LM:setdynpropvalue ss_pre_filter_set_xx_obj_ "distance1" (distance ss_pre_filter_set_xx_obj_ins_ (list (car ss_pre_filter_set_xx_obj_ins_) (cadr user-input-point_) 0 ) ))
        
        (setq ss_pre_filter_set_xx_i (+ ss_pre_filter_set_xx_i 1))
      )
    ;


    
  )




  (defun c:TA_SET_ALL_BLOCK_UNITS_MM ;แปลงทุกอย่างให้เป็นหน่วย millimeter 
    ( / acad_document_ blocks_collection_ block_obj_ success_count_ skip_count_ error_result_ )

    (vl-load-com)

    (setq acad_document_
      (vla-get-ActiveDocument
        (vlax-get-acad-object)
      )
    )

    (setq blocks_collection_
      (vla-get-Blocks acad_document_)
    )

    (setq success_count_ 0)
    (setq skip_count_    0)

    ;; กำหนดหน่วยของ Drawing เป็น Millimeters
    (setvar "INSUNITS" 4)

    (vlax-for block_obj_ blocks_collection_

      ;; ไม่แก้ Layout และ Xref
      (if
        (and
          (= (vla-get-IsLayout block_obj_) :vlax-false)
          (= (vla-get-IsXRef block_obj_)   :vlax-false)
          (vlax-property-available-p block_obj_ 'Units T)
        )

        (progn
          (setq error_result_
            (vl-catch-all-apply
              'vla-put-Units
              (list block_obj_ 4)
            )
          )

          (if (vl-catch-all-error-p error_result_)
            (setq skip_count_ (1+ skip_count_))
            (setq success_count_ (1+ success_count_))
          )
        )

        (setq skip_count_ (1+ skip_count_))
      )
    )

    (vla-Regen acad_document_ 1)

    (princ
      (strcat
        "\nBlock units changed to Millimeters: "
        (itoa success_count_)
        "\nSkipped Layout/Xref/Unsupported blocks: "
        (itoa skip_count_)
      )
    )

    (princ)
  )


(defun c:csvtoblk ()
  (defun TA:Addrectangle (spc StartPoint Width Height InsertPoint / x y x0 y0 pts pl)

    (setq x (car StartPoint)
          y (cadr StartPoint))

    ;; หา Bottom-Left ของ Rectangle
    (cond

      ;; Center
      ((= InsertPoint 0)
      (setq x0 (- x (/ Width 2.0))
            y0 (- y (/ Height 2.0)))
      )

      ;; Bottom Left
      ((= InsertPoint 1)
      (setq x0 x
            y0 y)
      )

      ;; Bottom Right
      ((= InsertPoint 2)
      (setq x0 (- x Width)
            y0 y)
      )

      ;; Top Right
      ((= InsertPoint 3)
      (setq x0 (- x Width)
            y0 (- y Height))
      )

      ;; Top Left
      ((= InsertPoint 4)
      (setq x0 x
            y0 (- y Height))
      )

    )

    ;; สร้าง Vertex Array
    (setq pts
      (vlax-make-safearray
        vlax-vbDouble
        '(0 . 7)
      )
    )

    (vlax-safearray-fill
      pts
      (list
        x0             y0
        (+ x0 Width)   y0
        (+ x0 Width)   (+ y0 Height)
        x0             (+ y0 Height)
      )
    )

    ;; สร้าง Polyline
    (setq pl
      (vla-AddLightWeightPolyline spc pts)
    )

    (vla-put-Closed pl :vlax-true)

    ;; Return VLA Object
    pl
  )
  (defun TA:GetBracketData (str / p1 p2)
    (if
      (and
        (setq p1 (vl-string-search "(" str))
        (setq p2 (vl-string-search ")" str p1))
      )
      (substr str (+ p1 2) (- p2 p1 1))
    )
  )
  (defun TA:ssget-vla-boundary (vla-obj filter / coords pts ss)

    ;; ดึง Coordinates จาก VLA Object
    (setq coords
      (vlax-safearray->list
        (vlax-variant-value
          (vla-get-Coordinates vla-obj)
        )
      )
    )

    ;; แปลง x y x y ... -> ((x y) (x y) ...)
    (while coords
      (setq pts
        (cons
          (list (car coords) (cadr coords))
          pts
        )
      )
      (setq coords (cddr coords))
    )

    (setq pts (reverse pts))

    ;; Selection
    (setq ss
      (ssget "_CP" pts filter)
    )

    ss
  )
  (defun TA:SS-SetLayerColor (ss layer color / i obj)

    (if ss
      (repeat (setq i (sslength ss))

        (setq obj
          (vlax-ename->vla-object
            (ssname ss (setq i (1- i)))
          )
        )

        ;; Layer
        (vla-put-Layer obj layer)

        ;; Color
        (vla-put-Color obj color)

      )
    )

    ss
  )
  (defun TA:Delay (ms / t0)
    (setq t0 (getvar "MILLISECS"))
    (while (< (- (getvar "MILLISECS") t0) ms))
  )
  (setq doc (vla-get-ActiveDocument (vlax-get-acad-object)))
  (setq spc (vla-get-ModelSpace doc))
  (setq kkk (TA:GetClipboardText ))
  (setq insert-list_ (LM:str->lst kkk "\r\n"))
  
  (setq startpoint (getpoint "startpoint ")
        startpoint (list (LM:round (car startpoint)) 
                         (LM:round (cadr startpoint))
                         (LM:round (caddr startpoint))
                   )
  )
  
  ;preloop_and_while
    (setq insert-list_i 0)
    (setq startpoint_runloop startpoint)
    (while (< insert-list_i (- (length insert-list_) 1))
      (setq insert-list_val_ (LM:str->lst (nth  insert-list_i insert-list_) ","))
      ; (setq insert-list_val_ (LM:str->lst "C04,1750,SD,S5206TH,standard_shape,(0)" ","))
      (if 
        (and 
          (>= (atof (nth 1 insert-list_val_ )) 200)
          (/= (wcmatch (nth 4 insert-list_val_ ) "*trapezoids*") T)
          (wcmatch 
            (vl-princ-to-string 
              (vl-catch-all-apply 
                (function 
                  (lambda () 
                    (vla-Item (vla-get-Blocks doc) (strcat "300HK ORDER FROM CHINA REV.2-LOT 2_300" (nth 1 insert-list_val_) "HK-A-PF-S-ACOUS" ) )
                  )
                )
              )
            )
            "*IAcadBlock*"
          )
        )
        (progn
          (TA:vla-insertblock 
            "A$C55c47737"
            startpoint_runloop
            1
            0
          )
          (TA:vla-insertblock 
            (strcat "300HK ORDER FROM CHINA REV.2-LOT 2_300" (nth 1 insert-list_val_ ) "HK-A-PF-S-ACOUS")
            startpoint_runloop
            1000
            0
          )
          ;new_blk_entlast object
            (setq newblkinsert_ename (entlast))
            (setq newblkinsert_obj_ (vlax-ename->vla-object newblkinsert_ename))
            (vla-explode newblkinsert_obj_)
            (vla-Delete newblkinsert_obj_)

            
          ;
          ;insertlist_data 
            (setq  insert-list_val_position_ (LM:str->lst (TA:GetBracketData (nth  insert-list_i insert-list_)) ","))
            (create-text-vla 
              (vlax-3d-point (list (car startpoint_runloop) (- (cadr startpoint_runloop) 2000) (caddr startpoint_runloop) ))
              (nth  insert-list_i insert-list_)
              500
              0
            )
            (vla-put-layer (vlax-ename->vla-object (entlast)) "Defpoints")
            (getstring "2000")
            (cond
              ( (= (length insert-list_val_position_ )  1)
                (progn
                  (setq insmid (list 
                                      (+ (car startpoint_runloop) (atof (nth 0 insert-list_val_position_)))
                                      (+ (cadr startpoint_runloop) 150)
                                      (+ (caddr startpoint_runloop) 0)
                                    )
                  )
                  (setq rec-mid_obj_ (if (= (wcmatch (nth 2 insert-list_val_) "*DL*") T) 
                          (progn 
                            (TA:Addrectangle spc insmid 110 110 0)
                          )
                          (TA:Addrectangle spc insmid 130 130 0)
                        )
                  )
                  (vla-put-layer rec-mid_obj_ "Defpoints")
                  (TA:SS-SetLayerColor 
                    (TA:ssget-vla-boundary rec-mid_obj_ '((0 . "circle")))  
                    "Defpoints" 
                    256
                  )
                )
              )
              ( (= (length insert-list_val_position_ )  2)
                (progn
                  (setq insleft (list 
                                      (+ (car startpoint_runloop) (atof (nth 0 insert-list_val_position_)))
                                      (+ (cadr startpoint_runloop) 150)
                                      (+ (caddr startpoint_runloop) 0)
                                    )
                  )
                  (setq insright (list 
                                          (+ (car startpoint_runloop) (atof (nth 1 insert-list_val_position_)))
                                          (+ (cadr startpoint_runloop) 150)
                                          (+ (caddr startpoint_runloop) 0)
                                        )
                  )
                  (setq rec-left_obj_ (if (= (wcmatch (nth 2 insert-list_val_) "*DL*") T) 
                          (progn 
                            (TA:Addrectangle spc insleft 110 110 0)
                          )
                          (TA:Addrectangle spc insleft 130 130 0)
                        )
                  )
                  (vla-put-layer rec-left_obj_ "Defpoints")
                  (TA:SS-SetLayerColor 
                    (TA:ssget-vla-boundary rec-left_obj_ '((0 . "circle")))  
                    "Defpoints" 
                    256
                  )
                  (setq rec-right_obj_ (if (= (wcmatch (nth 2 insert-list_val_) "*DL*") T) 
                          (progn 
                            (TA:Addrectangle spc insright 110 110 0)
                          )
                          (TA:Addrectangle spc insright 130 130 0)
                        )
                  )
                  (vla-put-layer rec-right_obj_ "Defpoints")
                  (TA:SS-SetLayerColor 
                    (TA:ssget-vla-boundary rec-right_obj_ '((0 . "circle")))  
                    "Defpoints" 
                    256
                  )
                )
              )
              ( (= (length insert-list_val_position_ )  3)
                (progn
                  (setq insleft (list 
                                      (+ (car startpoint_runloop) (atof (nth 0 insert-list_val_position_)))
                                      (+ (cadr startpoint_runloop) 150)
                                      (+ (caddr startpoint_runloop) 0)
                                    )
                  )
                  (setq insmid (list 
                                      (+ (car startpoint_runloop) (atof (nth 1 insert-list_val_position_)))
                                      (+ (cadr startpoint_runloop) 150)
                                      (+ (caddr startpoint_runloop) 0)
                                    )
                  )
                  (setq insright (list 
                                      (+ (car startpoint_runloop) (atof (nth 2 insert-list_val_position_)))
                                      (+ (cadr startpoint_runloop) 150)
                                      (+ (caddr startpoint_runloop) 0)
                                    )
                  )
                  (setq rec-left_obj_ (if (= (wcmatch (nth 2 insert-list_val_) "*DL*") T) 
                          (progn 
                            (TA:Addrectangle spc insleft 110 110 0)
                          )
                          (TA:Addrectangle spc insleft 130 130 0)
                        )
                  )
                  (vla-put-layer rec-left_obj_ "Defpoints")
                  (TA:SS-SetLayerColor 
                    (TA:ssget-vla-boundary rec-left_obj_ '((0 . "circle")))  
                    "Defpoints" 
                    256
                  )
                  (setq rec-mid_obj_ (if (= (wcmatch (nth 2 insert-list_val_) "*DL*") T) 
                          (progn 
                            (TA:Addrectangle spc insmid 110 110 0)
                          )
                          (TA:Addrectangle spc insmid 130 130 0)
                        )
                  )
                  (vla-put-layer rec-mid_obj_ "Defpoints")
                  (vla-put-layer rec-mid_obj_ "Defpoints")
                  (TA:SS-SetLayerColor 
                    (TA:ssget-vla-boundary rec-mid_obj_ '((0 . "circle")))  
                    "Defpoints" 
                    256
                  )
                  (setq rec-right_obj_ (if (= (wcmatch (nth 2 insert-list_val_) "*DL*") T) 
                          (progn 
                            (TA:Addrectangle spc insright 110 110 0)
                          )
                          (TA:Addrectangle spc insright 130 130 0)
                        )
                  )
                  (vla-put-layer rec-right_obj_ "Defpoints")
                  (TA:SS-SetLayerColor 
                    (TA:ssget-vla-boundary rec-right_obj_ '((0 . "circle")))  
                    "Defpoints" 
                    256
                  )
                )
              )
            )
            
          ;
        )
        (create-text-vla 
          (vlax-3d-point startpoint_runloop)
          (strcat "NO BLOCK " "300HK ORDER FROM CHINA REV.2-LOT 2_300" (nth 1 insert-list_val_) "HK-A-PF-S-ACOUS" "---------------" (nth  insert-list_i insert-list_))
          1000
          0
        )
      )
        (setq startpoint_runloop (list 
                                  (+ (car startpoint_runloop) 0)
                                  (- (cadr startpoint_runloop) 7000)
                                  (+ (caddr startpoint_runloop) 0)
                                  
                                  )
        )
      ;
      (setq insert-list_i (+ insert-list_i 1))
      (setq t0 (getvar "MILLISECS"))
    )
  ;
)
(defun c:csv2 ()
  
  ; (setq kkk_obj_str_ (TA:GetClipboardText ))
  (setq kkk_ename_ (car (nentsel "specify Object")))
  (setq kkk_obj_ (vlax-ename->vla-object kkk_ename_))
  (setq kkk_obj_str_ (vla-get-textstring kkk_obj_ ))
  (setq insert-list_ (LM:str->lst kkk_obj_str_ ","))
  (setq newTTB_ename_ (car (entsel "specify Object")))
  (setq newTTB_obj_ (vlax-ename->vla-object newTTB_ename_))
  (if (> (length insert-list_) 1) 
    (progn 
      (LM:vl-setattributevalue 
        newTTB_obj_
        "TTL_PJ_PART-CODE"
        (strcat 
          "300"
          (nth 1 insert-list_)
          "HK-A/PF-S/ACOUS"
          "-"
          (cond
            ( (= (wcmatch (nth 4 insert-list_) "standard_shape") T)
              (progn
                "STD"
              )
            )
            ( (= (wcmatch (nth 4 insert-list_) "*varies*") T)
              (progn
                "VAR"
              )
            )
            ( (= (wcmatch (nth 4 insert-list_) "*trapezoids*") T)
              (progn
                "TZD"
              )
            )
          )
          "\\P"
          "/"
          "("
          (nth 0 insert-list_)
          ","
          (nth 2 insert-list_)
          ","
          (TA:GetBracketData kkk_obj_str_)
          ")"
        )
      )
      (LM:vl-setattributevalue newTTB_obj_ "TTL_PJ_PART-NAME" "Alu.hook on Panel")
      (LM:vl-setattributevalue newTTB_obj_ "TTL_PJ_FINISH_1" (nth 3 insert-list_))
    )
  )
  
)
(defun c:csv3 ()
  
  (setq clipboard_list_ (TA:GetClipboardText ))
  (setq insert-list_ (LM:str->lst clipboard_list_ "\r\n"))
  (length insert-list_)
  ;selection_set_for_fillter_blk_name
    (if  ;pre_select_ssget_or_post_select_ssget
      (=
        (setq text-ss_ (ssget "i"
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq text-ss_ (ssget
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
      )
      (sslength text-ss_)
    )
    
  ;
  (TA:ss_text_to_list text-ss_)
  (length (TA:ss_text_to_list text-ss_))
  
  ;preloop_and_while
    (setq text-ss_i 0)
    (while (< text-ss_i (sslength text-ss_))
      (setq text-ss_ename_ (ssname  text-ss_ text-ss_i ))
      (setq text-ss_obj_ (vlax-ename->vla-object  text-ss_ename_  ))
      (setq text-ss_obj_str (vla-get-textstring  text-ss_obj_  ))
      (if (/= (member  text-ss_obj_str insert-list_) nil)
        (progn
          (vla-put-color text-ss_obj_ 1)
        )
        (vla-put-color text-ss_obj_ 2)
      )
  
      (setq text-ss_i (+ text-ss_i 1))
    )
  ;
)
(defun c:csv4 ()
  
  (setq clipboard_list_ (TA:GetClipboardText ))
  (setq insert-list_ (LM:str->lst clipboard_list_ "\r\n"))
  (length insert-list_)
  ;selection_set_for_fillter_blk_name
    (if  ;pre_select_ssget_or_post_select_ssget
      (=
        (setq text-ss_ (ssget "i"
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq text-ss_ (ssget
                                          (list
                                            (cons 0 "text") ;type of object
                                            ; (cons 8 "000 - GRID")   ;kind of layer
                                            ; (cons 2 "000-GRID_LINE_DYN")       ;kind of nameblock
                                            ; (cons 62 1)           ;kind of color call sign with color code index
                                          )
                                    )
        )
      )
      (sslength text-ss_)
    )
    
  ;
  ; (TA:ss_text_to_list text-ss_)
  
  ;preloop_and_while
    (setq text-ss_i 0)
    (while (< text-ss_i (sslength text-ss_))
      (setq text-ss_ename_ (ssname  text-ss_ text-ss_i ))
      (setq text-ss_obj_ (vlax-ename->vla-object  text-ss_ename_  ))
      (setq text-ss_obj_str (vla-get-textstring  text-ss_obj_  ))
      (if (/= (member  text-ss_obj_str insert-list_) nil)
        (progn
          (vla-put-color text-ss_obj_ 1)
        )
        (vla-put-color text-ss_obj_ 2)
      )
  
      (setq text-ss_i (+ text-ss_i 1))
    )
  ;
)

(defun c:TA1
  (
    /
    ss_
    ss_i_
    text_ename_
    text_obj_
    point_
    data_list_
    item_
    start_number_
    current_number_
    changed_
    error_result_
  )

  (vl-load-com)

  ;; ใช้วัตถุที่เลือกไว้ก่อน ถ้าไม่มีจึงให้เลือกใหม่
  (setq ss_ (ssget "_I" '((0 . "TEXT,MTEXT"))))

  (if (not ss_)
    (progn
      (prompt "\nSelect TEXT or MTEXT: ")
      (setq ss_ (ssget '((0 . "TEXT,MTEXT"))))
    )
  )

  (if ss_
    (progn
      ;; จำเลขเริ่มต้นครั้งก่อน
      (if
        (not
          (and
            (eq (type TA:text_number_start_) 'INT)
            (> TA:text_number_start_ 0)
          )
        )
        (setq TA:text_number_start_ 1)
      )

      (initget 6)
      (setq start_number_ (cond ((getint (strcat "\nStarting number <" (itoa TA:text_number_start_) ">: "))) (TA:text_number_start_)))
      (setq TA:text_number_start_ start_number_)

      (setq ss_i_ 0)
      (setq data_list_ nil)

      ;; เก็บ Object, ตำแหน่ง และลำดับเดิม
      (while (< ss_i_ (sslength ss_))
        (setq text_ename_ (ssname ss_ ss_i_))
        (setq text_obj_ (vlax-ename->vla-object text_ename_))

        (setq point_
          (vlax-safearray->list
            (vlax-variant-value
              (vla-get-InsertionPoint text_obj_)
            )
          )
        )

        ;; แปลง WCS เป็น UCS ปัจจุบัน
        (setq point_ (trans point_ 0 1))
        (setq data_list_ (cons (list text_obj_ point_ ss_i_) data_list_))
        (setq ss_i_ (1+ ss_i_))
      )

      ;; Y มากไปน้อย; ถ้า Y เท่ากัน X น้อยไปมาก
      (setq data_list_
        (vl-sort
          data_list_
          (function
            (lambda (a_ b_ / point_a_ point_b_)
              (setq point_a_ (cadr a_))
              (setq point_b_ (cadr b_))

              (cond
                ((/= (cadr point_a_) (cadr point_b_))
                  (> (cadr point_a_) (cadr point_b_))
                )
                ((/= (car point_a_) (car point_b_))
                  (< (car point_a_) (car point_b_))
                )
                (T
                  (< (caddr a_) (caddr b_))
                )
              )
            )
          )
        )
      )

      ;; เปลี่ยนข้อความเป็นตัวเลข
      (setq current_number_ start_number_)
      (setq changed_ 0)

      (foreach item_ data_list_
        (setq error_result_
          (vl-catch-all-apply
            'vla-put-TextString
            (list (car item_) (itoa current_number_))
          )
        )

        (if (not (vl-catch-all-error-p error_result_))
          (progn
            (setq current_number_ (1+ current_number_))
            (setq changed_ (1+ changed_))
          )
        )
      )

      (prompt
        (strcat
          "\nChanged "
          (itoa changed_)
          " text object(s)."
        )
      )
    )

    (prompt "\nNo TEXT or MTEXT selected.")
  )

  (princ)
)

(defun c:csv202 ()
  (defun TAS:OFFSET_BOUNDINGBOX (bbox_ offset_ / min_point_ max_point_)
    (if (and bbox_ (listp bbox_))
      (progn
        (setq min_point_ (car bbox_))
        (setq max_point_ (cadr bbox_))

        (list
          (list
            (- (car min_point_) offset_)
            (- (cadr min_point_) offset_)
            (caddr min_point_)
          )
          (list
            (+ (car max_point_) offset_)
            (+ (cadr max_point_) offset_)
            (caddr max_point_)
          )
        )
      )
      (progn
        (princ "\nError: bbox_ must be a list.")
        nil
      )
    )
  )
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  (setq ss_pre_filter_set_xx_ (TA:EF_Filter_ss_set_V2_ ss_pre_filter_set_xx_ (list "D5HU")))
        
  ;preloop_and_while
    ; (setq ss_pre_filter_set_xx_i 160)
    (setq ss_pre_filter_set_xx_i 0)
    (setq ss_finding_Text_ nil)
    (while (< ss_pre_filter_set_xx_i (sslength ss_pre_filter_set_xx_))
      
      (setq ss_pre_filter_set_xx_ename_ (ssname ss_pre_filter_set_xx_ ss_pre_filter_set_xx_i))
      (setq ss_pre_filter_set_xx_obj_ (vlax-ename->vla-object  ss_pre_filter_set_xx_ename_))
      (setq ss_pre_filter_set_xx_obj_getboundingbox (vla-getboundingbox ss_pre_filter_set_xx_obj_ 'min_ 'max_)) 
      (setq ss_pre_filter_set_xx_min_ (vlax-safearray->list min_)) 
      (setq ss_pre_filter_set_xx_max_ (vlax-safearray->list max_)) 
      
      (vla-zoomcenter 
        (vlax-get-acad-object)
        (vlax-3d-point (list 
                         (nth 0 (nth 2 (TA:assembly_coordinate_coner (list ss_pre_filter_set_xx_min_ ss_pre_filter_set_xx_max_) )))
                         (- (nth 1 (nth 2 (TA:assembly_coordinate_coner (list ss_pre_filter_set_xx_min_ ss_pre_filter_set_xx_max_) ))) 
                            110
                         )
                         (nth 2 (nth 2 (TA:assembly_coordinate_coner (list ss_pre_filter_set_xx_min_ ss_pre_filter_set_xx_max_) )))
                       ) 
        )
        100
      )
      (getstring "\nHit \nHit \nHit [ENTER] to continue...")
      
      (setq ss_finding_Text_ (ssget "_C" 
                                         (nth 0 (TAS:OFFSET_BOUNDINGBOX (list ss_pre_filter_set_xx_min_ ss_pre_filter_set_xx_max_ ) 50 ))
                                         (nth 1 (TAS:OFFSET_BOUNDINGBOX (list ss_pre_filter_set_xx_min_ ss_pre_filter_set_xx_max_ ) 50 ))
                                         (list (cons 0 "text"))
                                  )
      )
      (vla-zoomcenter 
        (vlax-get-acad-object)
        (vlax-3d-point (list 
                         (nth 0 (nth 2 (TA:assembly_coordinate_coner (list ss_pre_filter_set_xx_min_ ss_pre_filter_set_xx_max_) )))
                         (- (nth 1 (nth 2 (TA:assembly_coordinate_coner (list ss_pre_filter_set_xx_min_ ss_pre_filter_set_xx_max_) ))) 
                            110
                         )
                         (nth 2 (nth 2 (TA:assembly_coordinate_coner (list ss_pre_filter_set_xx_min_ ss_pre_filter_set_xx_max_) )))
                       ) 
        )
        100
      )
      (if (/=    nil) 
        (progn 
          (setq text_ename_ (ssname ss_finding_Text_ 0))
          (setq text_obj_ (vlax-ename->vla-object text_ename_))
          (setq insert-list_ (LM:str->lst (vla-get-textstring text_obj_) ","))
          (LM:vl-setattributevalue 
            ss_pre_filter_set_xx_obj_
            "TTL_PJ_PART-CODE"
            (strcat 
              "300"
              (nth 1 insert-list_)
              "HK-A/PF-S/ACOUS"
              "-"
              "\\P"
              (cond
                ( (= (wcmatch (nth 4 insert-list_) "standard_shape") T)
                  (progn
                    "STD"
                  )
                )
                ( (and
                    (= (wcmatch (nth 4 insert-list_) "*varies*") T)
                    (= (TA:KeepNumber (nth 4 insert-list_)) "")
                  )
                  (progn
                    "VAR"
                  )
                )
                ( (and
                    (= (wcmatch (nth 4 insert-list_) "*varies*") T)
                    (/= (TA:KeepNumber (nth 4 insert-list_)) "")
                  )
                  (progn
                    (strcat "VAR-" (TA:KeepNumber (nth 4 insert-list_))  )
                  )
                )
                ( (and
                    (= (wcmatch (nth 4 insert-list_) "*trapezoids*") T)
                    (= (TA:KeepNumber (nth 4 insert-list_)) "")
                  )
                  (progn
                    "TZD"
                  )
                )
                ( (and
                    (= (wcmatch (nth 4 insert-list_) "*trapezoids*") T)
                    (/= (TA:KeepNumber (nth 4 insert-list_)) "")
                  )
                  (progn
                    (strcat "TZD-" (TA:KeepNumber (nth 4 insert-list_))  )
                  )
                )
              )
              "/"
              "("
              (nth 0 insert-list_)
              ","
              (nth 2 insert-list_)
              ","
              (TA:GetBracketData (vla-get-textstring text_obj_))
              ")"
            )
          )
          (LM:vl-setattributevalue ss_pre_filter_set_xx_obj_ "TTL_PJ_PART-NAME" "Alu.hook on Panel")
          (LM:vl-setattributevalue ss_pre_filter_set_xx_obj_ "TTL_PJ_MATTERIAL" "Alu.hook on Panel")
          (LM:vl-setattributevalue ss_pre_filter_set_xx_obj_ "TTL_PJ_SPEC" "1100 H14")
          (LM:vl-setattributevalue ss_pre_filter_set_xx_obj_ "TTL_PJ_THK" "1.2 mm.")
          (LM:vl-setattributevalue ss_pre_filter_set_xx_obj_ "TTL_PJ_FINISH_1" (nth 3 insert-list_))
          (LM:vl-setattributevalue ss_pre_filter_set_xx_obj_ "TTL_PJ_FINISH_2" "ONE SIDE PAINT")
          (LM:vl-setattributevalue ss_pre_filter_set_xx_obj_ "TTL_PJ_DWG_TITLE" "ALU. HOOK ON PANEL MEP - PART")
        )
      )
      (getstring (strcat 
              "300"
              (nth 1 insert-list_)
              "HK-A/PF-S/ACOUS"
              "-"
              "\\P"
              (cond
                ( (= (wcmatch (nth 4 insert-list_) "standard_shape") T)
                  (progn
                    "STD"
                  )
                )
                ( (= (wcmatch (nth 4 insert-list_) "*varies*") T)
                  (progn
                    "VAR"
                  )
                )
                ( (= (wcmatch (nth 4 insert-list_) "*trapezoids*") T)
                  (progn
                    "TZD"
                  )
                )
              )
              "/"
              "("
              (nth 0 insert-list_)
              ","
              (nth 2 insert-list_)
              ","
              (TA:GetBracketData (vla-get-textstring text_obj_))
              ")"
              "--------------------"
              (rtos ss_pre_filter_set_xx_i 2 0) "/" (rtos (sslength ss_pre_filter_set_xx_) 2 0)
            ))
      (setq ss_pre_filter_set_xx_i (+ ss_pre_filter_set_xx_i 1))
      (princ (strcat (rtos ss_pre_filter_set_xx_i 2 0) "/" (rtos (sslength ss_pre_filter_set_xx_) 2 0)))
    )
  ;
)

(defun c:foo ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
    (setq ss_pre_filter_set_xx_ (TA:EF_Filter_ss_set_ ss_pre_filter_set_xx_ "xxxxxxxxxxxxxxxxxxxxxxxxxxxx"))
  ;
  ;get_data_process_for_fillter_blk_name
    (if
      (and
        (= (sslength ss_pre_filter_set_xx_) 1)
        (= (vla-get-objectname (vlax-ename->vla-object (ssname ss_pre_filter_set_xx_ 0))) "AcDbBlockReference")
        (= (LM:effectivename (vlax-ename->vla-object (ssname ss_pre_filter_set_xx_ 0)) ) "LV_DATA_FROM_EXCEl" )
      )
      (progn
        (setq LV_DATA_FROM_EXCEl_list_ (LM:vl-getattributevalues (vlax-ename->vla-object (ssname ss_pre_filter_set_xx_ 0))))
      )
    )
  ;                                                                                                                         
)



(defun c:temp_1 ()
  ;selection_set_for_fillter_blk_name
    (if  ;pre_select_ssget_or_post_select_ssget
      (=
        (setq ss_pre_filter_set_xx_ (ssget "i"
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
        nil
      )
      (progn
        (setq ss_pre_filter_set_xx_ (ssget
                                          (list
                                            (cons 0 "INSERT") ;type of object
                                            ; (cons 8 "000 - GRID")   ;kind of layer
                                            ; (cons 2 "000-GRID_LINE_DYN")       ;kind of nameblock
                                            ; (cons 62 1)           ;kind of color call sign with color code index
                                          )
                                    )
        )
      )
      (sslength ss_pre_filter_set_xx_)
    )
  ;
  ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object  ss_pre_filter_set_xx_ename_))
      (LM:setdynpropvalue ss_pre_filter_set_xx_obj_ "distance2"  (/ (LM:getdynpropvalue ss_pre_filter_set_xx_obj_ "OVL-L" ) 2))
      (setq ss_pre_filter_set_xx_i (+ ss_pre_filter_set_xx_i 1))
    )
  ;                                                                                                                         
)


(defun c:ROUND_PANEL_SIZE_UP ()
  ;selection_set_for_filter_blk_name
    (if
      (=
        (setq ss_pre_filter_set_xx_
          (ssget "i"
            (list
              (cons 0 "INSERT") ;type of object
            )
          )
        )
        nil
      )
      (setq ss_pre_filter_set_xx_
        (ssget
          (list
            (cons 0 "INSERT") ;type of object
          )
        )
      )
    )
  ;

  (if ss_pre_filter_set_xx_
    (progn
      ;preloop_and_while
        (setq ss_pre_filter_set_xx_i 0)
        (while (< ss_pre_filter_set_xx_i (sslength ss_pre_filter_set_xx_))
          (setq ss_pre_filter_set_xx_ename_
            (ssname ss_pre_filter_set_xx_ ss_pre_filter_set_xx_i)
          )
          (setq ss_pre_filter_set_xx_obj_
            (vlax-ename->vla-object ss_pre_filter_set_xx_ename_)
          )

          ;panel_length
            (setq panel_length_val_
              (LM:vl-getattributevalue ss_pre_filter_set_xx_obj_ "panel_length")
            )
            (if
              (and
                panel_length_val_
                (setq panel_length_num_ (distof panel_length_val_ 2))
              )
              (LM:vl-setattributevalue
                ss_pre_filter_set_xx_obj_
                "panel_length"
                (rtos (LM:roundup panel_length_num_ 1.0) 2 0)
              )
            )
          ;

          ;panel_width
            (setq panel_width_val_
              (LM:vl-getattributevalue ss_pre_filter_set_xx_obj_ "panel_width")
            )
            (if
              (and
                panel_width_val_
                (setq panel_width_num_ (distof panel_width_val_ 2))
              )
              (LM:vl-setattributevalue
                ss_pre_filter_set_xx_obj_
                "panel_width"
                (rtos (LM:roundup panel_width_num_ 1.0) 2 0)
              )
            )
          ;

          (setq ss_pre_filter_set_xx_i (+ ss_pre_filter_set_xx_i 1))
        )
      ;
    )
    (princ "\nNo INSERT selected.")
  )
  (princ)
)

(defun c:SET_SELF_DRILL_NO8 ()
  ;selection_set_for_filter_blk_name
    (if
      (=
        (setq ss_pre_filter_set_xx_
          (ssget "i"
            (list
              (cons 0 "INSERT") ;type of object
            )
          )
        )
        nil
      )
      (setq ss_pre_filter_set_xx_
        (ssget
          (list
            (cons 0 "INSERT") ;type of object
          )
        )
      )
    )
  ;

  (if ss_pre_filter_set_xx_
    (progn
      ;preloop_and_while
        (setq ss_pre_filter_set_xx_i 0)
        (while (< ss_pre_filter_set_xx_i (sslength ss_pre_filter_set_xx_))
          (setq ss_pre_filter_set_xx_ename_
            (ssname ss_pre_filter_set_xx_ ss_pre_filter_set_xx_i)
          )
          (setq ss_pre_filter_set_xx_obj_
            (vlax-ename->vla-object ss_pre_filter_set_xx_ename_)
          )

          (setq panel_length_val_
            (LM:vl-getattributevalue ss_pre_filter_set_xx_obj_ "panel_length")
          )

          (if
            (and
              panel_length_val_
              (setq panel_length_num_ (distof panel_length_val_ 2))
            )
            (LM:vl-setattributevalue
              ss_pre_filter_set_xx_obj_
              "SELF_DRILL_NO8"
              (rtos
                (LM:roundup (* (/ panel_length_num_ 300.0) 2) 1.0)
                2
                0
              )
            )
          )

          (setq ss_pre_filter_set_xx_i (+ ss_pre_filter_set_xx_i 1))
        )
      ;
    )
    (princ "\nNo INSERT selected.")
  )
  (princ)
)
(defun c:SET_PANEL_HARDWARE_QTY1 ()
  ;selection_set_for_filter_blk_name
    (if
      (=
        (setq ss_pre_filter_set_xx_
          (ssget "i"
            (list
              (cons 0 "INSERT") ;type of object
            )
          )
        )
        nil
      )
      (setq ss_pre_filter_set_xx_
        (ssget
          (list
            (cons 0 "INSERT") ;type of object
          )
        )
      )
    )
  ;

  (if ss_pre_filter_set_xx_
    (progn
      ;preloop_and_while
        (setq ss_pre_filter_set_xx_i 0)
        (while (< ss_pre_filter_set_xx_i (sslength ss_pre_filter_set_xx_))
          (setq ss_pre_filter_set_xx_ename_
            (ssname ss_pre_filter_set_xx_ ss_pre_filter_set_xx_i)
          )
          (setq ss_pre_filter_set_xx_obj_
            (vlax-ename->vla-object ss_pre_filter_set_xx_ename_)
          )

          (setq panel_length_val_
            (LM:vl-getattributevalue ss_pre_filter_set_xx_obj_ "panel_length")
          )
          (setq panel_width_val_
            (LM:vl-getattributevalue ss_pre_filter_set_xx_obj_ "panel_width")
          )

          (if
            (and
              panel_length_val_
              panel_width_val_
              (setq panel_length_num_ (distof panel_length_val_ 2))
              (setq panel_width_num_ (distof panel_width_val_ 2))
            )
            (progn
              ;ปัดขึ้นก่อน แล้วคูณ 2
                (setq length_qty_
                  (* 2.0
                    (LM:roundup (/ panel_length_num_ 300.0) 1.0)
                  )
                )
              ;

              ;เส้นรอบรูป = 2 x (length + width)
                (setq perimeter_qty_
                  (LM:roundup
                    (/ (* 2.0 (+ panel_length_num_ panel_width_num_)) 300.0)
                    1.0
                  )
                )
              ;

              (LM:vl-setattributevalue
                ss_pre_filter_set_xx_obj_
                "SELF_DRILL_NO8"
                (rtos perimeter_qty_ 2 0)
              )
              (LM:vl-setattributevalue
                ss_pre_filter_set_xx_obj_
                "BRACKET_A_VAL"
                (rtos perimeter_qty_ 2 0)
              )
              (LM:vl-setattributevalue
                ss_pre_filter_set_xx_obj_
                "BRACKET_B_VAL"
                (rtos perimeter_qty_ 2 0)
              )
              (LM:vl-setattributevalue
                ss_pre_filter_set_xx_obj_
                "Rivet_5-4_VAL"
                (rtos (* perimeter_qty_ 2) 2 0)
              )
            )
          )

          (setq ss_pre_filter_set_xx_i (+ ss_pre_filter_set_xx_i 1))
        )
      ;
    )
    (princ "\nNo INSERT selected.")
  )
  (princ)
)


(defun c:findatttemp1 ()
  (if (and 
        ; (/= att-pre_filter_set_xx_ nil)
        ; (= (TA:getkword "new input selection-set ?"  "Yes" "No"  att-pre_filter_set_xx_ "false") nil) ;พัง
        (= 1 1)
      )
    (progn
      ;selection_set_for_fillter_blk_name
        (if  ;pre_select_ssget_or_post_select_ssget
          (=
            (setq att-pre_filter_set_xx_ (ssget "i"
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
            nil
          )
          (progn
            (setq att-pre_filter_set_xx_ (ssget
                                              (list
                                                (cons 0 "INSERT") ;type of object
                                                ; (cons 8 "000 - GRID")   ;kind of layer
                                                ; (cons 2 "000-GRID_LINE_DYN")       ;kind of nameblock
                                                ; (cons 62 1)           ;kind of color call sign with color code index
                                              )
                                        )
            )
          )
          (sslength att-pre_filter_set_xx_)
        )
      ;
    )
  )
  (setq att-value_multi-list_ (list "*E1_PL_02*" "*E1_PL_03*" "*E1_PL_04*" "*E1_PL_05*" 
                                    "*E2_PL_07*" "*E2_PL_08*" "*E2_PL_09*" "*E2_PL_10*" 
                                    "*E1_PL_06*" "*E4_PL_03*" "*E4_PL_04*" "*E4_PL_05*" 
                                    "*E4_PL_06*" "*E4_PL_07*" "*E4_PL_01*"
                              )
  )
  ;preloop_and_while
    (setq att-pre_filter_set_xx_i 0)
    (setq att-pre_filter_set_xx_new-ss_ (ssadd))
    (while (and 
              (= (type att-pre_filter_set_xx_) 'PICKSET)
              (< att-pre_filter_set_xx_i (sslength att-pre_filter_set_xx_))
            )
      (setq att-pre_filter_set_xx_ename_ (ssname att-pre_filter_set_xx_ att-pre_filter_set_xx_i)) 
      (setq att-pre_filter_set_xx_obj_ (vlax-ename->vla-object  att-pre_filter_set_xx_ename_))
      
      (if (and 
            (= (vla-get-hasattributes att-pre_filter_set_xx_obj_) :vlax-true)
            (/= (setq att-pre_filter_set_xx_obj_val-list_ (nth 0 (LM:vl-getattributevalue-val-TA-Modifies att-pre_filter_set_xx_obj_)) ) nil)
            ; (and 
            ;   (= att-finder_mode "multi-name")
            ; )
          )
        (progn 
          (if (/= (setq att-pre_filter_set_xx_obj_match-val_ (TA:wcmatch_list_rev02 att-value_multi-list_ (list att-pre_filter_set_xx_obj_val-list_) nil)) nil)
            (progn
              (setq att-pre_filter_set_xx_new-ss_ (ssadd att-pre_filter_set_xx_ename_ att-pre_filter_set_xx_new-ss_ ))
            )
          )
        )
      )
      (setq att-pre_filter_set_xx_i (+ att-pre_filter_set_xx_i 1))
    )
  ;
  (command "pselect"  att-pre_filter_set_xx_new-ss_ "" )
)
;Matterial_TAKEOFF_FUNCTION_
  (defun TA:Group_Accessories_By_Name_ (block_data_list_ / group_list_ block_data_ group_name_ found_)
    (setq group_list_ ())

    (foreach block_data_ block_data_list_
      (if block_data_
        (progn
          (setq group_name_ (caar block_data_))

          (if (setq found_ (assoc group_name_ group_list_))
            (setq group_list_
              (subst
                (cons group_name_ (append (cdr found_) block_data_))
                found_
                group_list_
              )
            )
            (setq group_list_
              (append
                group_list_
                (list (cons group_name_ block_data_))
              )
            )
          )
        )
      )
    )

    (mapcar
      '(lambda (group_)
        (cons
          (car group_)
          (TA:GroupSum_ (cdr group_))
        )
      )
      group_list_
    )
  )
  (defun TA:Grouped_Accessories_To_CSVRows_ (grouped_data_ / csv_rows_)
    (setq csv_rows_ (list (list "GROUP_NAME" "ITEM_NAME" "QTY")))

    (foreach group_ grouped_data_
      (foreach item_ (cdr group_)
        (setq csv_rows_
          (append
            csv_rows_
            (list
              (list
                (car group_)
                (car item_)
                (vl-princ-to-string (cdr item_))
              )
            )
          )
        )
      )
    )

    csv_rows_
  )
  (defun TA:ATTRIBUTE_EDITOR (att_blkname_ ins_pos_ scc att-set0 att-set1 att-set2 att-set3 att-set4 att-set5 att-set6 att-set7 att-set8  )
    (TA:vla-insertblock 
      att_blkname_
      ins_pos_
      scc
      0
    )
    (LM:vl-setattributevalue (vlax-ename->vla-object (entlast)) (nth 0 att-set0) (nth 1 att-set0) )
    (LM:vl-setattributevalue (vlax-ename->vla-object (entlast)) (nth 0 att-set1) (nth 1 att-set1) )
    (LM:vl-setattributevalue (vlax-ename->vla-object (entlast)) (nth 0 att-set2) (nth 1 att-set2) )
    (LM:vl-setattributevalue (vlax-ename->vla-object (entlast)) (nth 0 att-set3) (nth 1 att-set3) )
    (LM:vl-setattributevalue (vlax-ename->vla-object (entlast)) (nth 0 att-set4) (nth 1 att-set4) )
    (LM:vl-setattributevalue (vlax-ename->vla-object (entlast)) (nth 0 att-set5) (nth 1 att-set5) )
    (LM:vl-setattributevalue (vlax-ename->vla-object (entlast)) (nth 0 att-set6) (nth 1 att-set6) )
    (LM:vl-setattributevalue (vlax-ename->vla-object (entlast)) (nth 0 att-set7) (nth 1 att-set7) )
    (LM:vl-setattributevalue (vlax-ename->vla-object (entlast)) (nth 0 att-set8) (nth 1 att-set8) )

  )
  (defun c:insacbox1 ()
    ;presetting_
      (setq ins_pos_ii 4)
      (setq scc 25)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list "A$C549e3519" "A$C5c8b8333" "010 - C10_PANEL_PANEL_PP17_BOT-VIEW" "010 - C10_PANEL_PANEL_PP17-E_BOT-VIEW")))
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP17-C10-UPPER PANEL" "-" (rtos (LM:getdynpropvalue ss_pre_filter_set_xx_obj_ "Distance1" ) 2 2) ",1"))
        (setq att-set0 (list "name" "PP17-C10-UPPER&LOWER BORDER" )
                att-set1 (list "acc_1" "BKK-A,12" )
                att-set2 (list "acc_2" "BKK-B,12" )
                att-set3 (list "acc_3" "Rivet,48" )
                att-set4 (list "acc_4" "self-drilling No8 3/4,24" )
                att-set5 (list "acc_5" "BK50x50,2" )
                att-set6 (list "acc_6" "BK50x50,2" )
                att-set7 (list "acc_7" "EB-04,2" )
                att-set8 (list "acc_8" dist_1 )
          )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox1-1 () ;pp17-lower-border
    ;presetting_
      (setq ins_pos_ii 4)
      (setq scc 25)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "IT3-M3-2026-0061-0069_แบบขอตัวอย่างสินค้าสั่งทำพิเศษ C10 MOCKUP PP18_20260823-001602[PP19][C10][C][LOWER-BORDER][BOT-VIEW]" 
                                                                                 "000 - MCK__20260804-194028_PP18_C10_LC-LOWER-SOLID_SHEET_BOT_VIEW" 
                                                                               )
                                )
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP17-C10-LOWER PANEL" "-" (rtos (LM:getdynpropvalue ss_pre_filter_set_xx_obj_ "Distance1" ) 2 2) ",1"))
        (setq att-set0 (list "name" "PP17-C10-UPPER&LOWER BORDER" )
                att-set1 (list "acc_1" dist_1 )
                att-set2 (list "acc_2" "" )
                att-set3 (list "acc_3" "" )
                att-set4 (list "acc_4" "" )
                att-set5 (list "acc_5" "" )
                att-set6 (list "acc_6" "" )
                att-set7 (list "acc_7" "" )
                att-set8 (list "acc_8" "" )
          )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox2 ()
    ;presetting_
      (setq ins_pos_ii 4)
      (setq scc 25)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list "A$C549e3519" "A$C5c8b8333" "010 - C10_PANEL_PANEL_PP17_BOT-VIEW" "010 - C10_PANEL_PANEL_PP17-E_BOT-VIEW")))
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP17-C10-Border-length" "-" (rtos (LM:getdynpropvalue ss_pre_filter_set_xx_obj_ "Distance1" ) 2 2) ",1"))
        (setq att-set0 (list "name" "PP17-UPPER-BORDER-ACESSORIES-300HK" )
          att-set1 (list "acc_1" "U-HOOK,1" )
          att-set2 (list "acc_2" "V-HOOK,1" )
          att-set3 (list "acc_3" "Rivet,4" )
          att-set4 (list "acc_4" "LK-04,2" )
          att-set5 (list "acc_5" "LK-01,1" )
          att-set6 (list "acc_6" dist_1 )
          att-set7 (list "acc_7" "" )
          att-set8 (list "acc_8" "" )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox3 ()
    ;presetting_
      (setq ins_pos_ii 4)
      (setq scc 25)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "000 - MCK__20260804-194028_PP18_C10_LC-UPPER-SOLID_SHEET_BOT_VIEW"
                                                                                 "000 - MCK__20260804-194028_PP18_C10_C-UPPER-SOLID_SHEET_BOT_VIEW"
                                                                               )
                                )
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP18-C10-UPPER Border-length" "-" (rtos (LM:getdynpropvalue ss_pre_filter_set_xx_obj_ "Distance1" ) 2 2) ",1"))
        (setq att-set0 (list "name" "PP17-UPPER-BORDER-ACESSORIES-BORDER" )
          att-set1 (list "acc_1" "BKK-A,4" )
          att-set2 (list "acc_2" "BKK-B,4" )
          att-set3 (list "acc_3" "Rivet,16" )
          att-set4 (list "acc_4" "self-drilling No8 3/4,12" )
          att-set5 (list "acc_5" "BK50x50,2" )
          att-set6 (list "acc_6" "EB-04,2" )
          att-set7 (list "acc_7" dist_1 )
          att-set8 (list "acc_8" "" )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox4 ()
    ;presetting_
      (setq ins_pos_ii 4)
      (setq scc 25)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "000 - MCK__20260804-194028_PP18_C10_LC-LOWER-SOLID_SHEET_BOT_VIEW"
                                                                                 "000 - MCK__20260804-194028_PP18_C10_RC-LOWER-SOLID_SHEET_BOT_VIEW"
                                                                                 "000 - MCK__20260804-194028_PP18_C10_C-LOWER-SOLID_SHEET_BOT_VIEW"
                                                                               )
                                )
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP18-C10-LOWER Border-length" "-" (rtos (LM:getdynpropvalue ss_pre_filter_set_xx_obj_ "Distance1" ) 2 2) ",1"))
        (setq att-set0 (list "name" "PP18-C10-LOWER Border-length" )
          att-set1 (list "acc_1" dist_1 )
          att-set2 (list "acc_2" "" )
          att-set3 (list "acc_3" "" )
          att-set4 (list "acc_4" "" )
          att-set5 (list "acc_5" "" )
          att-set6 (list "acc_6" "" )
          att-set7 (list "acc_7" "" )
          att-set8 (list "acc_8" "" )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox5 ()
    ;presetting_
      (setq ins_pos_ii 4)
      (setq scc 10)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "010 - C10_PANEL_PANEL_GREEN_PLATE_SET-A-BOT-VIEW"
                                                                                 "010 - C10_PANEL_PANEL_GREEN_PLATE_SET-B-BOT-VIEW"
                                                                                 "010 - C10_PANEL_PANEL_GREEN_PLATE_SET-C-BOT-VIEW"
                                                                                 "010 - C10_PANEL_PANEL_GREEN_PLATE_SET-D-BOT-VIEW"
                                                                               )
                                )
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (if (= (type (vl-string-search "SET-D" (LM:EffectiveName ss_pre_filter_set_xx_obj_ ) 1) ) 'INT )
          (progn
            (setq dist_1 (strcat "PP18-C10-PANEL" "-" (substr (LM:EffectiveName ss_pre_filter_set_xx_obj_ ) (+ 34 1)  5) "-" (rtos (LM:getdynpropvalue ss_pre_filter_set_xx_obj_ "Distance1" ) 2 2) ",1"))
          )
          (setq dist_1 (strcat "PP18-C10-PANEL-" (substr (LM:EffectiveName ss_pre_filter_set_xx_obj_ ) (+ 34 1)  5) ",1" ))
        )
        (setq att-set0 (list "name" "PP18-PANEL-ACESSORIES" )
          att-set1 (list "acc_1" "MEGA-BRACKET-CLIP-LENGTH-300,2" )
          att-set2 (list "acc_2" "RIVET 4-4,1" )
          att-set3 (list "acc_3" "CLAMP-RAIL-length-350,2" )
          att-set4 (list "acc_4" "CLAMP-LOCK,4" )
          att-set5 (list "acc_5" dist_1 )
          att-set6 (list "acc_6" "" )
          att-set7 (list "acc_7" "" )
          att-set8 (list "acc_8" "" )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox6 () ;เหล็กแผ่นโค้ง pp18
    ;presetting_
      (setq ins_pos_ii 4)
      (setq scc 10)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list "facade_1_MAXLEN") ) )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq att-set0 (list "name" "PP18-PANEL-ACESSORIES" )
          att-set1 (list "acc_1" "MEGA-BRACKET-CLIP-LENGTH-300,2" )
          att-set2 (list "acc_2" "RIVET 4-4,1" )
          att-set3 (list "acc_3" "CLAMP-RAIL-length-350,2" )
          att-set4 (list "acc_4" "CLAMP-LOCK,4" )
          att-set5 (list "acc_5" dist_1 )
          att-set6 (list "acc_6" "" )
          att-set7 (list "acc_7" "" )
          att-set8 (list "acc_8" "" )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox7 () ;upper border pp19
    ;presetting_
      (setq ins_pos_ii 4)
      (setq scc 10)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "IT3-M3-2026-0061-0069_แบบขอตัวอย่างสินค้าสั่งทำพิเศษ C10 MOCKUP PP18_20260823-001602[PP19][C10][LC][RC][UPPER-BORDER]"
                                                                                 "IT3-M3-2026-0061-0069_แบบขอตัวอย่างสินค้าสั่งทำพิเศษ C10 MOCKUP PP18_20260823-001602[PP19][C10][C][UPPER-BORDER][BOT-VIEW]"
                                                                               ) 
                                ) 
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP19-C10-UPPER border" "-" (rtos (LM:getdynpropvalue ss_pre_filter_set_xx_obj_ "Distance1" ) 2 2) ",1"))
        (setq att-set0 (list "name" "PP19-C10-UPPER Border-length" )
              att-set1 (list "acc_1" "BKK-A,3" )
              att-set2 (list "acc_2" "BKK-B,3" )
              att-set3 (list "acc_3" "Rivet,12" )
              att-set4 (list "acc_4" "self-drilling No8 3/4,3" )
              att-set5 (list "acc_5" "STEEL-BK50x50,2" )
              att-set6 (list "acc_6" "STEEL-BK50x50,2" )
              att-set7 (list "acc_7" "EB-04,2" )
              att-set8 (list "acc_8" dist_1 )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox8 () ;upper border pp19
    ;presetting_
      (setq ins_pos_ii 4)
      (setq scc 10)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "000 - MCK__20260804-194028_PP18_C10_LC-LOWER-SOLID_SHEET_BOT_VIEW"
                                                                                 "IT3-M3-2026-0061-0069_แบบขอตัวอย่างสินค้าสั่งทำพิเศษ C10 MOCKUP PP18_20260823-001602[PP19][C10][C][LOWER-BORDER][BOT-VIEW]"
                                                                               ) 
                                ) 
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP19-C10-UPPER border" "-" (rtos (LM:getdynpropvalue ss_pre_filter_set_xx_obj_ "Distance1" ) 2 2) ",1"))
        (setq att-set0 (list "name" "PP19-C10-LOWER Border-length" )
              att-set1 (list "acc_1" dist_1 )
              att-set2 (list "acc_2" "" )
              att-set3 (list "acc_3" "" )
              att-set4 (list "acc_4" "" )
              att-set5 (list "acc_5" "" )
              att-set6 (list "acc_6" "" )
              att-set7 (list "acc_7" "" )
              att-set8 (list "acc_8" dist_1 )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:insacbox9 () ;hookon pp19
    ;presetting_
      (setq ins_pos_ii 4)
      (setq scc 10)
    ;
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq ss_pre_filter_set_xx_ (TA:EF_Filter_ss_set_v2_ ss_pre_filter_set_xx_ (list 
                                                                                 "010 - C10_PANEL_PANEL_PP17_BOT-VIEW"
                                                                                ;  "010 - C10_PANEL_PANEL_PP17-E_BOT-VIEW"
                                                                               ) 
                                ) 
    )
    ;preloop_and_while
      (setq ss_pre_filter_set_xx_i 0)
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq ss_pre_filter_set_xx_obj_getboundingbox (vla-getboundingbox ss_pre_filter_set_xx_obj_ 'min_ 'max_)) 
        (setq ss_pre_filter_set_xx_min_ (TA:get-ins-current (vlax-safearray->list min_))) 
        (setq ss_pre_filter_set_xx_max_ (TA:get-ins-current (vlax-safearray->list max_))) 
        
        (setq ins_pos_ (nth ins_pos_ii (TA:assembly_coordinate_coner (list ss_pre_filter_set_xx_min_ ss_pre_filter_set_xx_max_) )))
        (setq dist_1 (strcat "PP19-300HK-PANEL" "-" (rtos (LM:getdynpropvalue ss_pre_filter_set_xx_obj_ "Distance1" ) 2 2) ",1"))
        (setq att-set0 (list "name" "PP19-C10-PANEL" )
          att-set1 (list "acc_1" "U-HOOK,1" )
          att-set2 (list "acc_2" "V-HOOK,1" )
          att-set3 (list "acc_3" "Rivet,4" )
          att-set4 (list "acc_4" "LK-04,2" )
          att-set5 (list "acc_5" "LK-01,1" )
          att-set6 (list "acc_6" dist_1 )
          att-set7 (list "acc_7" "" )
          att-set8 (list "acc_8" "" )
        )
        (TA:ATTRIBUTE_EDITOR "facade_1_acessoriesset" (trans ins_pos_ 1 0)  scc att-set0 att-set1 att-set2 att-set3 att-set4 att-set5 att-set6 att-set7 att-set8 )
        (setq ss_pre_filter_set_xx_i (+ ss_pre_filter_set_xx_i 1))
      )
    ;
  )
  (defun c:sumaray_acessories_box_sumacbox ()
    ;selection_set_for_fillter_blk_name
      (if
        (=
          (setq ss_pre_filter_set_xx_
            (ssget "i"
              (list
                (cons 0 "INSERT") ;type of object
                ; (cons 8 "000 - GRID") ;kind of layer
                ; (cons 2 "000-GRID_LINE_DYN") ;kind of nameblock
                ; (cons 62 1) ;kind of color
              )
            )
          )
          nil
        )
        (progn
          (setq ss_pre_filter_set_xx_
            (ssget
              (list
                (cons 0 "INSERT") ;type of object
                ; (cons 8 "000 - GRID") ;kind of layer
                ; (cons 2 "000-GRID_LINE_DYN") ;kind of nameblock
                ; (cons 62 1) ;kind of color
              )
            )
          )
        )
        (sslength ss_pre_filter_set_xx_)
      )
    ;

    (if ss_pre_filter_set_xx_
      (progn
        (setq fitler_ename_ (car (entsel "\nSpecify name Object: ")))

        (if fitler_ename_
          (progn
            (setq fitler_obj_ (vlax-ename->vla-object fitler_ename_))
            (setq fitler_obj_Efname (LM:EffectiveName fitler_obj_))

            (setq ss_pre_filter_set_xx_ (TA:EF_Filter_ss_set_v2_ ss_pre_filter_set_xx_ (list "facade_1_acessoriesset" "facade_1_MAXLEN") ) )

            ;preloop_and_while
              (setq ss_pre_filter_set_xx_i 0)
              (setq ss_pre_filter_set_xx_aclist_ ())

              (while (< ss_pre_filter_set_xx_i (sslength ss_pre_filter_set_xx_))
                (setq ss_pre_filter_set_xx_ename_ (ssname ss_pre_filter_set_xx_ ss_pre_filter_set_xx_i) )
                (setq ss_pre_filter_set_xx_obj_ (vlax-ename->vla-object ss_pre_filter_set_xx_ename_) )
                (setq data_ (LM:vl-getattributevalue-val-TA-Modifies ss_pre_filter_set_xx_obj_ ) )
                (setq result_
                  (mapcar
                    '(lambda (item_ / comma_pos_)
                      (if (setq comma_pos_ (vl-string-search "," item_))
                        (cons
                          (substr item_ 1 comma_pos_)
                          (atoi (substr item_ (+ comma_pos_ 2)))
                        )
                        (cons item_ 0)
                      )
                    )
                    data_
                  )
                )

                ;เก็บ result_ แยกเป็นชุดของแต่ละบล็อก
                (setq ss_pre_filter_set_xx_aclist_ (append ss_pre_filter_set_xx_aclist_ (list result_)) )

                (setq ss_pre_filter_set_xx_i (+ ss_pre_filter_set_xx_i 1))
              )
            ;

            (setq grouped_acsummary_ (TA:Group_Accessories_By_Name_ ss_pre_filter_set_xx_aclist_ ) )

            (setq csv_rows_ (TA:Grouped_Accessories_To_CSVRows_ grouped_acsummary_ ) )

            (setq filepath (getvar "DWGPREFIX"))
            (setq filename_ (strcat (LM:StringSubst "" ".dwg" (getvar "DWGNAME")) ".csv" ) )

            (if (findfile (strcat filepath filename_))
              (LM:writecsv csv_rows_ (strcat filepath (LM:StringSubst "-" "." (rtos (getvar "CDATE") 2 8)) "-" filename_ ) )
              (LM:writecsv csv_rows_ (strcat filepath filename_) )
            )
          )
        )
      )
    )
    (princ)
  )
  (defun c:unqiue_attval_ ()
    ;selection_set_for_fillter_blk_name
      (if  ;pre_select_ssget_or_post_select_ssget
        (=
          (setq ss_pre_filter_set_xx_ (ssget "i"
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn
          (setq ss_pre_filter_set_xx_ (ssget
                                            (list
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
        )
        (sslength ss_pre_filter_set_xx_)
      )
    ;
    (setq fitler_ename_ (car (entsel "specify name Object")))
    (setq fitler_obj_ (vlax-ename->vla-object fitler_ename_))
    (setq fitler_obj_Efname (LM:EffectiveName fitler_obj_ ))
    (setq att-target_ename_ (car (nentsel "specify Attribute Tag Object")))
    (setq att-target_obj_ (vlax-ename->vla-object att-target_ename_))
    (setq att-target_obj_atttag_ (vla-get-tagstring att-target_obj_ ))
    
    (setq ss_pre_filter_set_xx_ (TA:EF_Filter_ss_set_ ss_pre_filter_set_xx_ fitler_obj_Efname))
    ;preloop_and_while
      (setq ss_pre_filter_set_xx_i 0)
      (setq unique_list_ ())
      (while (< ss_pre_filter_set_xx_i (sslength ss_pre_filter_set_xx_))
        (setq ss_pre_filter_set_xx_ename_ (ssname ss_pre_filter_set_xx_ ss_pre_filter_set_xx_i))
        (setq ss_pre_filter_set_xx_obj_ (vlax-ename->vla-object  ss_pre_filter_set_xx_ename_))
        (setq result_ (LM:vl-getattributevalue ss_pre_filter_set_xx_obj_ att-target_obj_atttag_ ))
        ; (setq result_ (car 
        ;                 (mapcar 
        ;                   '(lambda (item_ / comma_pos_) 
        ;                      (if (setq comma_pos_ (vl-string-search "," item_)) 
        ;                        (cons 
        ;                          (substr item_ 1 comma_pos_)
        ;                          (atoi (substr item_ (+ comma_pos_ 2)))
        ;                        )
        ;                        (cons item_ 0)
        ;                      )
        ;                    )
        ;                   (list (LM:vl-getattributevalue ss_pre_filter_set_xx_obj_ att-target_obj_atttag_ ) )
        ;                 )
        ;               )
        ; )
        (setq unique_list_ (cons result_ unique_list_))
        (setq ss_pre_filter_set_xx_i (+ ss_pre_filter_set_xx_i 1))
      )
    ;
    (setq unique_list_item (TA:Count_item_in_list_ unique_list_ ))
    
    
    (setq filepath (getvar "dwgprefix"))
    (setq filename_ (strcat (LM:StringSubst "" ".dwg"  (getvar "dwgname"))  ".csv"))
    (setq filepath_ (strcat filepath filename_))
    
    (if (findfile (strcat filepath  filename_)) 
      (progn
        (LM:writecsv (TA:PairList_to_CSVRows unique_list_item ) (strcat filepath (LM:StringSubst "-" "." (rtos (getvar "cdate") 2 8) ) "-" filename_))
      )
      (LM:writecsv (TA:PairList_to_CSVRows unique_list_item ) (strcat filepath filename_))
    )
    
  )
;


; ;selection_set_for_fillter_blk_name
;   (if  ;pre_select_ssget_or_post_select_ssget
;     (=
;       (setq ss_pre_filter_set_xx_ (ssget "i"
;                                         (list
;                                           (cons 0 "INSERT") ;type of object
;                                           ; (cons 8 "000 - GRID")   ;kind of layer
;                                           ; (cons 2 "000-GRID_LINE_DYN")       ;kind of nameblock
;                                           ; (cons 62 1)           ;kind of color call sign with color code index
;                                         )
;                                   )
;       )
;       nil
;     )
;     (progn
;       (setq ss_pre_filter_set_xx_ (ssget
;                                         (list
;                                           (cons 0 "INSERT") ;type of object
;                                           ; (cons 8 "000 - GRID")   ;kind of layer
;                                           ; (cons 2 "000-GRID_LINE_DYN")       ;kind of nameblock
;                                           ; (cons 62 1)           ;kind of color call sign with color code index
;                                         )
;                                   )
;       )
;     )
;     (sslength ss_pre_filter_set_xx_)
;   )
;   (setq ss_pre_filter_set_xx_ (TA:EF_Filter_ss_set_ ss_pre_filter_set_xx_ "facade_1_MAXLEN"))
; ;

; ;preloop_and_while
;   (setq ss_pre_filter_set_xx_i 0)
;   (while (< ss_pre_filter_set_xx_i (sslength ss_pre_filter_set_xx_))
;     (setq ss_pre_filter_set_xx_ename_ (ssname ss_pre_filter_set_xx_ ss_pre_filter_set_xx_i))
;     (setq ss_pre_filter_set_xx_obj_ (vlax-ename->vla-object  ss_pre_filter_set_xx_ename_))
;     (LM:vl-setattributevalue
;       ss_pre_filter_set_xx_obj_ 
;       "length"
;       (strcat 
;         (LM:vl-getattributevalue ss_pre_filter_set_xx_obj_ "length")
;         ",1"
;       )
;     )
;     (setq ss_pre_filter_set_xx_i (+ ss_pre_filter_set_xx_i 1))
;   )
; ;
  

; (setq ss_mtext_number_
;   (ssget "_X"
;     (list
;       (cons 0 "MTEXT")
;       (cons 1 "#,##,###")
;       (cons 8 "T E X T")
;       (cons 62 4) ;Cyan
;     )
;   )
; )
; (if ss_mtext_number_
;   (command "_.PSELECT" ss_mtext_number_ "")
; )

(defun c:PL2L ( / source_ source_obj_ text_ pos_ code_
                 size_ mesh_pos_ louver_type_ new_text_
                 target_ target_obj_
              )
  (vl-load-com)
  ;get_source_text_by_nentsel_
    (if (setq source_ (nentsel "\nSelect source TEXT: "))
      (if
        (member
          (cdr (assoc 0 (entget (car source_))))
          '("TEXT" "MTEXT")
        )
        (progn
          (setq source_obj_ (vlax-ename->vla-object (car source_)))
          (setq text_ (vla-get-TextString source_obj_))
          (if (setq pos_ (vl-string-search " SIZE " (strcase text_)))
            (progn
              ;get_code_and_louver_type_
                (setq code_ (vl-string-trim " " (substr text_ 1 pos_)))
                (setq louver_type_
                  (cond
                    ((wcmatch (strcase code_) "PL-1065*")
                      "Single"
                    )
                    ((wcmatch (strcase code_) "PL-2065*")
                      "Double"
                    )
                    (T nil)
                  )
                )
              ;
              (if louver_type_
                (progn
                  ;get_size_and_remove_mesh_
                    (setq size_ (substr text_ (+ pos_ 7)))

                    (if (setq mesh_pos_ (vl-string-search "+ MESH" (strcase size_)))
                      (setq size_ (substr size_ 1 mesh_pos_))
                    )

                    (setq size_
                      (vl-list->string
                        (vl-remove 32 (vl-string->list size_))
                      )
                    )
                    (setq size_ (vl-string-translate "X" "x" size_))
                  ;
                  ;assemble_text_
                    (setq new_text_
                      (strcat
                        code_
                        " Vertical " louver_type_
                        "\\PBank Louver "
                        size_
                        "mm."
                      )
                    )
                  ;
                  ;put_target_attribute_by_nentsel_
                    (repeat 2
                      (if (setq target_ (nentsel "\nSelect target Attribute: "))
                        (if
                          (= (cdr (assoc 0 (entget (car target_)))) "ATTRIB")
                          (progn
                            (setq target_obj_ (vlax-ename->vla-object (car target_)))
                            (vla-put-TextString target_obj_ new_text_)
                            (entupd (car target_))
                          )
                          (princ "\nTarget must be an Attribute.")
                        )
                      )
                    )
                  ;
                )
                (princ "\nSupported codes: PL-1065 / PL-2065.")
              )
            )
            (princ "\nSource text does not contain ' Size '.")
          )
        )
        (princ "\nSource must be TEXT or MTEXT.")
      )
    )
  ;
  (princ)
)
(defun c:PPENT2ATT ( / ss_ i_ ename_ obj_
                      code_ numeric_ ENTxx_ TYPEXXX_
                      tag_ new_text_
                   )
  (vl-load-com)
  ;selection_set_
    (setq ss_ (ssget "_I" (list (cons 0 "INSERT"))))
  ;
  (if ss_
    (progn
      ;user_input_
        (setq code_ "")
        (while (= code_ "")
          (setq code_ (getstring T "\nSpecify PP number or text (X = PP-XX ENT X): "))
        )

        ;check_numeric_string_
          (setq numeric_
            (vl-every
              '(lambda (char_)
                (and (>= char_ 48) (<= char_ 57))
              )
              (vl-string->list code_)
            )
          )
        ;
        ;get_ENT_when_numeric_
          (if numeric_
            (progn
              (initget 5)
              (setq ENTxx_ (getint "\nSpecify ENTxx: "))
            )
          )
        ;
        ;get_TYPE_string_
          (setq TYPEXXX_ "")
          (while (= TYPEXXX_ "")
            (setq TYPEXXX_ (getstring T "\nSpecify TYPE (example 144+191): "))
          )
        ;
        (setq tag_ "TTL_PJ_PART-CODE")
      ;
      ;assemble_text_
        (setq new_text_
          (cond
            ((= (strcase code_) "X")
              (strcat
                "PP-XX ENT X"
                " Type-" TYPEXXX_
              )
            )
            (numeric_
              (strcat
                "PP" code_
                "ENT" (itoa ENTxx_)
                " Type-" TYPEXXX_
              )
            )
            (T
              (strcat
                code_
                " Type-" TYPEXXX_
              )
            )
          )
        )
      ;
      ;preloop_and_while
        (setq i_ 0)
        (while (< i_ (sslength ss_))
          (setq ename_ (ssname ss_ i_))
          (setq obj_ (vlax-ename->vla-object ename_))

          (if (= (vla-get-HasAttributes obj_) :vlax-true)
            (LM:vl-setattributevalue obj_ tag_ new_text_)
          )

          (setq i_ (+ i_ 1))
        )
      ;
      (princ (strcat "\nText: " new_text_))
    )
    (princ "\nPlease select blocks before running the command.")
  )
  (princ)
)
(defun c:TYPE2PPENT ( / ss_ i_ ename_ obj_
                       code_ numeric_ ENTxx_ TYPEXXX_
                       tag_ new_text_
                    )
  (vl-load-com)
  ;selection_set_
    (setq ss_ (ssget "_I" (list (cons 0 "INSERT"))))
  ;
  (if ss_
    (progn
      ;user_input_
        ;get_TYPE_string_
          (setq TYPEXXX_ "")
          (while (= TYPEXXX_ "")
            (setq TYPEXXX_ (getstring T "\nSpecify TYPE: "))
          )
        ;
        ;get_PP_number_or_text_
          (setq code_ "")
          (while (= code_ "")
            (setq code_ (getstring T "\nSpecify PP number or text <X = PP-XX ENT X>: "))
          )
        ;
        ;check_numeric_string_
          (setq numeric_
            (vl-every
              '(lambda (char_)
                (and (>= char_ 48) (<= char_ 57))
              )
              (vl-string->list code_)
            )
          )
        ;
        ;get_ENT_when_numeric_
          (if numeric_
            (progn
              (initget 5)
              (setq ENTxx_ (getint "\nSpecify ENTxx: "))
            )
          )
        ;
        (setq tag_ "TTL_PJ_PART-CODE")
      ;
      ;assemble_text_
        (setq new_text_
          (cond
            ((= (strcase code_) "X")
              (strcat
                "TYPE " TYPEXXX_
                " PP-XX ENT X"
              )
            )
            (numeric_
              (strcat
                "TYPE " TYPEXXX_
                " PP-" code_
                " ENT" (itoa ENTxx_)
              )
            )
            (T
              (strcat
                "TYPE " TYPEXXX_
                " " code_
              )
            )
          )
        )
      ;
      ;preloop_and_while
        (setq i_ 0)
        (while (< i_ (sslength ss_))
          (setq ename_ (ssname ss_ i_))
          (setq obj_ (vlax-ename->vla-object ename_))

          (if (= (vla-get-HasAttributes obj_) :vlax-true)
            (LM:vl-setattributevalue obj_ tag_ new_text_)
          )

          (setq i_ (+ i_ 1))
        )
      ;
      (princ (strcat "\nText: " new_text_))
    )
    (princ "\nPlease select blocks before running the command.")
  )
  (princ)
)
